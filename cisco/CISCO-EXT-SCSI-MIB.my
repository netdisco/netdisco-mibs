-- *********************************************************************
-- CISCO-EXT-SCSI-MIB.my: Extension to SCSI Mib
--
-- October 2002, H K Vivek
--
-- Copyright (c) 2002 by cisco Systems, Inc.
-- All rights reserved.
-- 
-- *********************************************************************
CISCO-EXT-SCSI-MIB DEFINITIONS ::= BEGIN 
    
IMPORTS 
   MODULE-IDENTITY, OBJECT-TYPE,  
   Unsigned32, NOTIFICATION-TYPE             FROM SNMPv2-SMI 
   TimeStamp, TestAndIncr, TruthValue        FROM SNMPv2-TC
   MODULE-COMPLIANCE, OBJECT-GROUP,
   NOTIFICATION-GROUP                        FROM SNMPv2-CONF 
   ciscoMgmt                                 FROM CISCO-SMI
   VsanIndex                                 FROM CISCO-ST-TC
   ciscoScsiInstanceEntry,
   ciscoScsiDscTgtEntry, 
   ciscoScsiDscLunEntry                      FROM CISCO-SCSI-MIB;
           
                   
    
ciscoExtScsiMIB MODULE-IDENTITY 
   LAST-UPDATED "200210100000Z"          
   ORGANIZATION "Cisco Systems Inc." 
   CONTACT-INFO 
                "     Cisco Systems
                      Customer Service
                Postal: 170 W Tasman Drive
                      San Jose, CA  95134
                      USA
                Tel: +1 800 553 -NETS
                E-mail: cs-san@cisco.com"
   DESCRIPTION  "The Cisco extension to CISCO-SCSI-MIB
                 which is a copy of the Internet draft, 
                 the SCSI-MIB, from the IETF."
   REVISION     "200210100000Z"
   DESCRIPTION  "Added ciscoExtScsiNotificationCntl object
                 and ciscoExtScsiLunDiscDoneNotify
                 notification."
   REVISION     "200210050000Z"            
   DESCRIPTION  "Initial version of this MIB." 
   ::= { ciscoMgmt 299 }
    
ciscoExtScsiMIBObjects     OBJECT IDENTIFIER ::= { ciscoExtScsiMIB 1 }
ciscoExtScsiMIBConformance OBJECT IDENTIFIER 
                           ::= { ciscoExtScsiMIB 2 }
ciscoExtScsiConfiguration  OBJECT IDENTIFIER 
                           ::= { ciscoExtScsiMIBObjects 1 }
ciscoExtScsiNotification   OBJECT IDENTIFIER
                           ::= { ciscoExtScsiMIBObjects 2 }
ciscoExtScsiNotifications  OBJECT IDENTIFIER
                           ::= { ciscoExtScsiNotification 0 }

-- Extensions to the ciscoScsiGenInstanceTable
--
 
ciscoExtScsiGenInstanceTable OBJECT-TYPE
        SYNTAX         SEQUENCE OF CiscoExtScsiGenInstanceEntry
        MAX-ACCESS     not-accessible
        STATUS         current
        DESCRIPTION
                "This table is an extension to the 
                 ciscoScsiInstanceTable defined in
                 the CISCO-SCSI-MIB.

                 The ciscoScsiInstIndex values are 
                 populated as follows:

                 - there is one ciscoScsiInstIndex value
                   defined per disk group associated with the 
                   system.

                 - there is one ciscoScsiInstIndex value
                   defined per line-card.

                 - there is one ciscoScsiInstIndex value
                   defined for the supervisor as a whole.

                 All ciscoScsiInstIndex values defined
                 for disk groups will have a disk group
                 id associated with them, which is that
                 of the corresponding disk group. This
                 value is present in the corresponding
                 instance of ciscoExtScsiDiskGrpId object.
                 The corresponding instance of
                 ciscoExtScsiLineCardOrSup object will
                 contain the entity physical index of
                 the line card to which it is associated.

                 For ciscoScsiInstIndex values defined
                 for a line card, the ciscoExtScsiDiskGrpId
                 object is not meaningful and will be
                 empty. The corresponding instance of
                 ciscoExtScsiLineCardOrSup object will
                 contain the entity physical index value
                 of that line card.

                 For the ciscoScsiInstIndex value defined 
                 for the supervisor, the ciscoExtScsiDiskGrpId
                 object is not meaningful and will be empty.
                 The corresponding instance of 
                 ciscoExtScsiLineCardOrSup object will
                 contain the entity physical index value
                 of the supervisor."
        ::= { ciscoExtScsiConfiguration 1 }

ciscoExtScsiGenInstanceEntry OBJECT-TYPE
        SYNTAX         CiscoExtScsiGenInstanceEntry
        MAX-ACCESS     not-accessible
        STATUS         current
        DESCRIPTION
                "An entry (conceptual row) in this table."
        AUGMENTS { ciscoScsiInstanceEntry }
        ::= { ciscoExtScsiGenInstanceTable 1 }

CiscoExtScsiGenInstanceEntry ::= SEQUENCE {
        ciscoExtScsiDiskGrpId              OCTET STRING,
        ciscoExtScsiLineCardOrSup          Unsigned32 

}

ciscoExtScsiDiskGrpId OBJECT-TYPE
        SYNTAX          OCTET STRING ( SIZE(0 | 64))
        MAX-ACCESS      read-only
        STATUS          current
        DESCRIPTION
                "This object contains the disk group
                 id of a disk group if the
                 value of the ciscoScsiInstIndex
                 corresponds to that of a disk
                 group. Otherwise, this object will
                 contain a null string."
        ::= {ciscoExtScsiGenInstanceEntry 1}

ciscoExtScsiLineCardOrSup OBJECT-TYPE
        SYNTAX          Unsigned32 (1..2147483647)
        MAX-ACCESS      read-only
        STATUS          current
        DESCRIPTION
                "This object contains the entity
                 physical index of a line card
                 if the ciscoScsiInstIndex value
                 corresponds to that of a disk
                 group or a line card. 

                 Otherwise, this object contains the
                 entity physical index value of the
                 supervisor of the system."
        ::= { ciscoExtScsiGenInstanceEntry 2 }


ciscoExtScsiLunDiscSpinLock OBJECT-TYPE
        SYNTAX           TestAndIncr
        MAX-ACCESS       read-write
        STATUS           current
        DESCRIPTION
                "This object is used to facilitate triggerring 
                 the LUN discovery by multiple managers. 

                 The procedure for triggering LUN discovery is
                 as follows:

                 1. Retrieve the value of 
                    ciscoExtScsiLunDiscSpinLock and determine the
                    value for ciscoExtScsiStartLunDisc object.

                 2. Set the value of ciscoExtScsiLunDiscSpinLock
                    to the retrieved value, and in the same PDU, 
                    the value of ciscoExtScsiStartLunDisc 
                    to the determined value. If the set fails for 
                    the ciscoExtScsiLunDiscSpinLock object, go back 
                    to step 1."
        ::= { ciscoExtScsiConfiguration 2 }


ciscoExtScsiStartLunDisc OBJECT-TYPE
        SYNTAX           INTEGER {
                            startDiscovery(1),
                            startLocalDiscovery(2),
                            startRemoteDiscovery(3),
                            noop(4)
                         }
        MAX-ACCESS       read-write
        STATUS           current
        DESCRIPTION
                "If this object is set to 'startLocalDiscovery',
                 then only the directly attached scsi target
                 devices/ports and LUNs associated with them on
                 all VSANs will be discovered.

                 If this object is set to 'startRemoteDiscovery',
                 then all scsi target devices/ports and LUNs
                 associated with them on all VSANs in the whole
                 fabric, except the directly attached ones, will
                 be discovered.

                 If this object is set to 'startDiscovery', then
                 both the above discoveries will be carried out.

                 No action is taken if this object is set
                 to 'noop'.

                 The value of this object when read is 
                 always 'noop'.

                 After a discovery has been triggered, this
                 object cannot be set again to trigger
                 another discovery, when the value of 
                 ciscoExtScsiLunDiscStatus is 'inProgress'."
        ::= { ciscoExtScsiConfiguration 3 }

ciscoExtScsiLunDiscStatus OBJECT-TYPE
        SYNTAX           INTEGER {
                            inProgress(1),
                            completed(2),
                            failure(3)
                         }
        MAX-ACCESS       read-only
        STATUS           current
        DESCRIPTION
                "This object indicates the outcome of the
                 LUN discovery on the local switch.

                 This object contains the status of the most
                 recent discovery.

                 inProgress(1) - indicates that the discovery is 
                                 still in progress.
                 completed(2)  - indicates that the discovery is
                                 complete.
                 failure(3)    - indicates that the discovery
                                 encountered a failure."
        ::= { ciscoExtScsiConfiguration 4 }

ciscoExtScsiLunDiscCompleteTime OBJECT-TYPE
        SYNTAX           TimeStamp
        MAX-ACCESS       read-only
        STATUS           current
        DESCRIPTION
                "This object contains the value of sysUpTime
                 when the last discovery was completed.
                 The value of this object will be zero, if
                 discovery has not been performed since the
                 last system restart."
        ::= { ciscoExtScsiConfiguration 5 }



ciscoExtScsiIntrDiscTgtTable OBJECT-TYPE
        SYNTAX           SEQUENCE OF CiscoExtScsiIntrDiscTgtEntry
        MAX-ACCESS       not-accessible
        STATUS           current
        DESCRIPTION
                "This table is an extension to the
                 ciscoScsiDscTgtTable."
        ::= { ciscoExtScsiConfiguration 6 }

ciscoExtScsiIntrDiscTgtEntry OBJECT-TYPE
        SYNTAX           CiscoExtScsiIntrDiscTgtEntry
        MAX-ACCESS       not-accessible
        STATUS           current
        DESCRIPTION
                "An entry (conceptual row) in this table."
        AUGMENTS { ciscoScsiDscTgtEntry }
        ::= { ciscoExtScsiIntrDiscTgtTable 1 }

CiscoExtScsiIntrDiscTgtEntry ::= SEQUENCE {
        ciscoExtScsiIntrDiscTgtVsanId      VsanIndex,
        ciscoExtScsiIntrDiscTgtDevType     Unsigned32,
        ciscoExtScsiIntrDiscTgtVendorId    OCTET STRING,
        ciscoExtScsiIntrDiscTgtProductId   OCTET STRING,
        ciscoExtScsiIntrDiscTgtRevLevel    OCTET STRING,
        ciscoExtScsiIntrDiscTgtOtherInfo   OCTET STRING
        
}

ciscoExtScsiIntrDiscTgtVsanId OBJECT-TYPE
        SYNTAX           VsanIndex
        MAX-ACCESS       read-only
        STATUS           current
        DESCRIPTION
                "The VSAN to which this target belongs to."
        ::= { ciscoExtScsiIntrDiscTgtEntry 1 }

ciscoExtScsiIntrDiscTgtDevType OBJECT-TYPE
        SYNTAX           Unsigned32
        MAX-ACCESS       read-only
        STATUS           current
        DESCRIPTION
                "The device type of the SCSI target."
        REFERENCE  "Section 7.3.2 Standard INQUIRY Data.   
                    SCSI Primary Commands- 2 (SPC-2)"        
        ::= { ciscoExtScsiIntrDiscTgtEntry 2 }

ciscoExtScsiIntrDiscTgtVendorId OBJECT-TYPE
        SYNTAX      OCTET STRING (SIZE (8))
        MAX-ACCESS  read-only
        STATUS      current
        DESCRIPTION
                "The vendor Id of the SCSI target."
        REFERENCE   "Section 7.3.2 Standard INQUIRY Data.   
                     SCSI Primary Commands- 2 (SPC-2)"        
        ::= { ciscoExtScsiIntrDiscTgtEntry 3 }

ciscoExtScsiIntrDiscTgtProductId OBJECT-TYPE
        SYNTAX      OCTET STRING (SIZE (16))
        MAX-ACCESS  read-only
        STATUS      current
        DESCRIPTION
                "The product Id of the SCSI target."
        REFERENCE   "Section 7.3.2 Standard INQUIRY Data.   
                     SCSI Primary Commands- 2 (SPC-2)" 
        ::= { ciscoExtScsiIntrDiscTgtEntry 4 }

ciscoExtScsiIntrDiscTgtRevLevel OBJECT-TYPE
        SYNTAX      OCTET STRING (SIZE (4))
        MAX-ACCESS  read-only
        STATUS      current
        DESCRIPTION
                "The product revision level of the SCSI target."
        REFERENCE   "Section 7.3.2 Standard INQUIRY Data.   
                     SCSI Primary Commands- 2 (SPC-2)" 
        ::= { ciscoExtScsiIntrDiscTgtEntry 5 }

ciscoExtScsiIntrDiscTgtOtherInfo OBJECT-TYPE
        SYNTAX      OCTET STRING (SIZE (8))
        MAX-ACCESS  read-only
        STATUS      current
        DESCRIPTION
                "The bytes from 0 to 7 in the INQUIRY command 
                 response data."
        REFERENCE   "Section 7.3.2 Standard INQUIRY Data.   
                     SCSI Primary Commands- 2 (SPC-2)" 
        ::= { ciscoExtScsiIntrDiscTgtEntry 6 }



ciscoExtScsiIntrDiscLunsTable OBJECT-TYPE
        SYNTAX           SEQUENCE OF CiscoExtScsiIntrDiscLunsEntry
        MAX-ACCESS       not-accessible
        STATUS           current
        DESCRIPTION
                "This table is an extension to the
                 ciscoScsiDscLunTable."
        ::= { ciscoExtScsiConfiguration 7 }

ciscoExtScsiIntrDiscLunsEntry OBJECT-TYPE
        SYNTAX           CiscoExtScsiIntrDiscLunsEntry
        MAX-ACCESS       not-accessible
        STATUS           current
        DESCRIPTION
                "An entry (conceptual row) in this table."
        AUGMENTS { ciscoScsiDscLunEntry }
        ::= { ciscoExtScsiIntrDiscLunsTable 1 }

CiscoExtScsiIntrDiscLunsEntry ::= SEQUENCE {
        ciscoExtScsiIntrDiscLunCapacity    Unsigned32,
        ciscoExtScsiIntrDiscLunNumber      OCTET STRING,
        ciscoExtScsiIntrDiscLunSerialNum   OCTET STRING
}

ciscoExtScsiIntrDiscLunCapacity OBJECT-TYPE
        SYNTAX            Unsigned32
        UNITS             "MBytes"
        MAX-ACCESS        read-only
        STATUS            current
        DESCRIPTION
                "The capacity of this Lun."
        ::={ ciscoExtScsiIntrDiscLunsEntry 1 }

ciscoExtScsiIntrDiscLunNumber OBJECT-TYPE
        SYNTAX            OCTET STRING (SIZE (8))
        MAX-ACCESS        read-only
        STATUS            current
        DESCRIPTION
                "The number of this LUN."
        REFERENCE   "Section 4.8 (Logical Units) and Section 3.1.63 
                     in SCSI Architecture Model-2 (SAM-2)."
        ::= { ciscoExtScsiIntrDiscLunsEntry 2 }

ciscoExtScsiIntrDiscLunSerialNum OBJECT-TYPE
        SYNTAX            OCTET STRING (SIZE (0..32))
        MAX-ACCESS        read-only
        STATUS            current
        DESCRIPTION
                "The serial number of this LUN."
        REFERENCE   "Section 8.4.6 (Unit Serial Number Page)
                     in SCSI Primary Commands-2 (SPC-2)."
        ::= { ciscoExtScsiIntrDiscLunsEntry 3 }

-- Notification control object

ciscoExtScsiNotificationCntl OBJECT-TYPE
        SYNTAX            TruthValue
        MAX-ACCESS        read-write
        STATUS            current
        DESCRIPTION
                "This object specifies if the 
                 'ciscoExtScsiLunDiscDoneNotify' notification
                 should be generated or not.

                 If the value of this object is 'true', then
                 the notification is generated when a 
                 discovery is completed.

                 If the value of this object is 'false', then
                 the notification is not generated."
        DEFVAL { false }
        ::= { ciscoExtScsiConfiguration 8 }

-- Notification

ciscoExtScsiLunDiscDoneNotify NOTIFICATION-TYPE
        OBJECTS {ciscoExtScsiLunDiscStatus}
        STATUS  current
        DESCRIPTION
                "This notification is generated whenever a 
                 Lun discovery cycle is completed."
        ::= { ciscoExtScsiNotifications 1 }


ciscoExtScsiMIBCompliances OBJECT IDENTIFIER 
                         ::= { ciscoExtScsiMIBConformance 1 }
ciscoExtScsiMIBGroups      OBJECT IDENTIFIER 
                         ::= { ciscoExtScsiMIBConformance 2 }

ciscoExtScsiMIBCompliance MODULE-COMPLIANCE
        STATUS   current
        DESCRIPTION
                "The compliance statement for entities that
                 implement the Cisco extension to the
                 CISCO-SCSI-MIB."
        MODULE  MANDATORY-GROUPS {ciscoExtScsiConfigGroup,
                                  ciscoExtScsiNotifyControlGroup,
                                  ciscoExtScsiNotifyGroup}

        ::= { ciscoExtScsiMIBCompliances 1 }

-- Units of conformance
ciscoExtScsiConfigGroup OBJECT-GROUP
        OBJECTS  {ciscoExtScsiDiskGrpId,
                  ciscoExtScsiLineCardOrSup,
                  ciscoExtScsiLunDiscSpinLock,
                  ciscoExtScsiStartLunDisc,
                  ciscoExtScsiLunDiscStatus,
                  ciscoExtScsiLunDiscCompleteTime,
                  ciscoExtScsiIntrDiscTgtVsanId,
                  ciscoExtScsiIntrDiscTgtDevType,
                  ciscoExtScsiIntrDiscTgtVendorId,
                  ciscoExtScsiIntrDiscTgtProductId,
                  ciscoExtScsiIntrDiscTgtRevLevel,
                  ciscoExtScsiIntrDiscTgtOtherInfo,
                  ciscoExtScsiIntrDiscLunCapacity,
                  ciscoExtScsiIntrDiscLunNumber,
                  ciscoExtScsiIntrDiscLunSerialNum}
        STATUS   current
        DESCRIPTION
                "A collection of objects for displaying and
                 configuring Cisco extension MIB objects to 
                 the CISCO-SCSI-MIB."
        ::= { ciscoExtScsiMIBGroups 1 }

ciscoExtScsiNotifyControlGroup OBJECT-GROUP
        OBJECTS  {ciscoExtScsiNotificationCntl}
        STATUS   current
        DESCRIPTION
                "A collection of notification control object(s)
                 for controlling notification generation."
        ::= { ciscoExtScsiMIBGroups 2 }

ciscoExtScsiNotifyGroup NOTIFICATION-GROUP
        NOTIFICATIONS  {ciscoExtScsiLunDiscDoneNotify}
        STATUS   current
        DESCRIPTION
                "A collection of notification(s) for monitoring
                 Lun discovery status."
        ::= { ciscoExtScsiMIBGroups 3 }

END
