-- *****************************************************************
-- CISCO-ENHANCED-IMAGE-MIB.my
--
-- September 2001, Narayana Pai H.
--
-- Copyright (c) 2001-2002 by cisco Systems, Inc.
-- All rights reserved.
--
-- *****************************************************************

CISCO-ENHANCED-IMAGE-MIB DEFINITIONS ::= BEGIN

IMPORTS
        MODULE-IDENTITY,
        OBJECT-TYPE
                FROM SNMPv2-SMI
        SnmpAdminString
                FROM SNMP-FRAMEWORK-MIB
        TEXTUAL-CONVENTION
                FROM SNMPv2-TC
        MODULE-COMPLIANCE,
        OBJECT-GROUP
                FROM SNMPv2-CONF
        ciscoMgmt
                FROM CISCO-SMI
        PhysicalIndex
                FROM ENTITY-MIB;

ciscoEnhancedImageMIB   MODULE-IDENTITY
        LAST-UPDATED    "200202280000Z"
        ORGANIZATION    "Cisco Systems, Inc."
        CONTACT-INFO
                        "Cisco Systems
                        Customer Service

                        Postal: 170 W Tasman Drive
                        San Jose, CA  95134
                        USA

                        Tel: +1 800 553-NETS

                        E-mail: cs-core-mibs@cisco.com"
        DESCRIPTION
                "Initial version of the MIB. This MIB has Image table
                 containing the following information related to the 
                 running IOS image
                 1. Entity Index
                 2. The image name
                 3. Family
                 4. Feature set
                 5. Version
                 6. Media and
                 7. Description
                 This MIB deprecates the objects in the CISCO-IMAGE-MIB."
        ::= { ciscoMgmt 249 }

ciscoEnhancedImageMIBObjects OBJECT IDENTIFIER 
        ::= { ciscoEnhancedImageMIB 1 }

ceImage OBJECT IDENTIFIER
        ::= { ciscoEnhancedImageMIBObjects 1 }

-- Textual Convention

MediaType ::= TEXTUAL-CONVENTION
        STATUS        current
        DESCRIPTION     
                 "This TC describes the media type on which the
                 IOS image is loaded and is running from.

                 This is not the secondary storage device from
                 which the image is loaded. The storage device
                 from which the image is loaded is part of the
                 image name (ceImageName)."
        SYNTAX        INTEGER {
                          ram (1),  -- The image is in RAM
                          rom (2),  -- The image is in ROM
                          other (3) -- The image is in unknown media
                      }


-- Image Table

ceImageTable OBJECT-TYPE
        SYNTAX        SEQUENCE OF CeImageEntry
        MAX-ACCESS    not-accessible
        STATUS        current
        DESCRIPTION
                "A table provides content information describing 
                the executing IOS image."
        ::= { ceImage 1 }

ceImageEntry OBJECT-TYPE
        SYNTAX        CeImageEntry
        MAX-ACCESS    not-accessible
        STATUS        current
        DESCRIPTION
                "An image characteristic entry."
        INDEX         { ceImageIndex }
        ::= { ceImageTable 1 }


CeImageEntry ::=
        SEQUENCE {
                ceImageIndex        PhysicalIndex,      
                ceImageName         SnmpAdminString,
                ceImageFamily       SnmpAdminString,
                ceImageFeature      SnmpAdminString,
                ceImageVersion      SnmpAdminString,
                ceImageMedia        MediaType,
                ceImageDescription  SnmpAdminString
        }

ceImageIndex          OBJECT-TYPE
        SYNTAX        PhysicalIndex 
        MAX-ACCESS    not-accessible
        STATUS        current
        DESCRIPTION
                "The entPhysicalIndex from the ENTITY-MIB of 
                the physical entity that runs this IOS image."
        ::= { ceImageEntry 1 }

ceImageName OBJECT-TYPE
        SYNTAX        SnmpAdminString 
        MAX-ACCESS    read-only
        STATUS        current
        DESCRIPTION
                "Name of the running IOS image. This will also
                include the path from where the image is loaded.
                For example, flash:c3640-is-mz."
        ::= { ceImageEntry 2 }

ceImageFamily OBJECT-TYPE
        SYNTAX        SnmpAdminString 
        MAX-ACCESS    read-only
        STATUS        current
        DESCRIPTION
                "Family of the running IOS image.The image family 
                indicates the platform for which the image is built.
                Examples of image families - 
                are C3640, C7200 etc."
        ::= { ceImageEntry 3 }

ceImageFeature OBJECT-TYPE
        SYNTAX        SnmpAdminString 
        MAX-ACCESS    read-only
        STATUS        current
        DESCRIPTION
                "Feature set supported on this image. Examples of 
                feature set are - 
                ENTERPRISE, PROVIDER etc."
        ::= { ceImageEntry 4 }

ceImageVersion OBJECT-TYPE
        SYNTAX        SnmpAdminString 
        MAX-ACCESS    read-only
        STATUS        current
        DESCRIPTION
                "Version of the running IOS image."
        ::= { ceImageEntry 5 }

ceImageMedia OBJECT-TYPE
        SYNTAX        MediaType 
        MAX-ACCESS    read-only
        STATUS        current
        DESCRIPTION
                "Media on which the image represented by this
                entry is running."
        ::= { ceImageEntry 6 }

ceImageDescription OBJECT-TYPE
        SYNTAX        SnmpAdminString 
        MAX-ACCESS    read-only
        STATUS        current
        DESCRIPTION
                "Description of running IOS image."
        ::= { ceImageEntry 7 }

--
-- Conformance
--

ciscoEnhancedImageMIBConformance OBJECT IDENTIFIER 
        ::= { ciscoEnhancedImageMIB 3 }

ciscoEnhancedImageMIBCompliances OBJECT IDENTIFIER 
        ::= { ciscoEnhancedImageMIBConformance 1 }

ciscoEnhancedImageMIBGroups      OBJECT IDENTIFIER 
        ::= { ciscoEnhancedImageMIBConformance 2 }

--
-- Compliance
--

ciscoEnhancedImageMIBCompliance  MODULE-COMPLIANCE
        STATUS        current
        DESCRIPTION
                "The compliance statement for entities which implement
                the CISCO-ENHANCED-IMAGE-MIB."
        MODULE  -- this module
        MANDATORY-GROUPS { ciscoEnhancedImageMIBGroup }
        ::= { ciscoEnhancedImageMIBCompliances 1 }

--
-- Units of Conformance
--

ciscoEnhancedImageMIBGroup       OBJECT-GROUP
        OBJECTS {
                ceImageName,
                ceImageFamily,
                ceImageFeature,
                ceImageVersion,
                ceImageMedia,
                ceImageDescription
        }
        STATUS        current
        DESCRIPTION
                "A collection of objects providing IOS image 
                characteristics."
        ::= { ciscoEnhancedImageMIBGroups 1 }

END
