-- *------------------------------------------------------------------
-- * ALTIGA-ADDRESS-STATS-MIB.my:  The Altiga Address Statistics MIB.
-- *
-- * Altiga Networks was acquired by Cisco Systems on March 29, 2000
-- *
-- * Copyright (c) 2002 by Cisco Systems, Inc.
-- * All rights reserved.
-- *
-- *------------------------------------------------------------------

ALTIGA-ADDRESS-STATS-MIB DEFINITIONS ::= BEGIN

   IMPORTS
      MODULE-IDENTITY, OBJECT-TYPE, Integer32, Gauge32
         FROM SNMPv2-SMI
      OBJECT-GROUP, MODULE-COMPLIANCE
         FROM SNMPv2-CONF
      alStatsAddress, alAddressGroup
         FROM ALTIGA-MIB
      alAddressMibModule
         FROM ALTIGA-GLOBAL-REG;

   altigaAddressStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga Address Statistics MIB models counters and objects that are
          of management interest for address assignment.
         
          Acronyms
          The following acronyms are used in this document:

            MIB:        Management Information Base

         "

        REVISION "200209051300Z"
        DESCRIPTION
                "Added module compliance."

        REVISION "200207100000Z"
        DESCRIPTION
                "Updated with new header"

      ::= { alAddressMibModule 2 }

-- +++++++++++++++++++++++++++++++++++++++++++++++++++++++
-- MIB Objects
-- +++++++++++++++++++++++++++++++++++++++++++++++++++++++

alAddressStatsGlobal OBJECT IDENTIFIER ::= { alStatsAddress 1 }

alAddressStatsPoolTable         OBJECT-TYPE
   SYNTAX         SEQUENCE OF AlAddressStatsPoolEntry
   MAX-ACCESS     not-accessible
   STATUS         current
   DESCRIPTION
          "The list of trap destinations."
   ::= { alStatsAddress 2}

alAddressStatsPoolEntry         OBJECT-TYPE
   SYNTAX         AlAddressStatsPoolEntry
   MAX-ACCESS     not-accessible
   STATUS         current
   DESCRIPTION
          "An entry in the alAddressStatsPoolTable."
   INDEX        { alAddressStatsPoolId }
   ::= { alAddressStatsPoolTable 1 }

AlAddressStatsPoolEntry ::= SEQUENCE {
        alAddressStatsPoolId               Integer32,
        alAddressStatsTotalPoolAddresses   Integer32,
        alAddressStatsCurrAllocAddresses   Gauge32,
        alAddressStatsCurrAvailAddresses   Gauge32,
        alAddressStatsMaxAddressesAssigned Gauge32
}

alAddressStatsPoolId             OBJECT-TYPE
   SYNTAX                 Integer32 (0..65535)
   MAX-ACCESS             read-only
   STATUS                 current 
   DESCRIPTION
      "The Global Address Pool ID for this entry."
   ::= { alAddressStatsPoolEntry 1 }

alAddressStatsTotalPoolAddresses OBJECT-TYPE
   SYNTAX                 Integer32 (0..65535)
   MAX-ACCESS             read-only
   STATUS                 current 
   DESCRIPTION
          "Total number of legal addresses defined in pool.
           This does not include Network and Broadcast addresses."
   ::= { alAddressStatsPoolEntry 2 }

alAddressStatsCurrAllocAddresses OBJECT-TYPE
   SYNTAX                 Gauge32
   MAX-ACCESS             read-only
   STATUS                 current 
   DESCRIPTION
          "Total number of addresses currently assigned"
   ::= { alAddressStatsPoolEntry 3 }

alAddressStatsCurrAvailAddresses OBJECT-TYPE
   SYNTAX                 Gauge32
   MAX-ACCESS             read-only
   STATUS                 current 
   DESCRIPTION
          "Total number of addresses currently available"
   ::= { alAddressStatsPoolEntry 4 }

alAddressStatsMaxAddressesAssigned  OBJECT-TYPE
   SYNTAX                 Gauge32
   MAX-ACCESS             read-only
   STATUS                 current 
   DESCRIPTION
          "Total number of addresses currently available"
   ::= { alAddressStatsPoolEntry 5 }

alAddressStatsPoolGroupTable  OBJECT-TYPE
   SYNTAX         SEQUENCE OF AlAddressStatsPoolGroupEntry
   MAX-ACCESS     not-accessible
   STATUS         current
   DESCRIPTION
          "The list of trap destinations."
   ::= { alStatsAddress 3}

alAddressStatsPoolGroupEntry  OBJECT-TYPE
   SYNTAX         AlAddressStatsPoolGroupEntry
   MAX-ACCESS     not-accessible
   STATUS         current
   DESCRIPTION
          "An entry in the alAddressPoolTable."
   INDEX        { alAddressStatsGrpId, alAddressStatsGrpPoolId }
   ::= { alAddressStatsPoolGroupTable 1 }

AlAddressStatsPoolGroupEntry ::= SEQUENCE {
        alAddressStatsGrpId                   Integer32,
        alAddressStatsGrpPoolId               Integer32,
        alAddressStatsGrpTotalPoolAddresses   Integer32,
        alAddressStatsGrpCurrAllocAddresses   Gauge32,
        alAddressStatsGrpCurrAvailAddresses   Gauge32,
        alAddressStatsGrpMaxAddressesAssigned Gauge32
}

alAddressStatsGrpId                  OBJECT-TYPE
   SYNTAX                 Integer32 (0..65535)
   MAX-ACCESS             read-only
   STATUS                 current 
   DESCRIPTION
      "The Group ID for this entry."
   ::= { alAddressStatsPoolGroupEntry 1 }

alAddressStatsGrpPoolId                 OBJECT-TYPE
   SYNTAX                 Integer32 (0..65535)
   MAX-ACCESS             read-only
   STATUS                 current 
   DESCRIPTION
      "The Group Pool ID for this entry."
   ::= { alAddressStatsPoolGroupEntry 2 }

alAddressStatsGrpTotalPoolAddresses OBJECT-TYPE
   SYNTAX                 Integer32 (0..65535)
   MAX-ACCESS             read-only
   STATUS                 current 
   DESCRIPTION
          "Total number of legal addresses defined in pool.
           This does not include Network and Broadcast addresses."
   ::= { alAddressStatsPoolGroupEntry 3 }

alAddressStatsGrpCurrAllocAddresses OBJECT-TYPE
   SYNTAX                 Gauge32
   MAX-ACCESS             read-only
   STATUS                 current 
   DESCRIPTION
          "Total number of addresses currently assigned"
   ::= { alAddressStatsPoolGroupEntry 4 }

alAddressStatsGrpCurrAvailAddresses OBJECT-TYPE
   SYNTAX                 Gauge32
   MAX-ACCESS             read-only
   STATUS                 current 
   DESCRIPTION
          "Total number of addresses currently available"
   ::= { alAddressStatsPoolGroupEntry 5 }

alAddressStatsGrpMaxAddressesAssigned  OBJECT-TYPE
   SYNTAX                 Gauge32
   MAX-ACCESS             read-only
   STATUS                 current 
   DESCRIPTION
          "Total number of addresses currently available"
   ::= { alAddressStatsPoolGroupEntry 6 }

altigaAddressStatsMibConformance OBJECT IDENTIFIER ::= { altigaAddressStatsMibModule 1 }
altigaAddressStatsMibCompliances OBJECT IDENTIFIER ::= { altigaAddressStatsMibConformance 1 }

altigaAddressStatsMibCompliance MODULE-COMPLIANCE
   STATUS         current
   DESCRIPTION
      "The compliance statement for agents which 
       implement the Altiga Address Statistics MIB."
   MODULE
   MANDATORY-GROUPS { 
      altigaAddressStatsGroup
   }
   ::= { altigaAddressStatsMibCompliances 1 }

altigaAddressStatsGroup OBJECT-GROUP
   OBJECTS
   {
      alAddressStatsPoolId,
      alAddressStatsTotalPoolAddresses,
      alAddressStatsCurrAllocAddresses,
      alAddressStatsCurrAvailAddresses,
      alAddressStatsMaxAddressesAssigned,
      alAddressStatsGrpId,
      alAddressStatsGrpPoolId,
      alAddressStatsGrpTotalPoolAddresses,
      alAddressStatsGrpCurrAllocAddresses,
      alAddressStatsGrpCurrAvailAddresses,
      alAddressStatsGrpMaxAddressesAssigned
   }
   STATUS   current
   DESCRIPTION
          "The objects for address statistics."
   ::= { alAddressGroup 2 }

END
