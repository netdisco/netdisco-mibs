-- *****************************************************************
-- CISCO Network Registrar MIB
--
-- Copyright (c) 1998-2003, by Cisco Systems, Inc.
-- All rights reserved.
-- *****************************************************************

-- This MIB allows admins to receive updates (via traps) on
-- the status of Cisco Network Registrar (CNR.)  CNR is a
-- DNS/DHCP solution that provides scalable naming and addressing
-- services, and IP address management for enterprise networks.
-- Please note that SNMP traps may be sent via an unreliable
-- network protocol, and so should not be relied on as the only
-- means to determine the operating status of CNR.

-- Establishing trap recipients, enabling and disabling
-- traps, and setting of trap thresholds can be done via the
-- CNR command-line interface, "nrcmd".  Please see the Network
-- Registrar Command Line User Guide for more information.


CISCO-NETWORK-REGISTRAR-MIB DEFINITIONS ::= BEGIN

IMPORTS
    MODULE-IDENTITY,
    OBJECT-TYPE,
    NOTIFICATION-TYPE,
    IpAddress, Unsigned32
        FROM SNMPv2-SMI
    MODULE-COMPLIANCE, OBJECT-GROUP, NOTIFICATION-GROUP 
        FROM SNMPv2-CONF
    TEXTUAL-CONVENTION, DisplayString, TruthValue 
        FROM SNMPv2-TC
    ciscoMgmt
        FROM CISCO-SMI;

ciscoNetworkRegistrarMIB MODULE-IDENTITY
    LAST-UPDATED        "200301110000Z"
    ORGANIZATION        "Cisco Systems, Inc."
    CONTACT-INFO
        "Cisco Systems
         Customer Service
             Postal: 170 W Tasman Drive
                     San Jose, CA  95134
                     USA

             Tel: +1 800 553-NETS

             E-mail: cs-cnr-snmp@cisco.com"
    DESCRIPTION
        "MIB for Cisco Network Registrar (CNR)"
    REVISION        "200301110000Z"
    DESCRIPTION
        "Added configuration objects to enable
         or disable notifications."
    REVISION        "9906170000Z"
    DESCRIPTION
        "Fixed OID for ciscoNetworkRegistrarMIBConformance"
    REVISION        "9811010000Z"
    DESCRIPTION
        "Initial version of this MIB module."
   ::= { ciscoMgmt 120 }


ciscoNetworkRegistrarMIBObjects OBJECT IDENTIFIER
    ::= { ciscoNetworkRegistrarMIB 1 }

cnrDHCP OBJECT IDENTIFIER
    ::= { ciscoNetworkRegistrarMIBObjects 1}

cnrNotifObjects OBJECT IDENTIFIER
    ::= { ciscoNetworkRegistrarMIBObjects 2 }

cnrNotifCfgObjects OBJECT IDENTIFIER
    ::= { ciscoNetworkRegistrarMIBObjects 3 }

--  cnrDHCPScopeTable:  Table of DHCP scopes
--  A Scope is a set of one or more address ranges used by
--  DHCP for handing out dynamic addresses.  A policy may
--  be associated with a scope.  See the Network Registrar
--  User's Guide for more information.

--  Objects in this table (or one like it) may become
--  readable in a later release of the MIB.

cnrDHCPScopeTable OBJECT-TYPE
    SYNTAX     SEQUENCE OF CnrDHCPScopeEntry
    MAX-ACCESS not-accessible
    STATUS     current
    DESCRIPTION
        "The table listing characteristics of all scopes.
        Entries in this table correspond to scopes, which are
        added and deleted via the CNR GUI or CLI."
    ::= { cnrDHCP 1 }

cnrDHCPScopeEntry OBJECT-TYPE
    SYNTAX     CnrDHCPScopeEntry
    MAX-ACCESS not-accessible
    STATUS     current
    DESCRIPTION
        "An entry in the cnrDHCPScopeTable."
        INDEX { cnrDHCPScopeName }
    ::= { cnrDHCPScopeTable 1 }

CnrDHCPScopeEntry ::= SEQUENCE 
{
    cnrDHCPScopeName                  DisplayString,
    cnrDHCPScopeFreeAddrLowThreshold  Unsigned32,
    cnrDHCPScopeFreeAddrHighThreshold Unsigned32,
    cnrDHCPScopeFreeAddrValue         Unsigned32,
    cnrDHCPScopeFreeAddrUnits         INTEGER
}

cnrDHCPScopeName OBJECT-TYPE
    SYNTAX     DisplayString(SIZE (1..100))
    MAX-ACCESS not-accessible
    STATUS      current
    DESCRIPTION
        "The name of the scope, which uniquely identifies
        an entry in the cnrDHCPScopeTable."
    ::= { cnrDHCPScopeEntry 1 }

cnrDHCPScopeFreeAddrLowThreshold OBJECT-TYPE
    SYNTAX     Unsigned32
    MAX-ACCESS accessible-for-notify
    STATUS     current
    DESCRIPTION
        "The low threshold for available free addresses in
        this scope.  If the value for available free addresses
        in this scope becomes equal to or less than this value,
        a cnrDHCPScopeFreeAddrLowThreshold event is generated 
        for this scope.  No more cnrDHCPScopeFreeAddrLowThreshold
        events will be generated for this scope during this
        execution of the DHCP server until the value for available
        free addresses has exceeded the value of
        cnrDHCPScopeFreeAddrHighThreshold.

        This value may be expressed as either an absolute value
        or a percentage; the units are specified by the value of
        cnrDHCPScopeFreeAddrUnits."
    ::= { cnrDHCPScopeEntry 2 }

cnrDHCPScopeFreeAddrHighThreshold 
OBJECT-TYPE
    SYNTAX     Unsigned32
    MAX-ACCESS accessible-for-notify
    STATUS     current
    DESCRIPTION
        "The high threshold for available free addresses in this
        scope.  If a cnrDHCPScopeFreeAddrLowThreshold event has
        been generated for this scope, and the value for available
        free addresses has exceeded the value of 
        cnrDHCPScopeFreeAddrHighThreshold, then a
        ciscoNetRegFreeAddressHigh event will be generated. No
        more ciscoNetRegFreeAddressHigh events will be generated
        for this scope during this execution of the DHCP server
        until the value for available free addresses becomes equal
        to or less than the value of 
        cnrDHCPScopeFreeAddrHighThreshold.

        This value may be expressed as either an absolute value
        or a percentage; the units are specified by the value of
        cnrDHCPScopeFreeAddrUnits."
     ::= { cnrDHCPScopeEntry 3 }

cnrDHCPScopeFreeAddrValue OBJECT-TYPE
    SYNTAX     Unsigned32
    MAX-ACCESS accessible-for-notify
    STATUS     current
    DESCRIPTION
        "The number of IP addresses which are available
        within this scope.  May be expressed as either
        an absolute value or a percentage; the units are
        given by the value of cnrDHCPScopeFreeAddrUnits."
    ::= { cnrDHCPScopeEntry 4 }

cnrDHCPScopeFreeAddrUnits OBJECT-TYPE
    SYNTAX     INTEGER { value(1), percent(2) }
    MAX-ACCESS accessible-for-notify
    STATUS     current
    DESCRIPTION
        "The units associated with the value of 
        cnrDHCPScopeFreeAddrValue."
    ::= { cnrDHCPScopeEntry 5 }


-- cnrNotifObjects: Objects which are used only in notifications

cnrNotifDupIpAddress OBJECT-TYPE
    SYNTAX IpAddress
    MAX-ACCESS accessible-for-notify
    STATUS current
    DESCRIPTION
        "The IP address which was found to be a duplicate."
    ::= { cnrNotifObjects 1 }


CnrPhysAddress ::= TEXTUAL-CONVENTION
    STATUS        current
    DESCRIPTION
        "A Layer 1 address which includes the hardware address
         space as well as the usual MAC address. This object is
         encoded in ASCII as
             <type>,<length>,<address>
         where
             <type> is the value of the hardware address space
             field, as used in ARP (i.e, 1 for Ethernet,
             6 for token ring...)  IANA has a list of
             registered numbers for this field.
             <length>  is the length of the address, in bytes (not
             ASCII chars)
             <address> is the ASCII hex-encoded address (2 ASCII
             characters per byte; 12 chars for an Ethernet
             address.)
         This encoding is intended to mirror the representation
         of MAC addresses in DHCP."
    REFERENCE       "RFC 2131"
        SYNTAX          OCTET STRING(SIZE (1..32))

cnrNotifMACAddress OBJECT-TYPE
    SYNTAX     CnrPhysAddress
    MAX-ACCESS accessible-for-notify
    STATUS     current
    DESCRIPTION
        "The offending MAC address which caused a duplicate IP
        address to be detected."
    ::= { cnrNotifObjects 2 }


cnrNotifServer OBJECT-TYPE
    SYNTAX IpAddress
    MAX-ACCESS accessible-for-notify
    STATUS current
    DESCRIPTION
        "The IP Address of a server with which CNR
        is attempting to communicate."
    ::= { cnrNotifObjects 3 }

cnrNotifServerType  OBJECT-TYPE
    SYNTAX     INTEGER {dns(1), dhcp(2), ldap(3) }
    MAX-ACCESS accessible-for-notify
    STATUS     current
    DESCRIPTION
        "The type of server"
    ::= { cnrNotifObjects 4 }

cnrNotifDupIpAddressDetectedBy OBJECT-TYPE
    SYNTAX     INTEGER {dhcpClient(1), dhcpServer(2)}
    MAX-ACCESS accessible-for-notify
    STATUS     current
    DESCRIPTION
         "For a ciscoNetRegDuplicateAddress notification, this
         object indicates whether the client or server detected
         the condition."
    ::= { cnrNotifObjects 5 }


cnrNotifContestedIpAddress OBJECT-TYPE
    SYNTAX     IpAddress
    MAX-ACCESS accessible-for-notify
    STATUS     current
    DESCRIPTION
        "The IP address for which ownership is claimed by two or
        more DHCP servers."
    ::= { cnrNotifObjects 6 }


-- cnrNotifCfgObjects: Objects used to enable/disable notifications

cnrEnableFreeAddressLow OBJECT-TYPE
    SYNTAX      TruthValue
    MAX-ACCESS  read-write
    STATUS      current
    DESCRIPTION
        "Indicates whether notifications should be generated
         for this entity. The default is disabled (FALSE)."
    DEFVAL { false }
    ::= { cnrNotifCfgObjects 1 }
	 
cnrEnableFreeAddressHigh OBJECT-TYPE
    SYNTAX      TruthValue
    MAX-ACCESS  read-write
    STATUS      current
    DESCRIPTION
        "Indicates whether notifications should be generated
         for this entity. The default is disabled (FALSE)."
    DEFVAL { false }
    ::= { cnrNotifCfgObjects 2 }

cnrEnableServerStart OBJECT-TYPE
    SYNTAX      TruthValue
    MAX-ACCESS  read-write
    STATUS      current
    DESCRIPTION
        "Indicates whether notifications should be generated
         for this entity. The default is disabled (FALSE)."
    DEFVAL { false }
    ::= { cnrNotifCfgObjects 3 }

cnrEnableServerStop OBJECT-TYPE
    SYNTAX      TruthValue
    MAX-ACCESS  read-write
    STATUS      current
    DESCRIPTION
        "Indicates whether notifications should be generated
         for this entity. The default is disabled (FALSE)."
    DEFVAL { false }
    ::= { cnrNotifCfgObjects 4 }

cnrEnableDNSQueueTooBig OBJECT-TYPE
    SYNTAX      TruthValue
    MAX-ACCESS  read-write
    STATUS      current
    DESCRIPTION
        "Indicates whether notifications should be generated
         for this entity. The default is disabled (FALSE)."
    DEFVAL { false }
    ::= { cnrNotifCfgObjects 5 }
 
cnrEnableOtherServerNotResponding OBJECT-TYPE
    SYNTAX      TruthValue
    MAX-ACCESS  read-write
    STATUS      current
    DESCRIPTION
        "Indicates whether notifications should be generated
         for this entity. The default is disabled (FALSE)."
    DEFVAL { false }
    ::= { cnrNotifCfgObjects 6 }

cnrEnableDuplicateAddress OBJECT-TYPE
    SYNTAX      TruthValue
    MAX-ACCESS  read-write
    STATUS      current
    DESCRIPTION
        "Indicates whether notifications should be generated
         for this entity. The default is disabled (FALSE)."
    DEFVAL { false }
    ::= { cnrNotifCfgObjects 7 }

cnrEnableAddressConflict OBJECT-TYPE
    SYNTAX      TruthValue
    MAX-ACCESS  read-write
    STATUS      current
    DESCRIPTION
        "Indicates whether notifications should be generated
         for this entity. The default is disabled (FALSE)."
    DEFVAL { false }
    ::= { cnrNotifCfgObjects 8 }

cnrEnableOtherServerResponding OBJECT-TYPE
    SYNTAX      TruthValue
    MAX-ACCESS  read-write
    STATUS      current
    DESCRIPTION
        "Indicates whether notifications should be generated
         for this entity. The default is disabled (FALSE)."
    DEFVAL { false }
    ::= { cnrNotifCfgObjects 9 }
 
cnrEnableFailoverConfigMismatch OBJECT-TYPE
    SYNTAX      TruthValue
    MAX-ACCESS  read-write
    STATUS      current
    DESCRIPTION
        "Indicates whether notifications should be generated
         for this entity. The default is disabled (FALSE)."
    DEFVAL { false }
    ::= { cnrNotifCfgObjects 10 }


-- Notifications

ciscoNetRegMIBNotificationPrefix OBJECT IDENTIFIER
    ::= { ciscoNetworkRegistrarMIB 2 }

ciscoNetRegMIBNotifications OBJECT IDENTIFIER 
    ::= { ciscoNetRegMIBNotificationPrefix 0 }

ciscoNetRegFreeAddressLow NOTIFICATION-TYPE
    OBJECTS { cnrDHCPScopeFreeAddrLowThreshold,
              cnrDHCPScopeFreeAddrValue,
              cnrDHCPScopeFreeAddrUnits }
    STATUS  current
    DESCRIPTION
        "This notification signifies that the number
        of available IP addresses for a particular scope
        has fallen below the value of
        cnrDHCPScopeFreeAddrLowThreshold for that scope."
    ::= { ciscoNetRegMIBNotifications 1 }

ciscoNetRegFreeAddressHigh NOTIFICATION-TYPE
    OBJECTS { cnrDHCPScopeFreeAddrHighThreshold,
              cnrDHCPScopeFreeAddrValue,
              cnrDHCPScopeFreeAddrUnits }
    STATUS  current
    DESCRIPTION
        "This notification signifies that the number
        of available IP addresses for a particular scope
        has risen above the value of
        cnrDHCPScopeFreeAddrHighThreshold for that scope."
   ::= { ciscoNetRegMIBNotifications 2 }

ciscoNetRegServerStart NOTIFICATION-TYPE
    OBJECTS { cnrNotifServerType }
    STATUS  current
    DESCRIPTION
        "This notification signifies that the server
        of the specified type has started on the
        host from which this notification has been sent."
    ::= { ciscoNetRegMIBNotifications 3 }

ciscoNetRegServerStop NOTIFICATION-TYPE
    OBJECTS { cnrNotifServerType }
    STATUS  current
    DESCRIPTION
        "This notification signifies that the server
        of the specified type has stopped normally on the
        host from which this notification has been sent."
    ::= { ciscoNetRegMIBNotifications 4 }

ciscoNetRegDNSQueueTooBig NOTIFICATION-TYPE
    STATUS  current
    DESCRIPTION
        "This notification indicates that the number of pending
        dns updates has reached its limit.  Successive updates
        may be dropped, and DHCP may stop responding to client
        requests until this problem has cleared."
    ::= { ciscoNetRegMIBNotifications 5 }

ciscoNetRegOtherServerNotResponding NOTIFICATION-TYPE
    OBJECTS { cnrNotifServer,
              cnrNotifServerType }
    STATUS  current
    DESCRIPTION
        "This notification signifies that a server is not
        responding to updates from the DHCP server.  The 
        identity of the server is given by the cnrNotifServer
        object.  The type of the server is given by the
        cnrNotifServerType object."
    ::= { ciscoNetRegMIBNotifications 6 }

ciscoNetRegDuplicateAddress NOTIFICATION-TYPE
    OBJECTS { cnrNotifDupIpAddress ,
              cnrNotifMACAddress,
              cnrNotifDupIpAddressDetectedBy }
    STATUS  current
    DESCRIPTION
        "This notification signifies that a  duplicate IP address
        has been detected.  The DHCP server can detect this
        condition through the ping-before-offer mechanism.
        Alternatively, the client may have sent a DHCPDECLINE 
        back to the server; this is assumed to be the result of
        the client detecting that the address was in use.  In
        either case, the DHCP server marks the IP address as
        unavailable for leasing to clients.  The
        cnrNotifDupIpAddressDetectedBy object indicates whether
        the client or server detected this condition."
    ::= { ciscoNetRegMIBNotifications 7 }

ciscoNetRegAddressConflict NOTIFICATION-TYPE
    OBJECTS { cnrNotifContestedIpAddress,
              cnrNotifServer }
    STATUS  current
    DESCRIPTION
        "This notification indicates that the DHCP server on this
        host, and a DHCP server on another host, have claimed
        ownership for the same IP address.  The
        cnrNotifContestedIpAddress object indicates which address
        is under contention.  The cnrNotifServer object indicates
        with which other server a conflict was detected."
    ::= { ciscoNetRegMIBNotifications 8 }

ciscoNetRegOtherServerResponding NOTIFICATION-TYPE
    OBJECTS { cnrNotifServer,
              cnrNotifServerType }
    STATUS  current
    DESCRIPTION
        "This notification signifies that a server which had formerly
        been in a 'not responding' state is now responding to
        updates from the CNR protocol server.  The identity of the
        server is given by the cnrNotifServer object.  The type of
        the server is given by the cnrNotifServerType object.

        NOTE: One should not rely on recieving this notification
        as an indication that all is well with the network.
        Several conditions, including restart of the CNR
        protocol server, could result in either multiple
        ciscoNetRegOtherServerNotResponding notifications being sent,
        or in a ciscoNetRegOtherServerResponding notification NOT
        being sent."
    ::= { ciscoNetRegMIBNotifications 9 }

ciscoNetRegFailoverConfigMismatch NOTIFICATION-TYPE
    OBJECTS { cnrNotifServer }
    STATUS  current
    DESCRIPTION
        "This notification signifies that a server has detected
        via the failover protocol that its configuration does
        not match that of its failover peer, and that reliable 
        DHCP operation in the event of a server failure may not
        be possible.  The identity of the peer server is given
        by the cnrNotifServer object."        
    ::= { ciscoNetRegMIBNotifications 10 }


-- Conformance

ciscoNetworkRegistrarMIBConformance OBJECT IDENTIFIER ::=
    { ciscoNetworkRegistrarMIB 3 }

ciscoNetworkRegistrarMIBCompliances OBJECT IDENTIFIER ::=
    { ciscoNetworkRegistrarMIBConformance 1 }
ciscoNetworkRegistrarMIBGroups      OBJECT IDENTIFIER ::=
    { ciscoNetworkRegistrarMIBConformance 2 }


-- Compliance

ciscoNetworkRegistrarMIBCompliance MODULE-COMPLIANCE
    STATUS current
    DESCRIPTION
        "The compliance statement for entities which implement
        the Cisco Network Registrar MIB"
    
    MODULE        -- this module
    MANDATORY-GROUPS { 
        ciscoNetworkRegistrarDHCPScopeObjectsGroup,
        ciscoNetworkRegistrarNotifObjectsGroup }
    
    GROUP ciscoNetworkRegistrarNotifCfgObjectsGroup
    DESCRIPTION
        "Optional configuration objects for notifications."

    OBJECT cnrEnableFreeAddressLow
    MIN-ACCESS read-only
    DESCRIPTION
        "Write access is not required."
    
    OBJECT cnrEnableFreeAddressHigh
    MIN-ACCESS read-only
    DESCRIPTION
        "Write access is not required."
    
    OBJECT cnrEnableServerStart
    MIN-ACCESS read-only
    DESCRIPTION
        "Write access is not required."
    
    OBJECT cnrEnableServerStop
    MIN-ACCESS read-only
    DESCRIPTION
        "Write access is not required."
    
    OBJECT cnrEnableDNSQueueTooBig
    MIN-ACCESS read-only
    DESCRIPTION
        "Write access is not required."
    
    OBJECT cnrEnableOtherServerNotResponding
    MIN-ACCESS read-only
    DESCRIPTION
        "Write access is not required."
    
    OBJECT cnrEnableDuplicateAddress
    MIN-ACCESS read-only
    DESCRIPTION
        "Write access is not required."
    
    OBJECT cnrEnableAddressConflict
    MIN-ACCESS read-only
    DESCRIPTION
        "Write access is not required."
    
    OBJECT cnrEnableOtherServerResponding
    MIN-ACCESS read-only
    DESCRIPTION
        "Write access is not required."
    
    OBJECT cnrEnableFailoverConfigMismatch 
    MIN-ACCESS read-only
    DESCRIPTION
        "Write access is not required."
	
    ::= { ciscoNetworkRegistrarMIBCompliances 1 }

-- Units of Conformance

ciscoNetworkRegistrarDHCPScopeObjectsGroup OBJECT-GROUP
    OBJECTS { cnrDHCPScopeFreeAddrLowThreshold,
              cnrDHCPScopeFreeAddrHighThreshold,
              cnrDHCPScopeFreeAddrValue,
              cnrDHCPScopeFreeAddrUnits }
    STATUS current
    DESCRIPTION
        "Network Registrar MIB objects used in DHCP scopes."
    ::= { ciscoNetworkRegistrarMIBGroups 1 }


ciscoNetworkRegistrarNotifObjectsGroup OBJECT-GROUP
    OBJECTS { cnrNotifDupIpAddress,
              cnrNotifMACAddress,
              cnrNotifDupIpAddressDetectedBy,
              cnrNotifServer,
              cnrNotifServerType,
              cnrNotifContestedIpAddress }
    STATUS current
    DESCRIPTION
        "Network Registrar MIB objects used in notifications."
    ::= { ciscoNetworkRegistrarMIBGroups 2 }

ciscoNetworkRegistrarNotifCfgObjectsGroup OBJECT-GROUP
    OBJECTS { cnrEnableFreeAddressLow,
              cnrEnableFreeAddressHigh,
              cnrEnableServerStart,
              cnrEnableServerStop,     
              cnrEnableDNSQueueTooBig,
              cnrEnableOtherServerNotResponding,
              cnrEnableDuplicateAddress,
              cnrEnableAddressConflict,
              cnrEnableOtherServerResponding,
              cnrEnableFailoverConfigMismatch }
    STATUS current
    DESCRIPTION
        "Network Registrar MIB objects used to enable/disable 
	notifications."
    ::= { ciscoNetworkRegistrarMIBGroups 3 }

ciscoNetworkRegistrarNotificationsGroup NOTIFICATION-GROUP
    NOTIFICATIONS { ciscoNetRegFreeAddressLow,
                    ciscoNetRegFreeAddressHigh,
                    ciscoNetRegServerStart,
                    ciscoNetRegServerStop,     
                    ciscoNetRegDNSQueueTooBig,
                    ciscoNetRegOtherServerNotResponding,
                    ciscoNetRegDuplicateAddress,
                    ciscoNetRegAddressConflict,
                    ciscoNetRegOtherServerResponding,
                    ciscoNetRegFailoverConfigMismatch }
    STATUS current
    DESCRIPTION
        "Notifications which are implemented by the
        Cisco Network Registrar agent."
    ::= { ciscoNetworkRegistrarMIBGroups 4 }

END
