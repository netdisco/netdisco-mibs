-- *********************************************************************
-- CISCO-WWNMGR-MIB.my: World Wide Name Manager Mib
--
-- October 2002, Vinay Gaonkar
--
-- Copyright (c) 2002 by cisco Systems, Inc.
-- All rights reserved.
-- 
-- *********************************************************************

CISCO-WWNMGR-MIB DEFINITIONS ::= BEGIN

IMPORTS        
     MODULE-IDENTITY, OBJECT-TYPE, 
     NOTIFICATION-TYPE,  
     Unsigned32, Gauge32                    FROM SNMPv2-SMI
     MODULE-COMPLIANCE, OBJECT-GROUP,
     NOTIFICATION-GROUP                     FROM SNMPv2-CONF
     MacAddress                             FROM SNMPv2-TC
     ciscoMgmt                              FROM CISCO-SMI;        

ciscoWwnmgrMIB MODULE-IDENTITY
        LAST-UPDATED "200210010000Z"
        ORGANIZATION "Cisco Systems Inc. "
        CONTACT-INFO
                "     Cisco Systems
                      Customer Service
                Postal: 170 W Tasman Drive
                      San Jose, CA  95134
                      USA
                Tel: +1 800 553 -NETS
                E-mail: cs-san@cisco.com"
        DESCRIPTION
		     "MIB module for WWN Manager related management 
		     functionalities."
        REVISION   "200210010000Z"
        DESCRIPTION
            "Initial version of this MIB module."
        ::= { ciscoMgmt 286 }

ciscoWwnmMIBObjects OBJECT IDENTIFIER    ::= { ciscoWwnmgrMIB 1 }
wwnmConfigurationGroup OBJECT IDENTIFIER ::= { ciscoWwnmMIBObjects 1 } 
wwnmNotificationGroup OBJECT IDENTIFIER  ::= { ciscoWwnmMIBObjects 2 }
wwnmNotification OBJECT IDENTIFIER       ::= {wwnmNotificationGroup  1 }
wwnmNotificationPrefix OBJECT IDENTIFIER ::= { wwnmNotification 0 }


-- WWN Manager configuration group
--

wwnmSecondaryBaseMacAddress OBJECT-TYPE
        SYNTAX        MacAddress
        MAX-ACCESS    read-write
        STATUS        current
        DESCRIPTION   
               "The first MAC address used for generating World Wide
               Names (WWNs) when the default range of WWNs generated 
               from supervisor MAC address are exhausted."   
        DEFVAL {'000000000000'H}
        ::= { wwnmConfigurationGroup 1 }

wwnmSecondaryMacAddressRange OBJECT-TYPE
        SYNTAX        Unsigned32 (0..4294967295)
        MAX-ACCESS    read-write
        STATUS        current
        DESCRIPTION
               "The number of secondary MAC Addresses starting from 
               and including the wwnmSecondayBaseMacAddress."
        DEFVAL { 0 }
        ::= { wwnmConfigurationGroup 2 }

-- WWN Manager Statistics
--

wwnmType1MaxWwns OBJECT-TYPE
        SYNTAX        Unsigned32 (0..4294967295)
        MAX-ACCESS    read-only
        STATUS        current
        DESCRIPTION
                "Maximum number of NAA Type 1 WWNs that are available
                for assignment to internal entities."
        REFERENCE
           "FC-FS-2 Rev 1.70, Section 14 Name Identifier Formats."
        ::= {wwnmConfigurationGroup  3 }

wwnmType1AvailableWwns OBJECT-TYPE
        SYNTAX        Gauge32
        MAX-ACCESS    read-only
        STATUS        current
        DESCRIPTION
                "Number of NAA Type 1 WWNs that are currently 
                available for assignment to internal entities."
        REFERENCE
           "FC-FS-2 Rev 1.70, Section 14 Name Identifier Formats."
        ::= {wwnmConfigurationGroup  4 }

wwnmTypeOtherMaxWwns  OBJECT-TYPE
        SYNTAX        Unsigned32 (0..4294967295)
        MAX-ACCESS     read-only
        STATUS         current
        DESCRIPTION
               "Maximum number of total WWNs of types NAA Type 2 
               and Type 5 WWNs available for assignment to  internal
               entities."
        REFERENCE
           "FC-FS-2 Rev 1.70, Section 14 Name Identifier Formats."
        ::= {wwnmConfigurationGroup  5 }   
                                      
wwnmTypeOtherAvailableWwns OBJECT-TYPE
        SYNTAX        Gauge32
        MAX-ACCESS    read-only
        STATUS        current
        DESCRIPTION                   
               "Sum of number of NAA Type 2 and Type 5 WWNs currently
               available for assignment to the internal entities."
        REFERENCE
           "FC-FS-2 Rev 1.70, Section 14 Name Identifier Formats."
        ::= {wwnmConfigurationGroup  6 }     

wwnmType1ReservedWwns OBJECT-TYPE
        SYNTAX        Unsigned32 (0..4294967295)
        MAX-ACCESS    read-only
        STATUS        current
        DESCRIPTION
                "Number of NAA Type 1 WWNs that are reserved
                for internal purposes."
        REFERENCE
           "FC-FS-2 Rev 1.70, Section 14 Name Identifier Formats."
        ::= {wwnmConfigurationGroup  7 }

wwnmTypeOtherReservedWwns  OBJECT-TYPE
        SYNTAX        Unsigned32 (0..4294967295)
        MAX-ACCESS     read-only
        STATUS         current
        DESCRIPTION
               "Number of total WWNs of types NAA Type 2 
               and Type 5 WWNs reserved for internal purposes."
        REFERENCE
           "FC-FS-2 Rev 1.70, Section 14 Name Identifier Formats."
        ::= {wwnmConfigurationGroup  8 }   
                                      

--
-- WWN Manager Notification Group
--

wwnmType1WwnShortageNotify  NOTIFICATION-TYPE
        OBJECTS     { wwnmType1AvailableWwns}
        STATUS      current
        DESCRIPTION
               "A WWN shortage notification is generated whenever the 
               number of available Type 1 WWNs 'wwnmType1AvailableWwns'
               reduces to either 20% or 10% or 0% of the maximum number
               of Type 1 WWNs 'wwnmType1MaxWwns'.
               After a shortage event is generated for a threshhold
               (say 20%), another such event will not be generated until
               after an availability event (see 
               wwnmType1WwnAvailableNotify) is generated for the same 
               threshold."
    ::= { wwnmNotificationPrefix 1 }

wwnmType1WwnAvailableNotify  NOTIFICATION-TYPE
        OBJECTS     { wwnmType1AvailableWwns}
        STATUS      current
        DESCRIPTION
               "An availability notification is generated whenever
               the number of available Type 1 WWNs 
               (wwnmType1AvailableWwns) increases to either 25% or 15% 
               or 5% of the maximum number of Type 1 WWNs 
               (wwnmType1MaxWwns) after a wwnmType1WwnShortageNotify
               notification has been generated for either 20% or 10%
               or 5% respectively."
    ::= { wwnmNotificationPrefix 2 }

wwnmTypeOtherWwnShortageNotify NOTIFICATION-TYPE
        OBJECTS     { wwnmTypeOtherAvailableWwns}
        STATUS      current
        DESCRIPTION
               "A WWN shortage notification is generated whenever the 
               number of available Type Other WWNs 
               'wwnmTypeOtherAvailableWwns' reduces to either 20% or 
               10% or 0% of the maximum number of Type Other WWNs 
               'wwnmTypeOtherMaxWwns'.
               After a shortage event is generated for a threshhold 
               (say 20%), another such event will not be generated until
               after an availability event (see 
               wwnmType1WwnAvailableNotify) is generated for the same 
               threshold."
    ::= { wwnmNotificationPrefix 3 }
    
wwnmTypeOtherWwnAvailableNotify  NOTIFICATION-TYPE
            OBJECTS     { wwnmTypeOtherAvailableWwns}
            STATUS      current
            DESCRIPTION
                   "An availability notification is generated whenever
                   the number of available Type Other WWNs
                   (wwnmTypeOtherAvailableWwns) increases to either 25% 
                   or 15% or 5% of the maximum number of Type Other WWNs
                   (wwnmTypeOtherMaxWwns) after a 
                   wwnmTypeOtherWwnShortageNotify notification has been 
                   generated for either 20% or 10% or 5% respectively."
    ::= { wwnmNotificationPrefix 4 }

-- Conformance

ciscoWwnmMIBConformance OBJECT IDENTIFIER ::= { ciscoWwnmgrMIB 2 }
ciscoWwnmMIBCompliances OBJECT IDENTIFIER 
                                 ::= { ciscoWwnmMIBConformance 1 }
ciscoWwnmMIBGroups OBJECT IDENTIFIER 
                                 ::= { ciscoWwnmMIBConformance 2 }

ciscoWwnmMIBCompliance MODULE-COMPLIANCE
        STATUS   current
        DESCRIPTION
                "The compliance statement for entities which
                 implement the CISCO-WWNMGR-MIB."
        MODULE MANDATORY-GROUPS { cwmWwnmConfigurationGroup,
                                  cwmWwnmNotificationGroup }

        ::= { ciscoWwnmMIBCompliances 1 }

-- Units of Conformance

cwmWwnmConfigurationGroup  OBJECT-GROUP
        OBJECTS  { wwnmSecondaryBaseMacAddress, 
                   wwnmSecondaryMacAddressRange, 
                   wwnmType1MaxWwns, wwnmType1AvailableWwns,
                   wwnmTypeOtherMaxWwns, wwnmTypeOtherAvailableWwns,
                   wwnmType1ReservedWwns, wwnmTypeOtherReservedWwns
                 }
        STATUS   current
        DESCRIPTION
                "A collection of objects for WWN Manager."
        ::= { ciscoWwnmMIBGroups 6 }

cwmWwnmNotificationGroup  NOTIFICATION-GROUP
        NOTIFICATIONS  { wwnmType1WwnShortageNotify , 
                         wwnmType1WwnAvailableNotify,
                         wwnmTypeOtherWwnShortageNotify,
                         wwnmTypeOtherWwnAvailableNotify }
        STATUS   current
        DESCRIPTION
                "A collection of notifications for the 
                WWN assignment."
        ::= { ciscoWwnmMIBGroups 8 }
END
