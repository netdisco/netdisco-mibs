-- *****************************************************************
-- CISCO-POWER-ETHERNET-EXT-MIB
--
-- March 2004, Seth Wang
--
-- Copyright (c) 2004, 2005 by Cisco Systems, Inc.
-- All rights reserved.
-- *****************************************************************
CISCO-POWER-ETHERNET-EXT-MIB DEFINITIONS ::= BEGIN

IMPORTS
    MODULE-IDENTITY, OBJECT-TYPE, Unsigned32
        FROM SNMPv2-SMI
    MODULE-COMPLIANCE, OBJECT-GROUP
        FROM SNMPv2-CONF
    TruthValue
        FROM SNMPv2-TC
    pethPsePortEntry, pethMainPseGroupIndex
        FROM POWER-ETHERNET-MIB
    ciscoMgmt
        FROM CISCO-SMI
    EntPhysicalIndexOrZero
        FROM CISCO-TC
    SnmpAdminString
        FROM SNMP-FRAMEWORK-MIB;

ciscoPowerEthernetExtMIB MODULE-IDENTITY
    LAST-UPDATED "200506100000Z"
    ORGANIZATION "Cisco Systems, Inc."
    CONTACT-INFO
        "        Cisco Systems
                 Customer Service

         Postal: 170 W Tasman Drive
                 San Jose, CA 95134
                 USA

            Tel: +1 800 553-NETS

         E-mail: cs-lan-switch-snmp@cisco.com"
    DESCRIPTION
        "A MIB module for extending the POWER-ETHERNET-MIB
         (RFC3621) to add objects which provide additional
         management information about Power Sourcing Equipment
         (PSE) not available in POWER-ETHERNET-MIB.

         Glossary

         Power Sourcing Equipment (PSE)
             These are devices supplying electrical power to
             other equipment. They are, for example, inline power
             switches, inline power daughterboards and power patch
             panels.

         Powered Device (PD)
             These are devices receiving their electrical power
             supply from Power Sourcing Equipment. They are, for
             example, IP telephones and wireless access points
             or bridges."

    REVISION    "200506100000Z"
    DESCRIPTION
        "Added 'limit' to cpeExtPsePortEnable, 'overdraw' to
         cpeExtPsePortAdditionalStatus and the groups
         cpeExtPsePortPwrMonitorGroup and
         cpeExtMainPseGroup."
    REVISION    "200404120000Z"
    DESCRIPTION
        "Initial version of this MIB module."
    ::= { ciscoMgmt 402 } 

cpeExtMIBNotifs
    OBJECT IDENTIFIER ::= { ciscoPowerEthernetExtMIB 0 }
cpeExtMIBObjects
    OBJECT IDENTIFIER ::= { ciscoPowerEthernetExtMIB 1 }
cpeExtMIBConformance
    OBJECT IDENTIFIER ::= { ciscoPowerEthernetExtMIB 2 }

cpeExtDefaultAllocation OBJECT-TYPE
    SYNTAX        Unsigned32
    UNITS         "milliwatts"
    MAX-ACCESS    read-write
    STATUS        current
    DESCRIPTION
        "This object indicates the default inline power allocation per
         port. This is a global configuration parameter that applies
         to all inline power capable ports in the system.

         The system must consider this object as well as the per port
         configuration object, cpeExtPsePortPwrMax, when determining
         how much power to allocate to a port. The system will use the
         lower of the two numbers."
    ::= { cpeExtMIBObjects 1 }

cpeExtPsePortTable OBJECT-TYPE
    SYNTAX        SEQUENCE OF CpeExtPsePortEntry
    MAX-ACCESS    not-accessible
    STATUS        current
    DESCRIPTION
        "This table extends the POWER-ETHERNET-MIB pethPsePortTable
         for power Ethernet ports on a Powered Sourcing Equipment
         (PSE) device."
    REFERENCE
        "RFC3621"
    ::= { cpeExtMIBObjects 2 }

cpeExtPsePortEntry OBJECT-TYPE
    SYNTAX        CpeExtPsePortEntry
    MAX-ACCESS    not-accessible
    STATUS        current
    DESCRIPTION
        "A cpeExtPsePortEntry extends a corresponding
         pethPsePortTable entry. This entry displays and
         controls more characteristics of a power Ethernet
         port on a PSE device."
    AUGMENTS      { pethPsePortEntry }
    ::= { cpeExtPsePortTable 1 }

CpeExtPsePortEntry ::= SEQUENCE {
        cpeExtPsePortEnable            INTEGER,
        cpeExtPsePortDiscoverMode      INTEGER,
        cpeExtPsePortDeviceDetected    TruthValue,
        cpeExtPsePortIeeePd            TruthValue,
        cpeExtPsePortAdditionalStatus  BITS,
        cpeExtPsePortPwrMax            Unsigned32,
        cpeExtPsePortPwrAllocated      Unsigned32,
        cpeExtPsePortPwrAvailable      Unsigned32,
        cpeExtPsePortPwrConsumption    Unsigned32,
        cpeExtPsePortMaxPwrDrawn       Unsigned32
    }

cpeExtPsePortEnable OBJECT-TYPE
    SYNTAX       INTEGER {
                           auto(1),
                           static(2),
                           limit(3)
                         }
    MAX-ACCESS   read-write
    STATUS       current
    DESCRIPTION
        "This object is an extension of the pethPsePortAdminEnable
         object from RFC3621. It allows the user to be more specific
         when enabling the PSE functions. The states, 'auto', 'static'
         and 'limit' correspond to a value of 'true' for the
         pethPsePortAdminEnable object. However, if the value of
         pethPsePortAdminEnable is 'false', then the value of this
         object is irrelevant.

         Setting this value to 'auto' enables Powered Device discovery
         on the interface and the amount of power allocated depends on
         the Powered Device discovered. If pethPsePortAdminEnable was
         'false' prior to this set operation, then it will become
         'true'.

         Setting this value to 'static' will also enable Powered
         Device discovery. However, this is different from 'auto'
         in that the amount of power is pre-allocated based on the
         configuration on the Power Sourcing Equipment. If
         pethPsePortAdminEnable was 'false' prior to this set
         operation, then it will become 'true'.

         Setting this value to 'limit' enables Powered Device
         discovery on the interface. The amount of power allocated
         depends on the Powered Device discovered and the value
         of cpeExtPsePortPwrMax. The lower value will be used.
         If pethPsePortAdminEnable was 'false' prior to this set
         operation, then it will become 'true'.

         When setting the pethPsePortAdminEnable object to 'true'
         this object will adopt the value of 'auto'."
    ::= { cpeExtPsePortEntry 1 }

cpeExtPsePortDiscoverMode OBJECT-TYPE
    SYNTAX       INTEGER {
                           unknown(1),
                           off(2),
                           ieee(3),
                           cisco(4),
                           ieeeAndCisco(5)
                         }
    MAX-ACCESS   read-only
    STATUS       current
    DESCRIPTION
        "This object indicates the discover mode used by the system to
         discover the PD.

         A value of 'unknown' indicates that the discover mode on the
         interface is unknown.

         A value of 'off' indicates that discovery is disabled on the
         interface.

         A value of 'ieee' indicates that the discover mode on the
         interface is IEEE based.

         A value of 'cisco' indicates that the discover mode on the
         interface is Cisco based.

         A value of 'ieeeAndCisco' indicates that the discover mode on
         the interface is both IEEE and Cisco based."
    ::= { cpeExtPsePortEntry 2 }

cpeExtPsePortDeviceDetected OBJECT-TYPE
    SYNTAX       TruthValue
    MAX-ACCESS   read-only
    STATUS       current
    DESCRIPTION
        "This object indicates if a Powered Device (PD) has been
         detected on the interface.

         A value of 'true' indicates that a PD has been detected on
         the interface.

         A value of 'false' indicates that no PD has been detected on
         the interface."
    ::= { cpeExtPsePortEntry 3 }

cpeExtPsePortIeeePd OBJECT-TYPE
    SYNTAX       TruthValue
    MAX-ACCESS   read-only
    STATUS       current
    DESCRIPTION
        "This object indicates whether the Powered Device attached
         to the interface is an IEEE compliant Powered Device or not.

         A value of 'true' indicates the attached Powered Device is
         an IEEE compliant Powered Device.

         A value of 'false' indicates the attached Powered Device
         is not an IEEE compliant Powered Device. This also means
         that the value of the corresponding object from the
         pethPsePortTable, pethPsePortPowerClassifications is
         irrelevant."
    ::= { cpeExtPsePortEntry 4 }

cpeExtPsePortAdditionalStatus OBJECT-TYPE
    SYNTAX       BITS { deny(0), overdraw(1) }
    MAX-ACCESS   read-only
    STATUS       current
    DESCRIPTION
        "This object is an extension of the pethPsePortDetectionStatus
         object from RFC3621 and provides additional status
         information.

         deny: When set, the PD attached to the interface is being
               denied power due to insufficient power resources on
               the Power Sourcing Equipment.

         overdraw: When set, the PD attached to the interface is
                   being denied power because the PD is trying
                   to consume more power than it has been
                   configured to consume."
    ::= { cpeExtPsePortEntry 5 }

cpeExtPsePortPwrMax OBJECT-TYPE
    SYNTAX       Unsigned32
    UNITS        "milliwatts"
    MAX-ACCESS   read-write
    STATUS       current
    DESCRIPTION
        "This indicates the maximum amount of power that the PSE will
         make available to the PD connected to this interface."
    ::= { cpeExtPsePortEntry 6 }

cpeExtPsePortPwrAllocated OBJECT-TYPE
    SYNTAX       Unsigned32
    UNITS        "milliwatts"
    MAX-ACCESS   read-only
    STATUS       current
    DESCRIPTION
        "This object indicates the amount of power allocated from the
         PSE for the PD."
    ::= { cpeExtPsePortEntry 7 }

cpeExtPsePortPwrAvailable OBJECT-TYPE
    SYNTAX       Unsigned32
    UNITS        "milliwatts"
    MAX-ACCESS   read-only
    STATUS       current
    DESCRIPTION
        "This object indicates the amount of power available for
         the PD to use. This value may differ from the value
         cpeExtPsePortPwrAllocated due to the efficiency issues
         of delivering the power from the PSE to the PD.

         When sufficient power is available to power a PD, this
         value should be equal to the lower of the two objects,
         cpeExtDefaultAllocation and cpeExtPsePortPwrMax."
    ::= { cpeExtPsePortEntry 8 }

cpeExtPsePortPwrConsumption OBJECT-TYPE
    SYNTAX       Unsigned32
    UNITS        "milliwatts"
    MAX-ACCESS   read-only
    STATUS       current
    DESCRIPTION
        "This indicates the actual power consumption of the PD
         connected to this interface. It may not necessarily
         be equal to the value of cpeExtPsePortPwrAvailable."
    ::= { cpeExtPsePortEntry 9 }

cpeExtPsePortMaxPwrDrawn OBJECT-TYPE
    SYNTAX       Unsigned32
    UNITS        "milliwatts"
    MAX-ACCESS   read-only
    STATUS       current
    DESCRIPTION
        "This indicates the maximum amount of power drawn by the PD
        connected to this interface, since it was powered on."
    ::= { cpeExtPsePortEntry 10 }

cpeExtMainPseTable OBJECT-TYPE
    SYNTAX        SEQUENCE OF CpeExtMainPseEntry
    MAX-ACCESS    not-accessible
    STATUS        current
    DESCRIPTION
        "This table contains the additional information for the
        main PSE group in pethMainPseTable."
    REFERENCE
        "RFC3621, pethMainPseTable"
    ::= { cpeExtMIBObjects 3 }

cpeExtMainPseEntry OBJECT-TYPE
    SYNTAX        CpeExtMainPseEntry
    MAX-ACCESS    not-accessible
    STATUS        current
    DESCRIPTION
        "A cpeExtMainPseEntry contains information about
        a particular pethMainPseGroupIndex. An entry is
        created by the agent when a main PSE group is added
        to the pethMainPseTable. An entry is deleted by the
        agent when a main PSE group is removed from the
        pethMainPseTable."
    REFERENCE
        "RFC3621, pethMainPseTable"
    INDEX  { pethMainPseGroupIndex }
    ::= { cpeExtMainPseTable 1 }

CpeExtMainPseEntry ::= SEQUENCE {
        cpeExtMainPseEntPhyIndex        EntPhysicalIndexOrZero,
        cpeExtMainPseDescr              SnmpAdminString,
        cpeExtMainPsePwrMonitorCapable  TruthValue
    }

cpeExtMainPseEntPhyIndex OBJECT-TYPE
    SYNTAX       EntPhysicalIndexOrZero
    MAX-ACCESS   read-only
    STATUS       current
    DESCRIPTION
        "The entPhysicalIndex value that uniquely identifies the
        main PSE group. If the main PSE group does not have a
        corresponding physical entry in entPhysicalTable or if
        the entPhysicalTable is not supported by the management
        system, then this object has the value of zero."
    REFERENCE
        "RFC 2737, entPhysicalIndex."
    ::= { cpeExtMainPseEntry 1 }

cpeExtMainPseDescr OBJECT-TYPE
    SYNTAX       SnmpAdminString
    MAX-ACCESS   read-only
    STATUS       current
    DESCRIPTION
        "A textual string containing information about the Power
        Source Equipment (PSE) group."
    ::= { cpeExtMainPseEntry 2 }

cpeExtMainPsePwrMonitorCapable OBJECT-TYPE
    SYNTAX       TruthValue
    MAX-ACCESS   read-only
    STATUS       current
    DESCRIPTION
        "This object indicates if the given group is capable of
        monitoring the power consumption of the interfaces that
        belong to the group. The value 'true' means that the
        group is capable. The value 'false' means that the group
        in not capable."
    ::= { cpeExtMainPseEntry 3 }

-- Conformance

cpeExtMIBCompliances
    OBJECT IDENTIFIER ::= { cpeExtMIBConformance 1 }

cpeExtMIBGroups
    OBJECT IDENTIFIER ::= { cpeExtMIBConformance 2 }

cpeExtMIBCompliance MODULE-COMPLIANCE
    STATUS deprecated
    DESCRIPTION
        "The compliance statement for the
         CISCO-POWER-ETHERNET-EXT-MIB."
    MODULE
        MANDATORY-GROUPS { cpeExtPsePortGroup }
    GROUP cpeExtPsePortGlobalConfigGroup
    DESCRIPTION
        "The cpeExtPsePortGlobalConfigGroup is mandatory for agents
         that support global configurations on the PSE interfaces."
    ::= { cpeExtMIBCompliances 1 }

cpeExtMIBCompliance2 MODULE-COMPLIANCE
    STATUS current
    DESCRIPTION
        "The compliance statement for the
         CISCO-POWER-ETHERNET-EXT-MIB."
    MODULE
        MANDATORY-GROUPS { cpeExtPsePortGroup }
    GROUP cpeExtPsePortGlobalConfigGroup
    DESCRIPTION
        "The cpeExtPsePortGlobalConfigGroup is mandatory for agents
         that support global configurations on the PSE interfaces."
    GROUP cpeExtPsePortPwrMonitorGroup
    DESCRIPTION
        "The cpeExtPsePortPwrMonitorGroup is mandatory for agents
         that provide power monitoring on PD's connected to the
         PSE interfaces."
    GROUP cpeExtMainPseGroup
    DESCRIPTION
        "The cpeExtMainPseGroup is mandatory for agents
         that support the interface power consumption
         monitoring, or need additional info to identify
         the PSE group."

    ::= { cpeExtMIBCompliances 2 }

-- Units of Conformance

cpeExtPsePortGroup OBJECT-GROUP
    OBJECTS {
        cpeExtPsePortEnable,
        cpeExtPsePortDiscoverMode,
        cpeExtPsePortDeviceDetected,
        cpeExtPsePortIeeePd,
        cpeExtPsePortAdditionalStatus,
        cpeExtPsePortPwrMax,
        cpeExtPsePortPwrAllocated,
        cpeExtPsePortPwrAvailable,
        cpeExtPsePortPwrConsumption
    }
    STATUS current
    DESCRIPTION
        "This group provides information and configuration objects
         in addition to those provided in the POWER-ETHERNET-MIB
         (RFC3621)."
    ::= { cpeExtMIBGroups 1 }

cpeExtPsePortGlobalConfigGroup OBJECT-GROUP
    OBJECTS {
        cpeExtDefaultAllocation
    }
    STATUS current
    DESCRIPTION
        "This is a collection of objects which provide global
         configuration of the PSE interfaces."
    ::= { cpeExtMIBGroups 2 }

cpeExtPsePortPwrMonitorGroup OBJECT-GROUP
    OBJECTS {
        cpeExtPsePortMaxPwrDrawn
    }
    STATUS current
    DESCRIPTION
        "This is a collection of objects which provide power
        monitoring on PD's connected to the PSE interfaces."
    ::= { cpeExtMIBGroups 3 }

cpeExtMainPseGroup OBJECT-GROUP
    OBJECTS {
        cpeExtMainPseEntPhyIndex,
        cpeExtMainPseDescr,
        cpeExtMainPsePwrMonitorCapable
    }
    STATUS current
    DESCRIPTION
        "This is a collection of objects which provide
        additional information for the PSE group."
    ::= { cpeExtMIBGroups 4 }

END
