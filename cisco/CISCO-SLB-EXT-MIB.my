-- *****************************************************************
-- CISCO-SLB-EXT-MIB.my: Server Load-Balancing Extension MIB
--
-- March 2002, Anh Nguyen
--
-- Copyright (c) 2002 by cisco Systems, Inc.
-- All rights reserved.
-- *****************************************************************
--
CISCO-SLB-EXT-MIB DEFINITIONS ::= BEGIN

IMPORTS
        MODULE-IDENTITY,
        NOTIFICATION-TYPE,
        OBJECT-TYPE,
        Counter32,
        Counter64,
        Gauge32
                FROM SNMPv2-SMI

        CiscoPort,
        CiscoIpProtocol,
        Unsigned32
                FROM CISCO-TC

        SnmpAdminString
                FROM SNMP-FRAMEWORK-MIB

        InetAddressType,
        InetAddress
                FROM INET-ADDRESS-MIB

        slbEntity,
        slbStatsTableEntry,
        slbServerFarmTableEntry,
        slbVirtualServerTableEntry,
        SlbServerString,
        SlbRealServerState,
        SlbConnectionState
                FROM CISCO-SLB-MIB

        TimeInterval,
        TimeStamp,
        TruthValue,
        TEXTUAL-CONVENTION,
        RowStatus
                FROM SNMPv2-TC

        MODULE-COMPLIANCE,
        OBJECT-GROUP,
        NOTIFICATION-GROUP
                FROM SNMPv2-CONF

        ciscoMgmt
                FROM CISCO-SMI;

ciscoSlbExtMIB MODULE-IDENTITY
        LAST-UPDATED    "200208190000Z"
        ORGANIZATION    "Cisco Systems, Inc."
        CONTACT-INFO
                "       Cisco Systems
                        Customer Service

                Postal: 170 W. Tasman Drive
                        San Jose, CA  95134
                        USA

                   Tel: +1 800 553-NETS

                E-mail: cs-slb@cisco.com"
        DESCRIPTION
                "The extended MIB for managing Server Load Balancing
                Manager(s). This MIB extends the SLB management
                functionality in the CISCO-SLB-MIB. The Cisco Content
                Switching Module (CSM) product is the first SLB
                product to support this MIB.

                SLB: Server Load Balancing. Server load balancing
                provides for the balancing of packets and connections
                arriving at the SLB device across a number of other
                devices, such as real servers, firewalls, or caches.
                A system containing an SLB device typically exhibits
                higher performance, scalability, and reliability than
                any of the devices being load balanced.  An SLB device
                determines how to handle incoming frames and
                connections according to the contents of incoming data
                and various configuration options. In determining how
                to handle incoming data, an SLB device may examine the
                data at any OSI layer, including Layer 7.

                This MIB includes instrumentation for the manager-side
                implementation of the Dynamic Feedback Protocol (DFP).
                A DFP manager uses the DFP protocol to communicate with
                DFP agents in order to obtain information about the
                current load and available capacity of devices.

                Acronyms and terms:
                
                  SLB    Server Load Balancing
                  VIP    Virtual Server IP address
                  NAT    Network Address Translation
                  SF     Serverfarm
                  FT     Fault Tolerance
                "

        REVISION        "200208190000Z"
        DESCRIPTION
                "Initial version of this MIB module.  It is an extension
                to SLB MIB for Layer 7 policy load balancing features."
        ::= { ciscoMgmt 254 }

ciscoSlbExtMIBNotifs  OBJECT IDENTIFIER ::= { ciscoSlbExtMIB 0 }
ciscoSlbExtMIBObjects OBJECT IDENTIFIER ::= { ciscoSlbExtMIB 1 }
cslbxStats            OBJECT IDENTIFIER ::= { ciscoSlbExtMIBObjects 1 }
cslbxServerFarms      OBJECT IDENTIFIER ::= { ciscoSlbExtMIBObjects 2 }
cslbxClientNatPools   OBJECT IDENTIFIER ::= { ciscoSlbExtMIBObjects 3 }
cslbxStickyObjects    OBJECT IDENTIFIER ::= { ciscoSlbExtMIBObjects 4 }
cslbxMaps             OBJECT IDENTIFIER ::= { ciscoSlbExtMIBObjects 5 }
cslbxServerProbes     OBJECT IDENTIFIER ::= { ciscoSlbExtMIBObjects 6 }
cslbxPolicies         OBJECT IDENTIFIER ::= { ciscoSlbExtMIBObjects 7 }
cslbxVirtualServers   OBJECT IDENTIFIER ::= { ciscoSlbExtMIBObjects 8 }
cslbxVlans            OBJECT IDENTIFIER ::= { ciscoSlbExtMIBObjects 9 }
cslbxFaultTolerance   OBJECT IDENTIFIER ::= { ciscoSlbExtMIBObjects 10 }
cslbxXmlConfig        OBJECT IDENTIFIER ::= { ciscoSlbExtMIBObjects 11 }
cslbxConnections      OBJECT IDENTIFIER ::= { ciscoSlbExtMIBObjects 12 }
cslbxNotifObjects     OBJECT IDENTIFIER ::= { ciscoSlbExtMIBObjects 13 }
ciscoSlbExtMIBConform OBJECT IDENTIFIER ::= { ciscoSlbExtMIB 2 }

--  ********************************************************************
--  *                                                                  *
--  * Textual Conventions                                              *
--  *                                                                  *
--  ********************************************************************

SlbObjectNameString ::= TEXTUAL-CONVENTION
        STATUS          current
        DESCRIPTION
                "The name of an associated SLB object.
                 All SLB object names are in uppercase."
        SYNTAX OCTET STRING (SIZE (0..15))

SlbUrlString ::= TEXTUAL-CONVENTION
        DISPLAY-HINT    "255a"
        STATUS          current
        DESCRIPTION
                "The octet string containing the Uniform Resource
                Locator (URL) information.  It is in human-readable
                form."
        SYNTAX OCTET STRING (SIZE (0..255))

SlbRegularExpression ::= TEXTUAL-CONVENTION
    DISPLAY-HINT    "255a"
    STATUS          current
    DESCRIPTION
        "A regular expression of length 0 to 255. Regular expressions
         are typically used for matching fields in Layer 7 data
         streams, such as URLs or Cookies in HTTP. The following
         syntax is based on the file name matching algorithm commonly
         employed in UNIX :
         '*' matches zero or more characters;
         '?' matches exactly one character;
         '\' means escaped character, e.g., '\*' matches the
                character '*';
         a bracketed range matches any single character from the
                range, e.g. [0-9] matches '0', '2', and '9', but not
                'a';
         a leading ^ in a range means don't match any in the range;
         '+' matches any sequence of one or more characters;
         '.' matches any single character;
         All other characters represent themselves.
         '\a' matches alert (ASCII 7);
         '\b' matches backspace (ASCII 8);
         '\f' matches form-feed (ASCII 12);
         '\n' matches newline (ASCII 10);
         '\r' matches carriage return (ASCII 13);
         '\t' matches tab (ASCII 9);
         '\v' matches vertical tab (ASCII 11);
         '\0' matches null (ASCII 0);
         '\\' matches backslash;
         '\x##' matches the ASCII character whose hexadecimal
                representation is ##.
        "
    SYNTAX OCTET STRING (SIZE (0..255))

SlbFailAction ::= TEXTUAL-CONVENTION
        STATUS          current
        DESCRIPTION
                "The current action setting for a server farm when
                a real server has failed.
                'noAction'      : No additional action besides taking
                                  the server out of service.
                'purgeConns'    : Purge all connections to this real
                                  server."

        SYNTAX INTEGER {
                noAction(1),
                purgeConns(2)
        }

SlbIpAdvertise ::= TEXTUAL-CONVENTION
        STATUS          current
        DESCRIPTION
                "The current advertise option for the virtual server
                IP address.
                'alwaysAdvertise' : Advertise VIP if configured. 
                'activeAdvertise' : Advertise VIP only if virtual
                                    server is active."

        SYNTAX INTEGER {
                alwaysAdvertise(1),
                activeAdvertise(2)
        }

SlbStickyType ::= TEXTUAL-CONVENTION
        STATUS          current
        DESCRIPTION
                "The current type of the Sticky Group. A Sticky Group
                is a list of rules mapping incoming connection
                parameters, such as source IP address, to specific
                real servers. If an incoming connection matches a
                rule in a Sticky Group, the SLB may 'stick' that
                connection to the real server specified in the
                matching rule.
                'srcIpSticky'      : Stick based on source IP address.
                'httpCookieSticky' : Stick based on HTTP Cookie name. 
                'sslSticky'        : Stick based on SSL Session ID."

        SYNTAX INTEGER {
                srcIpSticky(1),
                httpCookieSticky(2),
                sslSticky(3)
        }

SlbMapType ::= TEXTUAL-CONVENTION
        STATUS          current
        DESCRIPTION
                "The current type of the Map group. A Map group
                contains a list of rules matching information in
                the connection with the HTTP URL, HTTP Cookie,
                HTTP Header, or HTTP Return Code criteria.
                'notCfgMap'     : Map type has not been specified.
                'urlMap'        : HTTP URL matching group.
                'cookieMap'     : HTTP Cookie matching group.
                'headerMap'     : HTTP Header field matching group.
                'returnCodeMap' : HTTP return code matching group."

        SYNTAX INTEGER {
                notCfgMap(1),
                urlMap(2),
                cookieMap(3),
                headerMap(4),
                returnCodeMap(5)
        }

SlbReplicationMode ::= TEXTUAL-CONVENTION
        STATUS          current
        DESCRIPTION
                "The current replicating option for the virtual
                server.
                'replNone'       : Do not replicate any information.
                'replAll'        : Replicate connection and sticky
                                   information. 
                'replConnection' : Replicate only the connection
                                   information.
                'replStickyData' : Replicate only the sticky
                                   information."

        SYNTAX INTEGER {
                replNone(1),
                replAll(2),
                replConnection(3),
                replStickyData(4)
        }

SlbProbeType ::= TEXTUAL-CONVENTION
        STATUS          current
        DESCRIPTION
                "The probe type for probing the health of a server.
                'icmpProbe'     : Probe server by sending ICMP
                                  echo requests.
                'tcpProbe'      : Probe server by opening TCP
                                  connections.
                'dnsProbe'      : Probe server by sending DNS
                                  queries.
                'httpProbe'     : Probe server by sending HTTP
                                  requests.
                'ftpProbe'      : Probe server by opening FTP
                                  connections.
                'telnetProbe'   : Probe server by opening Telnet
                                  connections.
                'smtpProbe'     : Probe server by opening SMTP
                                  connections."

        SYNTAX INTEGER {
                icmpProbe(1),
                tcpProbe(2),
                dnsProbe(3),
                httpProbe(4),
                ftpProbe(5),
                telnetProbe(6),
                smtpProbe(7)
        }

SlbProbeAction ::= TEXTUAL-CONVENTION
        STATUS          current
        DESCRIPTION
                "The current action setting for a probing condition or
                monitoring condition such as the HTTP return code.
                'noAction'      : No action.
                'logAction'     : Logging the event.
                'removeAction'  : Removing the service."

        SYNTAX INTEGER {
                noAction(1),
                logAction(2),
                removeAction(3)
        }

SlbVlanType ::= TEXTUAL-CONVENTION
        STATUS          current
        DESCRIPTION
                "Each configured SLB VLAN has one of the following
                types :
                'clientVlan'    : Client side VLAN interface.
                'serverVlan'    : Server side VLAN interface.
                'ftVlan'        : Fault Tolerance VLAN interface."

        SYNTAX INTEGER {
                clientVlan(1),
                serverVlan(2),
                ftVlan(3)
        }

SlbFtState ::= TEXTUAL-CONVENTION
        STATUS          current
        DESCRIPTION
                "The current Fault Tolerance state of the SLB entity.
                'notConfigFT'      : Was not configured with FT.
                'initializingFT'   : Initializing Fault Tolerance.
                'activeFT'         : Active FT peer.
                'standbyFT'        : Standby FT peer."

        SYNTAX INTEGER {
                notConfigFT(1),
                initializingFT(2),
                activeFT(3),
                standbyFT(4)
        }

--  *************************************************************
--  *                                                           *
--  * SLB-EXT - Statistics Table                                *
--  *                                                           *
--  *************************************************************

cslbxStatsTable                           OBJECT-TYPE
        SYNTAX          SEQUENCE OF CslbxStatsTableEntry
        MAX-ACCESS      not-accessible
        STATUS          current
        DESCRIPTION
                "A table of global SLB statistics for all local SLB
                entities.  It contains addition information to the
                slbStatsTable."
        ::= { cslbxStats 1 }

cslbxStatsTableEntry                      OBJECT-TYPE
        SYNTAX          CslbxStatsTableEntry
        MAX-ACCESS      not-accessible
        STATUS          current
        DESCRIPTION
                "A list of additional SLB statistics for a particular
                SLB entity."
        AUGMENTS        { slbStatsTableEntry }
        ::= { cslbxStatsTable 1 }

CslbxStatsTableEntry ::= SEQUENCE {
        cslbxStatsServerInitConns                 Counter32,
        cslbxStatsServerInitHCConns               Counter64,
        cslbxStatsCurrConnections                 Gauge32,
        cslbxStatsCurrServerInitConns             Gauge32,
        cslbxStatsFailedConns                     Counter32,
        cslbxStatsFailedServerInitConns           Counter32,
        cslbxStatsL4PolicyConns                   Counter32,
        cslbxStatsL7PolicyConns                   Counter32,
        cslbxStatsDroppedL4PolicyConns            Counter32,
        cslbxStatsDroppedL7PolicyConns            Counter32,
        cslbxStatsFtpConns                        Counter32,
        cslbxStatsHttpRedirectConns               Counter32,
        cslbxStatsDroppedRedirectConns            Counter32,
        cslbxStatsNoMatchPolicyRejects            Counter32,
        cslbxStatsNoCfgPolicyRejects              Counter32,
        cslbxStatsNoActiveServerRejects           Counter32,
        cslbxStatsAclDenyRejects                  Counter32,
        cslbxStatsMaxParseLenRejects              Counter32,
        cslbxStatsBadSslFormatRejects             Counter32,
        cslbxStatsL7ParserErrorRejects            Counter32,
        cslbxStatsVerMismatchRejects              Counter32,
        cslbxStatsOutOfMemoryRejects              Counter32,
        cslbxStatsTimedOutConnections             Counter32,
        cslbxStatsTcpChecksumErrorPkts            Counter32,
        cslbxStatsIpChecksumErrorPkts             Counter32
}

cslbxStatsServerInitConns                 OBJECT-TYPE
        SYNTAX          Counter32
        UNITS           "connections"
        MAX-ACCESS      read-only
        STATUS          current
        DESCRIPTION
                "The total number of connections initiated by the
                servers."
        ::= { cslbxStatsTableEntry 1 }

cslbxStatsServerInitHCConns               OBJECT-TYPE
        SYNTAX          Counter64
        UNITS           "connections"
        MAX-ACCESS      read-only
        STATUS          current
        DESCRIPTION
                "The total number of connections initiated by the
                servers.  This is the 64-bit version of
                cslbxStatsServerInitConns."
        ::= { cslbxStatsTableEntry 2 }

cslbxStatsCurrConnections                 OBJECT-TYPE
        SYNTAX          Gauge32
        UNITS           "connections"
        MAX-ACCESS      read-only
        STATUS          current
        DESCRIPTION
                "The number of connections currently still open."
        ::= { cslbxStatsTableEntry 3 }

cslbxStatsCurrServerInitConns             OBJECT-TYPE
        SYNTAX          Gauge32
        UNITS           "connections"
        MAX-ACCESS      read-only
        STATUS          current
        DESCRIPTION
                "The number of server initiated connections currently
                 still open."
        ::= { cslbxStatsTableEntry 4 }

cslbxStatsFailedConns                     OBJECT-TYPE
        SYNTAX          Counter32
        UNITS           "connections"
        MAX-ACCESS      read-only
        STATUS          current
        DESCRIPTION
                "The number of connections that were load balanced
                to real servers that then failed to respond."
        ::= { cslbxStatsTableEntry 5 }

cslbxStatsFailedServerInitConns           OBJECT-TYPE
        SYNTAX          Counter32
        UNITS           "connections"
        MAX-ACCESS      read-only
        STATUS          current
        DESCRIPTION
                "The number of server initiated connections that
                failed."
        ::= { cslbxStatsTableEntry 6 }

cslbxStatsL4PolicyConns                   OBJECT-TYPE
        SYNTAX          Counter32
        UNITS           "connections"
        MAX-ACCESS      read-only
        STATUS          current
        DESCRIPTION
                "The number of connections made to the virtual servers
                with only layer 4 configuration."
        ::= { cslbxStatsTableEntry 7 }

cslbxStatsL7PolicyConns                   OBJECT-TYPE
        SYNTAX          Counter32
        UNITS           "connections"
        MAX-ACCESS      read-only
        STATUS          current
        DESCRIPTION
                "The number of connections made to the virtual servers
                with some layer 7 configuration."
        ::= { cslbxStatsTableEntry 8 }

cslbxStatsDroppedL4PolicyConns            OBJECT-TYPE
        SYNTAX          Counter32
        UNITS           "connections"
        MAX-ACCESS      read-only
        STATUS          current
        DESCRIPTION
                "The number of connections dropped by virtual
                servers with only layer 4 configuration."
        ::= { cslbxStatsTableEntry 9 }

cslbxStatsDroppedL7PolicyConns            OBJECT-TYPE
        SYNTAX          Counter32
        UNITS           "connections"
        MAX-ACCESS      read-only
        STATUS          current
        DESCRIPTION
                "The number of connections dropped by virtual
                servers with some layer 7 policy."
        ::= { cslbxStatsTableEntry 10 }

cslbxStatsFtpConns                        OBJECT-TYPE
        SYNTAX          Counter32
        UNITS           "connections"
        MAX-ACCESS      read-only
        STATUS          current
        DESCRIPTION
                "The number of connections made to virtual servers
                with the FTP service."
        ::= { cslbxStatsTableEntry 11 }

cslbxStatsHttpRedirectConns               OBJECT-TYPE
        SYNTAX          Counter32
        UNITS           "connections"
        MAX-ACCESS      read-only
        STATUS          current
        DESCRIPTION
                "The number of connections made to HTTP
                redirect servers."
        ::= { cslbxStatsTableEntry 12 }

cslbxStatsDroppedRedirectConns            OBJECT-TYPE
        SYNTAX          Counter32
        UNITS           "connections"
        MAX-ACCESS      read-only
        STATUS          current
        DESCRIPTION
                "The number of connections dropped by HTTP
                redirect servers."
        ::= { cslbxStatsTableEntry 13 }

cslbxStatsNoMatchPolicyRejects            OBJECT-TYPE
        SYNTAX          Counter32
        UNITS           "connections"
        MAX-ACCESS      read-only
        STATUS          current
        DESCRIPTION
                "The number of connections rejected because they
                failed to match any configured policy."
        ::= { cslbxStatsTableEntry 14 }

cslbxStatsNoCfgPolicyRejects              OBJECT-TYPE
        SYNTAX          Counter32
        UNITS           "connections"
        MAX-ACCESS      read-only
        STATUS          current
        DESCRIPTION
                "The number of connections rejected because the
                matching virtual server was not configured with any
                policy."
        ::= { cslbxStatsTableEntry 15 }

cslbxStatsNoActiveServerRejects           OBJECT-TYPE
        SYNTAX          Counter32
        UNITS           "connections"
        MAX-ACCESS      read-only
        STATUS          current
        DESCRIPTION
                "The number of connections rejected because the
                chosen server farm did not have any active servers."
        ::= { cslbxStatsTableEntry 16 }

cslbxStatsAclDenyRejects                  OBJECT-TYPE
        SYNTAX          Counter32
        UNITS           "connections"
        MAX-ACCESS      read-only
        STATUS          current
        DESCRIPTION
                "The number of connections rejected because the
                the matching client access list was configured to deny
                access."
        ::= { cslbxStatsTableEntry 17 }

cslbxStatsMaxParseLenRejects              OBJECT-TYPE
        SYNTAX          Counter32
        UNITS           "connections"
        MAX-ACCESS      read-only
        STATUS          current
        DESCRIPTION
                "The number of connections rejected because the length
                of an HTTP request or response header exceeded the
                maximum L7 parse length configured for the matching
                virtual server."
        ::= { cslbxStatsTableEntry 18 }

cslbxStatsBadSslFormatRejects             OBJECT-TYPE
        SYNTAX          Counter32
        UNITS           "connections"
        MAX-ACCESS      read-only
        STATUS          current
        DESCRIPTION
                "The number of connections rejected because some
                invalid or unrecognized SSL format was detected."
        ::= { cslbxStatsTableEntry 19 }

cslbxStatsL7ParserErrorRejects            OBJECT-TYPE
        SYNTAX          Counter32
        UNITS           "connections"
        MAX-ACCESS      read-only
        STATUS          current
        DESCRIPTION
                "The number of connections rejected because an
                error occurred while parsing the connection data
                at Layer 7."
        ::= { cslbxStatsTableEntry 20 }

cslbxStatsVerMismatchRejects              OBJECT-TYPE
        SYNTAX          Counter32
        UNITS           "connections"
        MAX-ACCESS      read-only
        STATUS          current
        DESCRIPTION
                "The number of connections rejected because the
                Layer 7 configuration was changed while Layer 7
                parsing was occurring on the connection."
        ::= { cslbxStatsTableEntry 21 }


cslbxStatsOutOfMemoryRejects              OBJECT-TYPE
        SYNTAX          Counter32
        UNITS           "connections"
        MAX-ACCESS      read-only
        STATUS          current
        DESCRIPTION
                "The number of connections rejected because the
                SLB module could not allocate the required memory."
        ::= { cslbxStatsTableEntry 22 }

cslbxStatsTimedOutConnections             OBJECT-TYPE
        SYNTAX          Counter32
        UNITS           "connections"
        MAX-ACCESS      read-only
        STATUS          current
        DESCRIPTION
                "The number of connections that were terminated because
                they were idle longer than the configured idle timeout
                value."
        ::= { cslbxStatsTableEntry 23 }

cslbxStatsTcpChecksumErrorPkts            OBJECT-TYPE
        SYNTAX          Counter32
        UNITS           "packets"
        MAX-ACCESS      read-only
        STATUS          current
        DESCRIPTION
                "The accumulated number of TCP packets which have
                checksum error."
        ::= { cslbxStatsTableEntry 24 }

cslbxStatsIpChecksumErrorPkts             OBJECT-TYPE
        SYNTAX          Counter32
        UNITS           "packets"
        MAX-ACCESS      read-only
        STATUS          current
        DESCRIPTION
                "The accumulated number of IP packets which have
                checksum error."
        ::= { cslbxStatsTableEntry 25 }


--  *************************************************************
--  *                                                           *
--  * SLB-EXT - Server Farm Table                               *
--  *                                                           *
--  *************************************************************

cslbxServerFarmTable                              OBJECT-TYPE
        SYNTAX          SEQUENCE OF CslbxServerFarmTableEntry
        MAX-ACCESS      not-accessible
        STATUS          current
        DESCRIPTION
                "This is a table of server farms, each of which is a
                group of real servers to be used by SLB for load
                balancing.  It contains additional configurations to
                the slbSeverFarmTable."
        ::= { cslbxServerFarms 1 }

cslbxServerFarmTableEntry                         OBJECT-TYPE
        SYNTAX          CslbxServerFarmTableEntry
        MAX-ACCESS      not-accessible
        STATUS          current
        DESCRIPTION
                "Additional configuration parameters about a
                particular server farm served by a particular
                local SLB entity."
        AUGMENTS        { slbServerFarmTableEntry }
        ::= { cslbxServerFarmTable 1 }

CslbxServerFarmTableEntry ::= SEQUENCE {
        cslbxServerFarmHashMaskAddrType           InetAddressType,
        cslbxServerFarmHashMaskAddr               InetAddress,
        cslbxServerFarmClientNatPool              SlbObjectNameString,
        cslbxServerFarmFailAction                 SlbFailAction,
        cslbxServerFarmHttpReturnCodeMap          SlbObjectNameString,
        cslbxServerFarmInFailedThreshold          Unsigned32,
        cslbxServerFarmInbandResetTimer           TimeInterval
            
}

cslbxServerFarmHashMaskAddrType           OBJECT-TYPE
        SYNTAX          InetAddressType
        MAX-ACCESS      read-create
        STATUS          current
        DESCRIPTION
                "The type of address stored in
                 cslbxServerFarmHashMaskAddr."
        DEFVAL          { ipv4 }
        ::= { cslbxServerFarmTableEntry 1 }

cslbxServerFarmHashMaskAddr               OBJECT-TYPE
        SYNTAX          InetAddress (SIZE (0..20))
        MAX-ACCESS      read-create
        STATUS          current
        DESCRIPTION
                "The mask value applied to the IP address before
                performing IP hashing operation."
        DEFVAL          { 'ffffffff'H } -- 255.255.255.255
        ::= { cslbxServerFarmTableEntry 2 }

cslbxServerFarmClientNatPool              OBJECT-TYPE
        SYNTAX          SlbObjectNameString
        MAX-ACCESS      read-create
        STATUS          current
        DESCRIPTION
                "The name of the current client NAT pool associated
                with this server farm."
        DEFVAL          { "" }
        ::= { cslbxServerFarmTableEntry 3 }

cslbxServerFarmFailAction                 OBJECT-TYPE
        SYNTAX          SlbFailAction
        MAX-ACCESS      read-create
        STATUS          current
        DESCRIPTION
                "The current action assigned to this server farm when
                a server has failed ARP or health probe."
        DEFVAL          { noAction }
        ::= { cslbxServerFarmTableEntry 4 }

cslbxServerFarmHttpReturnCodeMap          OBJECT-TYPE
        SYNTAX          SlbObjectNameString
        MAX-ACCESS      read-create
        STATUS          current
        DESCRIPTION
                "The name of the HTTP return code checking applied
                to with this server farm."
        DEFVAL          { "" }
        ::= { cslbxServerFarmTableEntry 5 }

cslbxServerFarmInFailedThreshold          OBJECT-TYPE
        SYNTAX          Unsigned32
        MAX-ACCESS      read-create
        STATUS          current
        DESCRIPTION
                "The threshold of failed connections before the 
                inband health check taking a server in this farm
                out-of-service."
        DEFVAL          { 4294967295 }
        ::= { cslbxServerFarmTableEntry 6 }

cslbxServerFarmInbandResetTimer           OBJECT-TYPE
        SYNTAX          TimeInterval
        MAX-ACCESS      read-create
        STATUS          current
        DESCRIPTION
                "The wait time interval before the inband health check
                reset a failed server to enable state.  The value of
                zero indicates failed state will never reset."
        DEFVAL          { 0 }
        ::= { cslbxServerFarmTableEntry 7 }


--  *************************************************************
--  *                                                           *
--  * SLB-EXT - HTTP Redirect Server Table                      *
--  *                                                           *
--  *************************************************************
 
cslbxRedirectSvrTable                     OBJECT-TYPE
        SYNTAX          SEQUENCE OF CslbxRedirectSvrTableEntry
        MAX-ACCESS      not-accessible
        STATUS          current
        DESCRIPTION
                "A table of HTTP redirect servers.  Entry attributes
                may be modified regardless of the value of
                cslbxRedirectSvrState."
        ::= { cslbxServerFarms 2 }
 
cslbxRedirectSvrTableEntry                OBJECT-TYPE
         SYNTAX          CslbxRedirectSvrTableEntry
         MAX-ACCESS      not-accessible
         STATUS          current
         DESCRIPTION
                 "Information about a particular HTTP redirect
                 virtual server in a particular server farm
                 served by a particular local SLB entity."
         INDEX   {
                 slbEntity,
                 cslbxRedirectSvrFarmName,
                 cslbxRedirectSvrName
         }
         ::= { cslbxRedirectSvrTable 1 }
 
CslbxRedirectSvrTableEntry ::= SEQUENCE {
         cslbxRedirectSvrFarmName                 SlbServerString,
         cslbxRedirectSvrName                     SlbServerString,
         cslbxRedirectSvrRelocationStr            SlbUrlString,
         cslbxRedirectSvrBackupString             SlbUrlString,
         cslbxRedirectSvrRedirectCode             Unsigned32,
         cslbxRedirectSvrRedirectPort             CiscoPort,
         cslbxRedirectSvrState                    SlbRealServerState,
         cslbxRedirectSvrNumberOfConns            Gauge32,
         cslbxRedirectSvrMaxConns                 Unsigned32,
         cslbxRedirectSvrAdminWeight              Unsigned32,
         cslbxRedirectSvrOperWeight               Gauge32,
         cslbxRedirectSvrMetric                   Unsigned32,
         cslbxRedirectSvrTotalConns               Counter32,
         cslbxRedirectSvrHCTotalConns             Counter64,
         cslbxRedirectSvrRowStatus                RowStatus
}
 
cslbxRedirectSvrFarmName               OBJECT-TYPE
         SYNTAX          SlbServerString
         MAX-ACCESS      not-accessible
         STATUS          current
         DESCRIPTION
                 "Redirect Server's server farm name."
         ::= { cslbxRedirectSvrTableEntry 1 }

cslbxRedirectSvrName                   OBJECT-TYPE
         SYNTAX          SlbServerString
         MAX-ACCESS      not-accessible
         STATUS          current
         DESCRIPTION
                 "The name of the Redirect Server"
         ::= { cslbxRedirectSvrTableEntry 2 }

cslbxRedirectSvrRelocationStr          OBJECT-TYPE
        SYNTAX          SlbUrlString
        MAX-ACCESS      read-create
        STATUS          current
        DESCRIPTION
                "The relocation URL string sent in the reply
                of the Redirect Server."
        ::= { cslbxRedirectSvrTableEntry 3 }

cslbxRedirectSvrBackupString           OBJECT-TYPE
        SYNTAX          SlbUrlString
        MAX-ACCESS      read-create
        STATUS          current
        DESCRIPTION
                "The backup string sent in the reply of the
                Redirect Server when the associated real server
                is disabled."
        ::= { cslbxRedirectSvrTableEntry 4 }

cslbxRedirectSvrRedirectCode           OBJECT-TYPE
        SYNTAX          Unsigned32
        MAX-ACCESS      read-create
        STATUS          current
        DESCRIPTION
                "The HTTP response code sent in the reply by
                the Redirect Server."
        DEFVAL          { 302 }
        ::= { cslbxRedirectSvrTableEntry 5 }

cslbxRedirectSvrRedirectPort           OBJECT-TYPE
        SYNTAX          CiscoPort
        MAX-ACCESS      read-create
        STATUS          current
        DESCRIPTION
                "The TCP port in the HTTP response sent by
                the Redirect Server.  Instead of the original
                HTTP port (80), the Redirect Server can tell
                the client to use a different port (like HTTPS)
                when connection to the redirected URL
                destination."
        DEFVAL          { 80 }
        ::= { cslbxRedirectSvrTableEntry 6 }

cslbxRedirectSvrState                  OBJECT-TYPE
        SYNTAX          SlbRealServerState
        MAX-ACCESS      read-create
        STATUS          current
        DESCRIPTION
                "The current state of the Redirect Server."
        DEFVAL          { outOfService }
        ::= { cslbxRedirectSvrTableEntry 7 }

cslbxRedirectSvrNumberOfConns          OBJECT-TYPE
        SYNTAX          Gauge32
        MAX-ACCESS      read-only
        STATUS          current
        DESCRIPTION
                "The number TCP and UDP connections currently open
                on this Redirect Server."
        ::= { cslbxRedirectSvrTableEntry 8 }

cslbxRedirectSvrMaxConns               OBJECT-TYPE
        SYNTAX          Unsigned32
        MAX-ACCESS      read-create
        STATUS          current
        DESCRIPTION
                "The maximum number of concurrent open connections
                the SLB will allow on this Redirect Server."
        DEFVAL          { 4294967295 }
        ::= { cslbxRedirectSvrTableEntry 9 }

cslbxRedirectSvrAdminWeight            OBJECT-TYPE
        SYNTAX          Unsigned32 ( 0..65535 )
        MAX-ACCESS      read-create
        STATUS          current
        DESCRIPTION
                "The user configured weight of the Redirect Server
                for the load-balancing algorithms.  A weight of zero
                indicates that no new connections will be assigned
                to this Redirect Server.  Higher weight values
                indicate to the load-balancing algorithms a higher
                availability of this Redirect Server to accept more
                work."
        DEFVAL          { 8 }
        ::= { cslbxRedirectSvrTableEntry 10 }

cslbxRedirectSvrOperWeight             OBJECT-TYPE
        SYNTAX          Gauge32
        MAX-ACCESS      read-only
        STATUS          current
        DESCRIPTION
                "The actual operating weight of the Redirect Server
                used by the load-balancing algorithms.  This can be
                adjusted dynamically by DFP.  A weight of zero
                indicates that no new connections will be assigned
                to this Redirect Server.  Higher weight values 
                indicate to the load-balancing algorithms a higher
                availability of this Redirect Server to accept more
                work."
        ::= { cslbxRedirectSvrTableEntry 11 }

cslbxRedirectSvrMetric                 OBJECT-TYPE
        SYNTAX          Unsigned32
        MAX-ACCESS      read-only
        STATUS          current
        DESCRIPTION
                "The value used by the least connections load-balancing
                algorithm.  It is the number of connections divided by
                the actual operating weight.  New connections will be
                given to the server with the smaller metric."
        ::= { cslbxRedirectSvrTableEntry 12 }

cslbxRedirectSvrTotalConns             OBJECT-TYPE
        SYNTAX          Counter32
        MAX-ACCESS      read-only
        STATUS          current
        DESCRIPTION
                "The total number of connections assigned to this
                Redirect Server since this server was configured."
        ::= { cslbxRedirectSvrTableEntry 13 }

cslbxRedirectSvrHCTotalConns           OBJECT-TYPE
        SYNTAX          Counter64
        MAX-ACCESS      read-only
        STATUS          current
        DESCRIPTION
                "The total number of connections assigned to this
                Redirect Server since this server was configured.
                This is the 64-bit version of
                cslbxRedirectSvrTotalConnections."
        ::= { cslbxRedirectSvrTableEntry 14 }

cslbxRedirectSvrRowStatus              OBJECT-TYPE
        SYNTAX          RowStatus
        MAX-ACCESS      read-create
        STATUS          current
        DESCRIPTION
                "The object used by a management station to create
                or delete the row entry in cslbxRedirectSvrTable
                following the RowStatus textual convention."
        ::= { cslbxRedirectSvrTableEntry 15 }


--  *************************************************************
--  *                                                           *
--  * SLB-EXT - Server Farm Probe Table                         *
--  *                                                           *
--  *************************************************************

cslbxServerFarmProbeTable                 OBJECT-TYPE
        SYNTAX          SEQUENCE OF CslbxServerFarmProbeTableEntry
        MAX-ACCESS      not-accessible
        STATUS          current
        DESCRIPTION
                "This is a table of probes in the server farms."
        ::= { cslbxServerFarms 3 }

cslbxServerFarmProbeTableEntry            OBJECT-TYPE
        SYNTAX          CslbxServerFarmProbeTableEntry
        MAX-ACCESS      not-accessible
        STATUS          current
        DESCRIPTION
                "Information about a particular probe associated with
                a particular server farm, served by a particular local
                SLB entity."
        INDEX   {
                slbEntity,
                cslbxServerFarmProbeFarmName,
                cslbxServerFarmProbeProbeName
        }
        ::= { cslbxServerFarmProbeTable 1 }

CslbxServerFarmProbeTableEntry ::= SEQUENCE {
        cslbxServerFarmProbeFarmName              SlbServerString,
        cslbxServerFarmProbeProbeName             SlbServerString,
        cslbxServerFarmProbeRowStatus             RowStatus            
}

cslbxServerFarmProbeFarmName              OBJECT-TYPE
        SYNTAX          SlbServerString
        MAX-ACCESS      not-accessible
        STATUS          current
        DESCRIPTION
                "The name the server farm."
        ::= { cslbxServerFarmProbeTableEntry 1 }

cslbxServerFarmProbeProbeName             OBJECT-TYPE
        SYNTAX          SlbServerString
        MAX-ACCESS      not-accessible
        STATUS          current
        DESCRIPTION
                "The name of probe."
        ::= { cslbxServerFarmProbeTableEntry 2 }

cslbxServerFarmProbeRowStatus             OBJECT-TYPE
        SYNTAX          RowStatus
        MAX-ACCESS      read-create
        STATUS          current
        DESCRIPTION
                "The object is used by a management station to create
                or delete the row entry in cslbxServerFarmProbeTable
                following the RowStatus textual convention."
        ::= { cslbxServerFarmProbeTableEntry 3 }


--  *************************************************************
--  *                                                           *
--  * SLB-EXT - IP NAT Pool Table                               *
--  *                                                           *
--  *************************************************************

cslbxNatPoolTable                         OBJECT-TYPE
        SYNTAX          SEQUENCE OF CslbxNatPoolEntry
        MAX-ACCESS      not-accessible
        STATUS          current
        DESCRIPTION
                "A table of IP NAT pools."
        ::= { cslbxClientNatPools 1 }

cslbxNatPoolEntry                         OBJECT-TYPE
        SYNTAX          CslbxNatPoolEntry
        MAX-ACCESS      not-accessible
        STATUS          current
        DESCRIPTION
                 "Information about a particular NAT pool
                 served by a particular local SLB entity."
        INDEX   { 
                slbEntity, 
                cslbxNatPoolName 
        }
        ::= { cslbxNatPoolTable 1 }

CslbxNatPoolEntry ::= SEQUENCE {
        cslbxNatPoolName                          SlbServerString,
        cslbxNatPoolStartAddressType              InetAddressType,
        cslbxNatPoolStartAddress                  InetAddress,
        cslbxNatPoolEndAddressType                InetAddressType,
        cslbxNatPoolEndAddress                    InetAddress,
        cslbxNatPoolRowStatus                     RowStatus
}

cslbxNatPoolName                          OBJECT-TYPE
        SYNTAX          SlbServerString
        MAX-ACCESS      not-accessible
        STATUS          current
        DESCRIPTION
                "The name of the NAT pool."
        ::= { cslbxNatPoolEntry 1 }

cslbxNatPoolStartAddressType              OBJECT-TYPE
        SYNTAX          InetAddressType
        MAX-ACCESS      read-create
        STATUS          current
        DESCRIPTION
                "The type of address stored in
                cslbxNatPoolStartAddress."
        DEFVAL          { ipv4 }
        ::= { cslbxNatPoolEntry 2 }

cslbxNatPoolStartAddress                  OBJECT-TYPE
        SYNTAX          InetAddress (SIZE (0..20))
        MAX-ACCESS      read-create
        STATUS          current
        DESCRIPTION
                "The first IP address in this NAT pool."
        DEFVAL          { '00000000'H } -- 0.0.0.0
        ::= { cslbxNatPoolEntry 3 }

cslbxNatPoolEndAddressType                OBJECT-TYPE
        SYNTAX          InetAddressType
        MAX-ACCESS      read-create
        STATUS          current
        DESCRIPTION
                "The type of address stored in
                cslbxNatPoolEndAddress."
        DEFVAL          { ipv4 }
        ::= { cslbxNatPoolEntry 4 }

cslbxNatPoolEndAddress                    OBJECT-TYPE
        SYNTAX          InetAddress (SIZE (0..20))
        MAX-ACCESS      read-create
        STATUS          current
        DESCRIPTION
                "The last IP address in this NAT pool."
        DEFVAL          { '00000000'H } -- 0.0.0.0
        ::= { cslbxNatPoolEntry 5 }

cslbxNatPoolRowStatus                     OBJECT-TYPE
        SYNTAX          RowStatus
        MAX-ACCESS      read-create
        STATUS          current
        DESCRIPTION
                "The object is used by a management station to create
                or delete the row entry in cslbxNatPoolTable following
                the RowStatus textual convention."
        ::= { cslbxNatPoolEntry 6 }


--  *************************************************************
--  *                                                           *
--  * SLB-EXT - Sticky Group Table                              *
--  *                                                           *
--  *************************************************************

cslbxStickyGroupTable                     OBJECT-TYPE
        SYNTAX          SEQUENCE OF CslbxStickyGroupEntry
        MAX-ACCESS      not-accessible
        STATUS          current
        DESCRIPTION
                "A table of Sticky Groups."
        ::= { cslbxStickyObjects 1 }

cslbxStickyGroupEntry                     OBJECT-TYPE
        SYNTAX          CslbxStickyGroupEntry
        MAX-ACCESS      not-accessible
        STATUS          current
        DESCRIPTION
                 "Information about a particular Sticky Group
                 served by a particular local SLB entity."
        INDEX   { 
                slbEntity, 
                cslbxStickyGroupId 
        }
        ::= { cslbxStickyGroupTable 1 }

CslbxStickyGroupEntry ::= SEQUENCE {
        cslbxStickyGroupId                        Unsigned32,
        cslbxStickyGroupType                      SlbStickyType,
        cslbxStickyGroupMaskAddressType           InetAddressType,
        cslbxStickyGroupMaskAddress               InetAddress,
        cslbxStickyGroupCookieName                SnmpAdminString,
        cslbxStickyGroupStickyTimer               Unsigned32,
        cslbxStickyGroupRowStatus                 RowStatus
}

cslbxStickyGroupId                        OBJECT-TYPE
        SYNTAX          Unsigned32
        MAX-ACCESS      not-accessible
        STATUS          current
        DESCRIPTION
                "This Sticky Group's ID."
        ::= { cslbxStickyGroupEntry 1 }

cslbxStickyGroupType                      OBJECT-TYPE
        SYNTAX          SlbStickyType
        MAX-ACCESS      read-create
        STATUS          current
        DESCRIPTION
                "This Sticky Group's type."
        ::= { cslbxStickyGroupEntry 2 }

cslbxStickyGroupMaskAddressType           OBJECT-TYPE
        SYNTAX          InetAddressType
        MAX-ACCESS      read-create
        STATUS          current
        DESCRIPTION
                "The type of address stored in
                cslbxStickyGroupMaskAddress."
        DEFVAL          { ipv4 }
        ::= { cslbxStickyGroupEntry 3 }

cslbxStickyGroupMaskAddress               OBJECT-TYPE
        SYNTAX          InetAddress (SIZE (0..20))
        MAX-ACCESS      read-create
        STATUS          current
        DESCRIPTION
                "The network mask used with the ipSticky type.  The
                source IP address will be AND'ed with this mask before
                inserting into the sticky database."
        DEFVAL          { 'ffffffff'H } -- 255.255.255.255
        ::= { cslbxStickyGroupEntry 4 }

cslbxStickyGroupCookieName                OBJECT-TYPE
        SYNTAX          SnmpAdminString (SIZE(0..64))
        MAX-ACCESS      read-create
        STATUS          current
        DESCRIPTION
                "The HTTP Cookie name used with httpCookieSticky
                type."
        ::= { cslbxStickyGroupEntry 5 }

cslbxStickyGroupStickyTimer               OBJECT-TYPE
        SYNTAX          Unsigned32
        UNITS           "minutes"
        MAX-ACCESS      read-create
        STATUS          current
        DESCRIPTION
                "The length of time a Sticky Group may exist before
                 being automatically removed."
        ::= { cslbxStickyGroupEntry 6 }

cslbxStickyGroupRowStatus                 OBJECT-TYPE
        SYNTAX          RowStatus
        MAX-ACCESS      read-create
        STATUS          current
        DESCRIPTION
                "The row status is used by a management station to
                create or delete the row entry in
                cslbxStickyGroupTable following the RowStatus
                textual convention."
        ::= { cslbxStickyGroupEntry 7 }


--  *************************************************************
--  *                                                           *
--  * SLB-EXT - Sticky Object Table                             *
--  *                                                           *
--  *************************************************************

cslbxStickyObjectTable                    OBJECT-TYPE
        SYNTAX          SEQUENCE OF CslbxStickyObjectTableEntry
        MAX-ACCESS      not-accessible
        STATUS          current
        DESCRIPTION
                "Table of existing sticky entries.  Sticky entries
                allow related connections to be sent to the same
                real server on a per client basis. This table
                supports the Content Switching Module (CSM) feature
                which is not supported by the slbStickyObjectTable
                in the CISCO-SLB-MIB."
        ::= { cslbxStickyObjects 2 }

cslbxStickyObjectTableEntry               OBJECT-TYPE
        SYNTAX          CslbxStickyObjectTableEntry
        MAX-ACCESS      not-accessible
        STATUS          current
        DESCRIPTION
                "Information about a particular sticky entry by a
                particular local SLB entity."
        INDEX   {
                slbEntity,
                cslbxStickyObjectIndex
        }
        ::= { cslbxStickyObjectTable 1 }

CslbxStickyObjectTableEntry ::= SEQUENCE {
        cslbxStickyObjectIndex                    Unsigned32,
        cslbxStickyObjectGroupId                  Unsigned32,
        cslbxStickyObjectType                     SlbStickyType,
        cslbxStickyObjectSourceInfo               Unsigned32,
        cslbxStickyObjectRealAddressType          InetAddressType,
        cslbxStickyObjectRealAddress              InetAddress,
        cslbxStickyObjectRealPort                 CiscoPort
}

cslbxStickyObjectIndex                    OBJECT-TYPE
        SYNTAX          Unsigned32
        MAX-ACCESS      not-accessible
        STATUS          current
        DESCRIPTION
                "The sticky entry index."
        ::= { cslbxStickyObjectTableEntry 1 }

cslbxStickyObjectGroupId                  OBJECT-TYPE
        SYNTAX          Unsigned32
        MAX-ACCESS      read-only
        STATUS          current
        DESCRIPTION
                "The group ID associated with this sticky entry."
        ::= { cslbxStickyObjectTableEntry 2 }

cslbxStickyObjectType                     OBJECT-TYPE
        SYNTAX          SlbStickyType
        MAX-ACCESS      read-only
        STATUS          current
        DESCRIPTION
                "The sticky type of this sticky entry."
        ::= { cslbxStickyObjectTableEntry 3 }

cslbxStickyObjectSourceInfo               OBJECT-TYPE
        SYNTAX          Unsigned32
        MAX-ACCESS      read-only
        STATUS          current
        DESCRIPTION
                "The client IP address or hashed of source data used
                created this sticky entry."
        ::= { cslbxStickyObjectTableEntry 4 }

cslbxStickyObjectRealAddressType          OBJECT-TYPE
        SYNTAX          InetAddressType
        MAX-ACCESS      read-only
        STATUS          current
        DESCRIPTION
                "The type of address stored in
                cslbxStickyObjectRealAddress."
        ::= { cslbxStickyObjectTableEntry 5 }

cslbxStickyObjectRealAddress              OBJECT-TYPE
        SYNTAX          InetAddress (SIZE (0..20))
        MAX-ACCESS      read-only
        STATUS          current
        DESCRIPTION
                "The real server IP address selected for all clients
                matched this sticky entry."
        ::= { cslbxStickyObjectTableEntry 6 }

cslbxStickyObjectRealPort                 OBJECT-TYPE
        SYNTAX          CiscoPort
        MAX-ACCESS      read-only
        STATUS          current
        DESCRIPTION
                "The port number of the real server associated with
                this sticky entry."
        ::= { cslbxStickyObjectTableEntry 7 }


--  *************************************************************
--  *                                                           *
--  * SLB-EXT - Map Table                                       *
--  *                                                           *
--  *************************************************************

cslbxMapTable                             OBJECT-TYPE
        SYNTAX          SEQUENCE OF CslbxMapTableEntry
        MAX-ACCESS      not-accessible
        STATUS          current
        DESCRIPTION
                "Table of SLB map groups.  A SLB map group contains
                a list of matching criteria."
        ::= { cslbxMaps 1 }

cslbxMapTableEntry                        OBJECT-TYPE
        SYNTAX          CslbxMapTableEntry
        MAX-ACCESS      not-accessible
        STATUS          current
        DESCRIPTION
                "Information about a particular map group,
                served by a particular local SLB entity."
        INDEX   {
                slbEntity,
                cslbxMapName
        }
        ::= { cslbxMapTable 1 }

CslbxMapTableEntry ::= SEQUENCE {
        cslbxMapName                              SlbServerString,
        cslbxMapType                              SlbMapType,
        cslbxMapRowStatus                         RowStatus
}

cslbxMapName                              OBJECT-TYPE
        SYNTAX          SlbServerString
        MAX-ACCESS      not-accessible
        STATUS          current
        DESCRIPTION
                "The name of the map group."
        ::= { cslbxMapTableEntry 1 }

cslbxMapType                              OBJECT-TYPE
        SYNTAX          SlbMapType
        MAX-ACCESS      read-create
        STATUS          current
        DESCRIPTION
                "The type of the map group."
        DEFVAL          { notCfgMap }
        ::= { cslbxMapTableEntry 2 }

cslbxMapRowStatus                         OBJECT-TYPE
        SYNTAX          RowStatus
        MAX-ACCESS      read-create
        STATUS          current
        DESCRIPTION
                "The object used by a management station to create
                or delete the row entry in cslbxMapTable
                following the RowStatus textual convention."
        ::= { cslbxMapTableEntry 3 }


--  *************************************************************
--  *                                                           *
--  * SLB-EXT - HTTP Regular Expression Table                   *
--  *                                                           *
--  *************************************************************

cslbxHttpExpressionTable                  OBJECT-TYPE
        SYNTAX          SEQUENCE OF CslbxHttpExpressionTableEntry
        MAX-ACCESS      not-accessible
        STATUS          current
        DESCRIPTION
                "Table of HTTP field and regular expressions."
        ::= { cslbxMaps 2 }

cslbxHttpExpressionTableEntry             OBJECT-TYPE
        SYNTAX          CslbxHttpExpressionTableEntry
        MAX-ACCESS      not-accessible
        STATUS          current
        DESCRIPTION
                "Information about a particular HTTP field and
                the regular expression in a particular map group,
                served by a particular local SLB entity."
        INDEX   {
                slbEntity,
                cslbxHttpExpressionMapName,
                cslbxHttpExpressionIndex
        }
        ::= { cslbxHttpExpressionTable 1 }

CslbxHttpExpressionTableEntry ::= SEQUENCE {
        cslbxHttpExpressionMapName                SlbServerString,
        cslbxHttpExpressionIndex                  Unsigned32,
        cslbxHttpExpressionFieldName              SlbRegularExpression,
        cslbxHttpExpressionValue                  SlbRegularExpression,
        cslbxHttpExpressionRowStatus              RowStatus
}

cslbxHttpExpressionMapName                OBJECT-TYPE
        SYNTAX          SlbServerString
        MAX-ACCESS      not-accessible
        STATUS          current
        DESCRIPTION
                "The name of the Map containing this entry.
                This entry is only valid for cslbxMapType of:
                'urlMap', 'cookieMap', or 'headerMap'."
        ::= { cslbxHttpExpressionTableEntry 1 }

cslbxHttpExpressionIndex                 OBJECT-TYPE
        SYNTAX          Unsigned32
        MAX-ACCESS      not-accessible
        STATUS          current
        DESCRIPTION
                "The index of this item within a Map group."
        ::= { cslbxHttpExpressionTableEntry 2 }

cslbxHttpExpressionFieldName             OBJECT-TYPE
        SYNTAX          SlbRegularExpression
        MAX-ACCESS      read-create
        STATUS          current
        DESCRIPTION
                "The HTTP Cookie Name or Header Name.  The SLB device
                will parse the HTTP packets for this field name.  This
                object is not used for the Map type of 'urlMap', since
                there is only one HTTP URL field in a HTTP request."
        ::= { cslbxHttpExpressionTableEntry 3 }

cslbxHttpExpressionValue                 OBJECT-TYPE
        SYNTAX          SlbRegularExpression
        MAX-ACCESS      read-create
        STATUS          current
        DESCRIPTION
                "The regular expression to match against a HTTP URL,
                Cookie, or Header field."
        ::= { cslbxHttpExpressionTableEntry 4 }

cslbxHttpExpressionRowStatus              OBJECT-TYPE
        SYNTAX          RowStatus
        MAX-ACCESS      read-create
        STATUS          current
        DESCRIPTION
                "The object used by a management station to create
                or delete the row entry in cslbxHttpExpressionTable
                following the RowStatus textual convention."
        ::= { cslbxHttpExpressionTableEntry 5 }


--  *************************************************************
--  *                                                           *
--  * SLB-EXT - ReturnCode Action Rule Table                    *
--  *                                                           *
--  *************************************************************

cslbxHttpReturnCodeTable                  OBJECT-TYPE
        SYNTAX          SEQUENCE OF CslbxHttpReturnCodeEntry
        MAX-ACCESS      not-accessible
        STATUS          current
        DESCRIPTION
                "Table of rules associating ReturnCode maps and
                intervals of HTTP return codes with actions to
                perform when particular HTTP return codes are seen
                in the data stream."
        ::= { cslbxMaps 3 }

cslbxHttpReturnCodeEntry                  OBJECT-TYPE
        SYNTAX          CslbxHttpReturnCodeEntry
        MAX-ACCESS      not-accessible
        STATUS          current
        DESCRIPTION
                "Information about the particular action rule in a
                particular map of type 'returnCodeMap' dealing with
                a particular range of HTTP return codes, served by a
                particular local SLB entity."
        INDEX   {
                slbEntity,
                cslbxHttpReturnCodeMapName,
                cslbxHttpReturnCodeMinValue
        }
        ::= { cslbxHttpReturnCodeTable 1 }

CslbxHttpReturnCodeEntry ::= SEQUENCE {
        cslbxHttpReturnCodeMapName                SlbServerString,
        cslbxHttpReturnCodeMinValue               Unsigned32,
        cslbxHttpReturnCodeMaxValue               Unsigned32,
        cslbxHttpReturnCodeThreshold              Unsigned32,
        cslbxHttpReturnCodeResetTimer             TimeInterval,
        cslbxHttpReturnCodeType                   SlbProbeAction,
        cslbxHttpReturnCodeRowStatus              RowStatus
}

cslbxHttpReturnCodeMapName                OBJECT-TYPE
        SYNTAX          SlbServerString
        MAX-ACCESS      not-accessible
        STATUS          current
        DESCRIPTION
                "The name of the ReturnCode map containing this action
                rule."
        ::= { cslbxHttpReturnCodeEntry 1 }

cslbxHttpReturnCodeMinValue               OBJECT-TYPE
        SYNTAX          Unsigned32
        MAX-ACCESS      not-accessible
        STATUS          current
        DESCRIPTION
                "The minimum HTTP return code that this rule matches."
        ::= { cslbxHttpReturnCodeEntry 2 }

cslbxHttpReturnCodeMaxValue               OBJECT-TYPE
        SYNTAX          Unsigned32
        MAX-ACCESS      read-create
        STATUS          current
        DESCRIPTION
                "The maximum HTTP return code that this rule matches."
        DEFVAL          { 0 }
        ::= { cslbxHttpReturnCodeEntry 3 }

cslbxHttpReturnCodeThreshold              OBJECT-TYPE
        SYNTAX          Unsigned32
        MAX-ACCESS      read-create
        STATUS          current
        DESCRIPTION
                "The number of times the return code seen before the
                action taking place.  Once HTTP return codes between
                cslbxHttpReturnCodeMinValue and
                cslbxHttpReturnCodeMaxValue, inclusive, have
                been seen at least cslbxHttpReturnCodeThreshold
                times, the action specified by
                cslbxHttpReturnCodeType is taken.  The value
                of zero indicates this object has not been set."
        DEFVAL          { 0 }
        ::= { cslbxHttpReturnCodeEntry 4 }

cslbxHttpReturnCodeResetTimer             OBJECT-TYPE
        SYNTAX          TimeInterval
        MAX-ACCESS      read-create
        STATUS          current
        DESCRIPTION
                "The time interval before resetting the state of the
                real server.  Once the action associated with this
                rule is taken, the associated real server state is
                reset after cslbxHttpReturnCodeResetTimer.
                The value of zero indicates the state will never
                reset."
        DEFVAL          { 0 }
        ::= { cslbxHttpReturnCodeEntry 5 }

cslbxHttpReturnCodeType                   OBJECT-TYPE
        SYNTAX          SlbProbeAction
        MAX-ACCESS      read-create
        STATUS          current
        DESCRIPTION
                "The action associated with this rule."
        DEFVAL          { noAction }
        ::= { cslbxHttpReturnCodeEntry 6 }

cslbxHttpReturnCodeRowStatus              OBJECT-TYPE
        SYNTAX          RowStatus
        MAX-ACCESS      read-create
        STATUS          current
        DESCRIPTION
                "The object used by a management station to create
                or delete the row entry in
                cslbxHttpReturnCodeTable following the
                RowStatus textual convention."
        ::= { cslbxHttpReturnCodeEntry 7 }


--  *************************************************************
--  *                                                           *
--  * SLB-EXT - Probe Configuration Table                       *
--  *                                                           *
--  *************************************************************

cslbxProbeCfgTable                        OBJECT-TYPE
        SYNTAX          SEQUENCE OF CslbxProbeCfgEntry
        MAX-ACCESS      not-accessible
        STATUS          current
        DESCRIPTION
                "The probing function monitors the health of
                real servers.  The SLB device actively probes
                real servers to determine if they are healthy.  
                This table is for configuring the parameters
                of probes."
        ::= { cslbxServerProbes 1 }

cslbxProbeCfgEntry                        OBJECT-TYPE
        SYNTAX          CslbxProbeCfgEntry
        MAX-ACCESS      not-accessible
        STATUS          current
        DESCRIPTION
                "This entry provides the basic configuration of a
                probe of a particular name, served by a particular
                SLB entity. This entry may be of any probe type."
        INDEX   {
                slbEntity, 
                cslbxProbeName 
        }
        ::= { cslbxProbeCfgTable 1 }

CslbxProbeCfgEntry  ::= SEQUENCE {
        cslbxProbeName                            SlbServerString,
        cslbxProbeType                            SlbProbeType,
        cslbxProbeInterval                        TimeInterval,
        cslbxProbeRetries                         Unsigned32,
        cslbxProbeFailedInterval                  TimeInterval,
        cslbxProbeReceiveTimeout                  TimeInterval,
        cslbxProbeTcpOpenTimeout                  TimeInterval,
        cslbxProbeAlternateDestAddrType           InetAddressType,
        cslbxProbeAlternateDestAddr               InetAddress,
        cslbxProbeDnsDomainName                   SnmpAdminString,
        cslbxProbeHttpRequestMethod               SnmpAdminString,
        cslbxProbeHttpRequestUrl                  SlbUrlString,
        cslbxProbeRowStatus                       RowStatus
}

cslbxProbeName                            OBJECT-TYPE
        SYNTAX          SlbServerString
        MAX-ACCESS      not-accessible
        STATUS          current
        DESCRIPTION
                "The name of the probe."
        ::= { cslbxProbeCfgEntry 1 }

cslbxProbeType                            OBJECT-TYPE
        SYNTAX          SlbProbeType
        MAX-ACCESS      read-create
        STATUS          current
        DESCRIPTION
                "The type of probe."
        ::= { cslbxProbeCfgEntry 2 }

cslbxProbeInterval                        OBJECT-TYPE
        SYNTAX          TimeInterval
        MAX-ACCESS      read-create
        STATUS          current
        DESCRIPTION
                "Time between health checks.  It is from the end of
                previous check to the beginning of the next check."
        DEFVAL { 12000 }
        ::= { cslbxProbeCfgEntry 3 }

cslbxProbeRetries                         OBJECT-TYPE
        SYNTAX          Unsigned32
        MAX-ACCESS      read-create
        STATUS          current
        DESCRIPTION
                "The number of consecutive retries without a successful
                probe before marking the real server as 'failed'."
        DEFVAL { 3 }
        ::= { cslbxProbeCfgEntry 4 }

cslbxProbeFailedInterval                  OBJECT-TYPE
        SYNTAX          TimeInterval
        MAX-ACCESS      read-create
        STATUS          current
        DESCRIPTION
                "Time before retrying a 'failed' real
                server to see if it has recovered yet."
        DEFVAL { 30000 }
        ::= { cslbxProbeCfgEntry 5 }

cslbxProbeReceiveTimeout                  OBJECT-TYPE
        SYNTAX          TimeInterval
        MAX-ACCESS      read-create
        STATUS          current
        DESCRIPTION
                "Maximum time to wait for a reply from a real
                server before considering this probe attempt
                to have failed."
        DEFVAL { 1000 }
        ::= { cslbxProbeCfgEntry 6 }

cslbxProbeTcpOpenTimeout                  OBJECT-TYPE
        SYNTAX          TimeInterval
        MAX-ACCESS      read-create
        STATUS          current
        DESCRIPTION
                "Maximum time to wait for a TCP SYN/ACK frame
                from the real server.  This entry is only valid
                for probes employing TCP, such as SMTP and HTTP
                probes."
        DEFVAL { 1000 }
        ::= { cslbxProbeCfgEntry 7 }

cslbxProbeAlternateDestAddrType           OBJECT-TYPE
        SYNTAX          InetAddressType
        MAX-ACCESS      read-create
        STATUS          current
        DESCRIPTION
                "The type of address stored in
                cslbxProbeAlternateDestAddr."
        DEFVAL { ipv4 }
        ::= { cslbxProbeCfgEntry 8 }

cslbxProbeAlternateDestAddr               OBJECT-TYPE
        SYNTAX          InetAddress (SIZE (0..20))
        MAX-ACCESS      read-create
        STATUS          current
        DESCRIPTION
                "The alternative destination IP address to be used with
                the probing packet.  Probe frames are normally sent to
                a real server IP address. If the setting is not
                '0.0.0.0', probe frames are sent to the IP address
                given by this object.  This entry is only valid with
                the ICMP probe type."
        DEFVAL { '00000000'H } -- 0.0.0.0
        ::= { cslbxProbeCfgEntry 9 }

cslbxProbeDnsDomainName                   OBJECT-TYPE
        SYNTAX          SnmpAdminString
        MAX-ACCESS      read-create
        STATUS          current
        DESCRIPTION
                "The domain name string use with the DNS probe. (Only
                applicable to DNS probes.)"
        ::= { cslbxProbeCfgEntry 10 }

cslbxProbeHttpRequestMethod               OBJECT-TYPE
        SYNTAX          SnmpAdminString (SIZE (0..64))
        MAX-ACCESS      read-create
        STATUS          current
        DESCRIPTION
                "The request method type string to be used in the
                HTTP probe packets. (Only applicable to HTTP
                probes.)"
        DEFVAL          { "get" }
        ::= { cslbxProbeCfgEntry 11 }

cslbxProbeHttpRequestUrl                  OBJECT-TYPE
        SYNTAX          SlbUrlString
        MAX-ACCESS      read-create
        STATUS          current
        DESCRIPTION
                "The URI string in the HTTP request of HTTP probe
                packets. (Only applicable to HTTP probes.)"
        DEFVAL          { "" }
        ::= { cslbxProbeCfgEntry 12 }

cslbxProbeRowStatus                       OBJECT-TYPE
        SYNTAX          RowStatus
        MAX-ACCESS      read-create
        STATUS          current
        DESCRIPTION
                "The row status is used by a management station to
                create or delete the row entry in cslbxProbeCfgTable
                following the RowStatus textual convention."
        ::= { cslbxProbeCfgEntry 13 }


--  *************************************************************
--  *                                                           *
--  * SLB-EXT - DNS Probe Expected IP Configuration Table       *
--  *                                                           *
--  *************************************************************

cslbxDnsProbeIpTable                      OBJECT-TYPE
        SYNTAX          SEQUENCE OF CslbxDnsProbeIpEntry
        MAX-ACCESS      not-accessible
        STATUS          current
        DESCRIPTION
                "The probing function monitors the health of
                real servers.  The SLB device actively probes
                real servers to determine if they are healthy.  
                This table is for configuring the parameters
                of DNS probes. In a DNS probe, resolution of a
                specific domain name is requested, and the
                resulting IP address must match one of a list of
                'expected IP addresses' configured for that
                probe. This table stores the list of expected IP
                addresses for each DNS probe."
        ::= { cslbxServerProbes 2 }

cslbxDnsProbeIpEntry                      OBJECT-TYPE
        SYNTAX          CslbxDnsProbeIpEntry
        MAX-ACCESS      not-accessible
        STATUS          current
        DESCRIPTION
                "The IP address in this entry is a valid response
                to a request for resolution of the domain name
                associated with the DNS probe in this entry."
        INDEX   {
                slbEntity, 
                cslbxDnsProbeIpProbeName,
                cslbxDnsProbeIpAddressType,
                cslbxDnsProbeIpAddress
        }
        ::= { cslbxDnsProbeIpTable 1 }

CslbxDnsProbeIpEntry  ::= SEQUENCE {
        cslbxDnsProbeIpProbeName                  SlbServerString,
        cslbxDnsProbeIpAddressType                InetAddressType,
        cslbxDnsProbeIpAddress                    InetAddress,
        cslbxDnsProbeIpRowStatus                  RowStatus
}

cslbxDnsProbeIpProbeName                  OBJECT-TYPE
        SYNTAX          SlbServerString
        MAX-ACCESS      not-accessible
        STATUS          current
        DESCRIPTION
                "The name of the DNS probe."
        ::= { cslbxDnsProbeIpEntry 1 }

cslbxDnsProbeIpAddressType                OBJECT-TYPE
        SYNTAX          InetAddressType
        MAX-ACCESS      not-accessible
        STATUS          current
        DESCRIPTION
                "The type of address stored in
                cslbxDnsProbeIpAddress."
        ::= { cslbxDnsProbeIpEntry 2 }

cslbxDnsProbeIpAddress                    OBJECT-TYPE
        SYNTAX          InetAddress (SIZE (1..20))
        MAX-ACCESS      not-accessible
        STATUS          current
        DESCRIPTION
                "The IP address that may be expected in response
                to a DNS probe from a 'healthy' real DNS server."
        ::= { cslbxDnsProbeIpEntry 3 }

cslbxDnsProbeIpRowStatus                  OBJECT-TYPE   
        SYNTAX          RowStatus
        MAX-ACCESS      read-create
        STATUS          current
        DESCRIPTION
                "The object used by a management station to create
                or delete the row entry in cslbxDnsProbeIpTable
                following the RowStatus textual convention."
        ::= { cslbxDnsProbeIpEntry 4 }


--  *************************************************************
--  *                                                           *
--  * SLB-EXT - HTTP Probe Header Table                         *
--  *                                                           *
--  *************************************************************

cslbxProbeHeaderCfgTable                  OBJECT-TYPE
        SYNTAX          SEQUENCE OF CslbxProbeHeaderCfgEntry
        MAX-ACCESS      not-accessible
        STATUS          current
        DESCRIPTION
                "The probing function monitors the health of
                real servers.  The SLB device actively probes
                real servers to determine if they are healthy.  
                This table is for configuring the parameters
                of HTTP probes. In particular, each HTTP probe
                request may be sent with a number of fixed HTTP
                headers. This table defines such fixed HTTP
                headers sent with HTTP probes."
        ::= { cslbxServerProbes 3 }

cslbxProbeHeaderCfgEntry                  OBJECT-TYPE
        SYNTAX          CslbxProbeHeaderCfgEntry
        MAX-ACCESS      not-accessible
        STATUS          current
        DESCRIPTION
                "This entry defines the HTTP header value
                of a particular HTTP header name sent with a
                particular HTTP probe, served by a particular SLB
                entity."
        INDEX   {
                slbEntity, 
                cslbxProbeHeaderProbeName,
                cslbxProbeHeaderFieldName 
        }
        ::= { cslbxProbeHeaderCfgTable 1 }

CslbxProbeHeaderCfgEntry  ::= SEQUENCE {
        cslbxProbeHeaderProbeName                 SlbServerString,
        cslbxProbeHeaderFieldName                 SnmpAdminString,
        cslbxProbeHeaderFieldValue                SnmpAdminString,
        cslbxProbeHeaderRowStatus                 RowStatus
}

cslbxProbeHeaderProbeName                 OBJECT-TYPE
        SYNTAX          SlbServerString
        MAX-ACCESS      not-accessible
        STATUS          current
        DESCRIPTION
                "The name of the HTTP probe."
        ::= { cslbxProbeHeaderCfgEntry 1 }

cslbxProbeHeaderFieldName                 OBJECT-TYPE
        SYNTAX          SnmpAdminString (SIZE (1..64))
        MAX-ACCESS      not-accessible
        STATUS          current
        DESCRIPTION
                "An HTTP header of this name is transmitted in the
                HTTP request sent by this probe."
        ::= { cslbxProbeHeaderCfgEntry 2 }

cslbxProbeHeaderFieldValue                OBJECT-TYPE
        SYNTAX          SnmpAdminString
        MAX-ACCESS      read-create
        STATUS          current
        DESCRIPTION
                "The HTTP header value associated with the HTTP header
                name given by cslbxProbeHeaderFieldName."
        ::= { cslbxProbeHeaderCfgEntry 3 }

cslbxProbeHeaderRowStatus                 OBJECT-TYPE   
        SYNTAX          RowStatus
        MAX-ACCESS      read-create
        STATUS          current
        DESCRIPTION
                "The object used by a management station to create
                or delete the row entry in cslbxProbeHeaderTable
                following the RowStatus textual convention."
        ::= { cslbxProbeHeaderCfgEntry 4 }


--  *************************************************************
--  *                                                           *
--  * SLB-EXT - Probe Expect Status Codes Configuration Table   *
--  *                                                           *
--  *************************************************************

cslbxProbeExpectStatusCfgTable            OBJECT-TYPE
        SYNTAX          SEQUENCE OF CslbxProbeExpectStatusCfgEntry
        MAX-ACCESS      not-accessible
        STATUS          current
        DESCRIPTION
                "The probing function monitors the health of
                real servers.  The SLB device actively probes
                real servers to determine if they are healthy.  
                This table is for configuring the expect status
                codes returned by a server."
        ::= { cslbxServerProbes 4 }

cslbxProbeExpectStatusCfgEntry            OBJECT-TYPE
        SYNTAX          CslbxProbeExpectStatusCfgEntry
        MAX-ACCESS      not-accessible
        STATUS          current
        DESCRIPTION
                "This entry provides the configuration of a range of
                expect status codes for a particular probe, served by
                a particular SLB entity."
        INDEX   {
                slbEntity, 
                cslbxProbeExpectStatusProbeName,
                cslbxProbeExpectStatusMinValue
        }
        ::= { cslbxProbeExpectStatusCfgTable 1 }

CslbxProbeExpectStatusCfgEntry  ::= SEQUENCE {
        cslbxProbeExpectStatusProbeName           SlbServerString,
        cslbxProbeExpectStatusMinValue            Unsigned32,
        cslbxProbeExpectStatusMaxValue            Unsigned32,
        cslbxProbeExpectStatusRowStatus           RowStatus
}

cslbxProbeExpectStatusProbeName           OBJECT-TYPE
        SYNTAX          SlbServerString
        MAX-ACCESS      not-accessible
        STATUS          current
        DESCRIPTION
                "The name of the probe."
        ::= { cslbxProbeExpectStatusCfgEntry 1 }

cslbxProbeExpectStatusMinValue            OBJECT-TYPE
        SYNTAX          Unsigned32
        MAX-ACCESS      not-accessible
        STATUS          current
        DESCRIPTION
                "The starting value of the expect status code range."
        ::= { cslbxProbeExpectStatusCfgEntry 2 }

cslbxProbeExpectStatusMaxValue            OBJECT-TYPE
        SYNTAX          Unsigned32
        MAX-ACCESS      read-create
        STATUS          current
        DESCRIPTION
                "The ending value of the expect status code range."
        ::= { cslbxProbeExpectStatusCfgEntry 3 }

cslbxProbeExpectStatusRowStatus           OBJECT-TYPE   
        SYNTAX          RowStatus
        MAX-ACCESS      read-create
        STATUS          current
        DESCRIPTION
                "The object used by a management station to create
                or delete the row entry in 
                cslbxProbeExpectStatusCfgTable following the 
                RowStatus textual convention."
        ::= { cslbxProbeExpectStatusCfgEntry 4 }


--  *************************************************************
--  *                                                           *
--  * SLB-EXT - Policy Table                                    *
--  *                                                           *
--  *************************************************************

cslbxPolicyTable                          OBJECT-TYPE
        SYNTAX          SEQUENCE OF CslbxPolicyTableEntry
        MAX-ACCESS      not-accessible
        STATUS          current
        DESCRIPTION
                "Table of load balancing policies."
        ::= { cslbxPolicies 1 }

cslbxPolicyTableEntry                     OBJECT-TYPE
        SYNTAX          CslbxPolicyTableEntry
        MAX-ACCESS      not-accessible
        STATUS          current
        DESCRIPTION
                "Information about a particular policy configured on
                a particular local SLB entity."
        INDEX   {
                slbEntity,
                cslbxPolicyName
        }
        ::= { cslbxPolicyTable 1 }

CslbxPolicyTableEntry ::= SEQUENCE {
        cslbxPolicyName                           SlbServerString,
        cslbxPolicyClientGroupNumber              Unsigned32,
        cslbxPolicyClientGroupName                SlbObjectNameString,
        cslbxPolicyUrlMap                         SlbObjectNameString,
        cslbxPolicyCookieMap                      SlbObjectNameString,
        cslbxPolicyGenericHeaderMap               SlbObjectNameString,
        cslbxPolicyStickyGroup                    Unsigned32,
        cslbxPolicyDscpEnabled                    TruthValue,
        cslbxPolicyDscpStamping                   Unsigned32,
        cslbxPolicyFarmName                       SlbObjectNameString,
        cslbxPolicyRowStatus                      RowStatus
}

cslbxPolicyName                           OBJECT-TYPE
        SYNTAX          SlbServerString
        MAX-ACCESS      not-accessible
        STATUS          current
        DESCRIPTION
                "The name of the policy."
        ::= { cslbxPolicyTableEntry 1 }

cslbxPolicyClientGroupNumber              OBJECT-TYPE
        SYNTAX          Unsigned32
        MAX-ACCESS      read-create
        STATUS          current
        DESCRIPTION
                "The group number of the associated client access
                list."
        ::= { cslbxPolicyTableEntry 2 }

cslbxPolicyClientGroupName                OBJECT-TYPE
        SYNTAX          SlbObjectNameString
        MAX-ACCESS      read-create
        STATUS          current
        DESCRIPTION
                "The group name of the associated client access list."
        ::= { cslbxPolicyTableEntry 3 }

cslbxPolicyUrlMap                         OBJECT-TYPE
        SYNTAX          SlbObjectNameString
        MAX-ACCESS      read-create
        STATUS          current
        DESCRIPTION
                "The name of the associated URL map."
        ::= { cslbxPolicyTableEntry 4 }

cslbxPolicyCookieMap                      OBJECT-TYPE
        SYNTAX          SlbObjectNameString
        MAX-ACCESS      read-create
        STATUS          current
        DESCRIPTION
                "The name of the associated Cookie map."
        ::= { cslbxPolicyTableEntry 5 }

cslbxPolicyGenericHeaderMap               OBJECT-TYPE
        SYNTAX          SlbObjectNameString
        MAX-ACCESS      read-create
        STATUS          current
        DESCRIPTION
                "The name of the associated generic HTTP 
                header map."
        ::= { cslbxPolicyTableEntry 6 }

cslbxPolicyStickyGroup                    OBJECT-TYPE
        SYNTAX          Unsigned32
        MAX-ACCESS      read-create
        STATUS          current
        DESCRIPTION
                "The number of the associated sticky group.  The
                value '0' indicates no sticky group is associated."
        DEFVAL { 0 }
        ::= { cslbxPolicyTableEntry 7 }

cslbxPolicyDscpEnabled                    OBJECT-TYPE
        SYNTAX          TruthValue
        MAX-ACCESS      read-create
        STATUS          current
        DESCRIPTION
                "The current setting for enabling TOS byte stamping.
                If this is set, the TCP TOS (type-of-service) byte
                of traffic matching this policy will be
                stamped with the cslbxPolicyDscpStamping value."
        DEFVAL          { false }
        ::= { cslbxPolicyTableEntry 8 }

cslbxPolicyDscpStamping                   OBJECT-TYPE
        SYNTAX          Unsigned32
        MAX-ACCESS      read-create
        STATUS          current
        DESCRIPTION
                "The value to be stamped over the TCP TOS
                (type-of-service) byte."
        DEFVAL          { 0 }
        ::= { cslbxPolicyTableEntry 9 }

cslbxPolicyFarmName                       OBJECT-TYPE
        SYNTAX          SlbObjectNameString
        MAX-ACCESS      read-create
        STATUS          current
        DESCRIPTION
                "The server farm to which a connection matching this
                policy may be assigned."
        DEFVAL          { "" }
        ::= { cslbxPolicyTableEntry 10 }

cslbxPolicyRowStatus                      OBJECT-TYPE   
        SYNTAX          RowStatus
        MAX-ACCESS      read-create
        STATUS          current
        DESCRIPTION
                "The object used by a management station to create
                or delete the row entry in cslbxPolicyTable following
                the RowStatus textual convention."
        ::= { cslbxPolicyTableEntry 11 }


--  *************************************************************
--  *                                                           *
--  * SLB-EXT - Virtual Server Table                            *
--  *                                                           *
--  *************************************************************

cslbxVirtualServerTable                   OBJECT-TYPE
        SYNTAX          SEQUENCE OF CslbxVirtualServerTableEntry
        MAX-ACCESS      not-accessible
        STATUS          current
        DESCRIPTION
                "Table of virtual servers.  It contains addtional 
                configurations for the slbVirtualServerTable."
        ::= { cslbxVirtualServers 1 }

cslbxVirtualServerTableEntry              OBJECT-TYPE
        SYNTAX          CslbxVirtualServerTableEntry
        MAX-ACCESS      not-accessible
        STATUS          current
        DESCRIPTION
                "Additional configuration information about a
                particular virtual server served by a particular
                local SLB entity."
        AUGMENTS        { slbVirtualServerTableEntry }
        ::= { cslbxVirtualServerTable 1 }

CslbxVirtualServerTableEntry ::= SEQUENCE {
        cslbxVirtualAdvertiseOption               SlbIpAdvertise,
        cslbxVirtualVlanId                        Unsigned32,
        cslbxVirtualReplicationMode               SlbReplicationMode,
        cslbxVirtualPendingTimer                  TimeInterval,
        cslbxVirtualL7MaxParseLength              Unsigned32,
        cslbxVirtualHttpPersistenceSlb            TruthValue,
        cslbxVirtualURLHashBeginString            SlbRegularExpression,
        cslbxVirtualURLHashEndString              SlbRegularExpression
}

cslbxVirtualAdvertiseOption                  OBJECT-TYPE
        SYNTAX          SlbIpAdvertise
        MAX-ACCESS      read-create
        STATUS          current
        DESCRIPTION
                "The advertise option for the virtual IP address.
                This value and the cslbxVirtualAdvertise value will
                determine whether and when to add the virtual IP
                address into the static route table."
        DEFVAL          { alwaysAdvertise }
        ::= { cslbxVirtualServerTableEntry 1 }

cslbxVirtualVlanId                           OBJECT-TYPE
        SYNTAX          Unsigned32
        MAX-ACCESS      read-create
        STATUS          current
        DESCRIPTION
                "The VLAN ID associated with the virtual server.
                Only traffic from this VLAN may match the
                virtual server. By default (value of zero), a
                virtual server may match traffic from any VLAN."
        DEFVAL { 0 }
        ::= { cslbxVirtualServerTableEntry 2 }

cslbxVirtualReplicationMode                  OBJECT-TYPE
        SYNTAX          SlbReplicationMode
        MAX-ACCESS      read-create
        STATUS          current
        DESCRIPTION
                "Specifies which information will be replicated
                from the active device to a standby device in a
                fault tolerant configuration."
        DEFVAL { replNone }
        ::= { cslbxVirtualServerTableEntry 3 }

cslbxVirtualPendingTimer                     OBJECT-TYPE
        SYNTAX          TimeInterval
        MAX-ACCESS      read-create
        STATUS          current
        DESCRIPTION
                "The length of time before a connection in the
                pending state gets torn down."
        DEFVAL { 3000 }
        ::= { cslbxVirtualServerTableEntry 4 }

cslbxVirtualL7MaxParseLength                 OBJECT-TYPE
        SYNTAX          Unsigned32
        MAX-ACCESS      read-create
        STATUS          current
        DESCRIPTION
                "The maximum number of characters to be parsed for
                Layer 7 (application level) specific information.
                If HTTP processing is required on an HTTP request
                or response with HTTP header length greater than
                cslbxVirtualL7MaxParseLength, the connection will be
                rejected and reset."
        DEFVAL { 600 }
        ::= { cslbxVirtualServerTableEntry 5 }

cslbxVirtualHttpPersistenceSlb               OBJECT-TYPE
        SYNTAX          TruthValue
        MAX-ACCESS      read-create
        STATUS          current
        DESCRIPTION
                "The setting for load balancing each request in a
                HTTP 1.1 persistence connection.  If set to 'true',
                the SLB device may direct successive HTTP requests
                in the same TCP connection to different destinations."
        DEFVAL { true }
        ::= { cslbxVirtualServerTableEntry 6 }

cslbxVirtualURLHashBeginString               OBJECT-TYPE
        SYNTAX          SlbRegularExpression
        MAX-ACCESS      read-create
        STATUS          current
        DESCRIPTION
                "The sub-string within the URL string at which to
                start the hashing operation.  The hash result
                will be used in the server farm with predictor
                'urlHash'.  An empty string indicates hashing should
                begin at the beginning of the URL."
        DEFVAL { "" }
        ::= { cslbxVirtualServerTableEntry 7 }

cslbxVirtualURLHashEndString                 OBJECT-TYPE
        SYNTAX          SlbRegularExpression
        MAX-ACCESS      read-create
        STATUS          current
        DESCRIPTION
                "The sub-string within the URL string at which to
                end the hashing operation.  The hash result
                will be used in the server farm with predictor
                'urlHash'.  An empty string indicates hashing should
                end at the end of the URL."
        DEFVAL { "" }
        ::= { cslbxVirtualServerTableEntry 8 }


--  *************************************************************
--  *                                                           *
--  * SLB-EXT - Rule Table                                      *
--  *                                                           *
--  *************************************************************
 
cslbxRuleTable                            OBJECT-TYPE
        SYNTAX          SEQUENCE OF CslbxRuleEntry
        MAX-ACCESS      not-accessible
        STATUS          current
        DESCRIPTION
                "This table provides the function to apply the
                policies to the virtual servers.  Using different
                policies, the SLB can direct traffic matching
                different patterns to different server farms."
        ::= { cslbxVirtualServers 2 }

cslbxRuleEntry                            OBJECT-TYPE
        SYNTAX          CslbxRuleEntry
        MAX-ACCESS      not-accessible
        STATUS          current
        DESCRIPTION
                "This entry links one SLB policy to a virtual server.
                If the status of associated cslbxRuleVirtualServerName
                or the status of associated cslbxRulePolicyName is not
                active, the status of this entry cannot be active."
        INDEX   { 
                slbEntity, 
                cslbxRuleVirtualServerName, 
                cslbxRulePolicyName 
        }
        ::= { cslbxRuleTable 1 }

CslbxRuleEntry ::= SEQUENCE {
        cslbxRuleVirtualServerName                SlbServerString,
        cslbxRulePolicyName                       SlbServerString,
        cslbxRuleCurrentConnections               Gauge32,
        cslbxRuleTotalConnections                 Counter32,
        cslbxRuleHCTotalConnections               Counter64,
        cslbxRuleTotalClientPackets               Counter32,
        cslbxRuleHCTotalClientPackets             Counter64,
        cslbxRuleTotalServerPackets               Counter32,
        cslbxRuleHCTotalServerPackets             Counter64,
        cslbxRuleRowStatus                        RowStatus
}

cslbxRuleVirtualServerName                OBJECT-TYPE
        SYNTAX          SlbServerString
        MAX-ACCESS      not-accessible
        STATUS          current
        DESCRIPTION
                "The name of the associated virtual server."
        ::= { cslbxRuleEntry 1 }

cslbxRulePolicyName                       OBJECT-TYPE
        SYNTAX          SlbServerString
        MAX-ACCESS      not-accessible
        STATUS          current
        DESCRIPTION
                "The name of the associated SLB policy."
        ::= { cslbxRuleEntry 2 }

cslbxRuleCurrentConnections               OBJECT-TYPE
        SYNTAX          Gauge32
        MAX-ACCESS      read-only
        STATUS          current
        DESCRIPTION
                "The current number of open connections that matched
                this SLB policy."
        ::= { cslbxRuleEntry 3 }

cslbxRuleTotalConnections                 OBJECT-TYPE
        SYNTAX          Counter32
        MAX-ACCESS      read-only
        STATUS          current
        DESCRIPTION
                "The total number of connections that ever matched
                this SLB policy."
        ::= { cslbxRuleEntry 4 }

cslbxRuleHCTotalConnections               OBJECT-TYPE
        SYNTAX          Counter64
        MAX-ACCESS      read-only
        STATUS          current
        DESCRIPTION
                "The total number of connections that ever matched
                this SLB policy. This is the 64-bit version of 
                cslbxRuleTotalConnections."
        ::= { cslbxRuleEntry 5 }

cslbxRuleTotalClientPackets               OBJECT-TYPE
        SYNTAX          Counter32
        MAX-ACCESS      read-only
        STATUS          current
        DESCRIPTION
                "The total number of packets ever sent by the client
                to the server on a connection that matched this SLB
                policy."
        ::= { cslbxRuleEntry 6 }

cslbxRuleHCTotalClientPackets             OBJECT-TYPE
        SYNTAX          Counter64
        MAX-ACCESS      read-only
        STATUS          current
        DESCRIPTION
                "The total number of packets ever sent by the client
                to the server on a connection that matched this SLB
                policy.  This is the 64-bit version of
                cslbxRuleTotalClientPackets."
        ::= { cslbxRuleEntry 7 }

cslbxRuleTotalServerPackets               OBJECT-TYPE
        SYNTAX          Counter32
        MAX-ACCESS      read-only
        STATUS          current
        DESCRIPTION
                "The total number of packets ever sent by the server
                to the client on a connection that matched this SLB
                policy."
        ::= { cslbxRuleEntry 8 }

cslbxRuleHCTotalServerPackets             OBJECT-TYPE
        SYNTAX          Counter64
        MAX-ACCESS      read-only
        STATUS          current
        DESCRIPTION
                "The total number of packets ever sent by the server
                to the client on a connection that matched this
                SLB policy.  This is the 64-bit version of
                cslbxRuleTotalClientPackets."
        ::= { cslbxRuleEntry 9 }

cslbxRuleRowStatus                        OBJECT-TYPE
        SYNTAX          RowStatus
        MAX-ACCESS      read-create
        STATUS          current
        DESCRIPTION
                "The object used by a management station to create
                or delete the row entry in cslbxRuleTable following
                the RowStatus textual convention."
        ::= { cslbxRuleEntry 10 }


--  *************************************************************
--  *                                                           *
--  * SLB-EXT - VLAN Table                                      *
--  *                                                           *
--  *************************************************************

cslbxVlanTable                            OBJECT-TYPE
        SYNTAX          SEQUENCE OF CslbxVlanEntry
        MAX-ACCESS      not-accessible
        STATUS          current
        DESCRIPTION
                "This table provides the configuration of VLANs
                configured on the SLB."
        ::= { cslbxVlans 1 }

cslbxVlanEntry                            OBJECT-TYPE
        SYNTAX          CslbxVlanEntry
        MAX-ACCESS      not-accessible
        STATUS          current
        DESCRIPTION
                "This entry is for configuring the VLAN on the SLB
                device."
        INDEX   { 
                slbEntity, 
                cslbxVlanId
        }
        ::= { cslbxVlanTable 1 }

CslbxVlanEntry ::= SEQUENCE {
        cslbxVlanId                               Unsigned32,
        cslbxVlanType                             SlbVlanType,
        cslbxVlanAddressType                      InetAddressType,
        cslbxVlanAddress                          InetAddress,
        cslbxVlanMaskAddressType                  InetAddressType,
        cslbxVlanMaskAddress                      InetAddress,
        cslbxVlanRowStatus                        RowStatus
}

cslbxVlanId                               OBJECT-TYPE
        SYNTAX          Unsigned32
        MAX-ACCESS      not-accessible
        STATUS          current
        DESCRIPTION
                "The 802.1q VLAN ID of this VLAN."
        ::= { cslbxVlanEntry 1 }

cslbxVlanType                             OBJECT-TYPE
        SYNTAX          SlbVlanType
        MAX-ACCESS      read-create
        STATUS          current
        DESCRIPTION
                "The type of this VLAN."
        ::= { cslbxVlanEntry 2 }

cslbxVlanAddressType                      OBJECT-TYPE
        SYNTAX          InetAddressType
        MAX-ACCESS      read-create
        STATUS          current
        DESCRIPTION
                "The type of address stored in cslbxVlanAddress."
        DEFVAL          { ipv4 }
        ::= { cslbxVlanEntry 3 }

cslbxVlanAddress                          OBJECT-TYPE
        SYNTAX          InetAddress (SIZE (0..20))
        MAX-ACCESS      read-create
        STATUS          current
        DESCRIPTION
                "The IP address of this VLAN interface."
        DEFVAL          { '00000000'H } -- 0.0.0.0
        ::= { cslbxVlanEntry 4 }

cslbxVlanMaskAddressType                  OBJECT-TYPE
        SYNTAX          InetAddressType
        MAX-ACCESS      read-create
        STATUS          current
        DESCRIPTION
                "The type of address stored in cslbxVlanMaskAddress."
        DEFVAL          { ipv4 }
        ::= { cslbxVlanEntry 5 }

cslbxVlanMaskAddress                      OBJECT-TYPE
        SYNTAX          InetAddress (SIZE (0..20))
        MAX-ACCESS      read-create
        STATUS          current
        DESCRIPTION
                "The network mask for this VLAN interface."
        DEFVAL          { '00000000'H } -- 0.0.0.0
        ::= { cslbxVlanEntry 6 }

cslbxVlanRowStatus                        OBJECT-TYPE
        SYNTAX          RowStatus
        MAX-ACCESS      read-create
        STATUS          current
        DESCRIPTION
                "The object is used by a management station to create
                or delete the row entry in cslbxVlanTable following
                the RowStatus textual convention."
        ::= { cslbxVlanEntry 7 }


--  *************************************************************
--  *                                                           *
--  * SLB-EXT - Alias IP Address Table                          *
--  *                                                           *
--  *************************************************************

cslbxAliasAddrTable                       OBJECT-TYPE
        SYNTAX          SEQUENCE OF CslbxAliasAddrEntry
        MAX-ACCESS      not-accessible
        STATUS          current
        DESCRIPTION
                "This table provides the configuration of alias IP 
                addresses on the SLB device.  The SLB device will
                respond to an ARP request for alias IP addresses if
                the ARP request arrives on the configured VLAN.
                A given VLAN may be associated with multiple alias
                IP addresses."
        ::= { cslbxVlans 2 }

cslbxAliasAddrEntry                       OBJECT-TYPE
        SYNTAX          CslbxAliasAddrEntry
        MAX-ACCESS      not-accessible
        STATUS          current
        DESCRIPTION
                "This entry is for configuring an alias IP address on 
                the SLB device."
        INDEX   { 
                slbEntity, 
                cslbxAliasAddrVlanId,
                cslbxAliasAddrAddressType,
                cslbxAliasAddrAddress
        }
        ::= { cslbxAliasAddrTable 1 }

CslbxAliasAddrEntry ::= SEQUENCE {
        cslbxAliasAddrVlanId                      Unsigned32,
        cslbxAliasAddrAddressType                 InetAddressType,
        cslbxAliasAddrAddress                     InetAddress,
        cslbxAliasAddrRowStatus                   RowStatus
}

cslbxAliasAddrVlanId                      OBJECT-TYPE
        SYNTAX          Unsigned32
        MAX-ACCESS      not-accessible
        STATUS          current
        DESCRIPTION
                "The VLAN ID associated with this alias address."
        ::= { cslbxAliasAddrEntry 1 }

cslbxAliasAddrAddressType                 OBJECT-TYPE
        SYNTAX          InetAddressType
        MAX-ACCESS      not-accessible
        STATUS          current
        DESCRIPTION
                "The type of address stored in cslbxAliasAddrAddress."
        ::= { cslbxAliasAddrEntry 2 }

cslbxAliasAddrAddress                     OBJECT-TYPE
        SYNTAX          InetAddress (SIZE (1..20))
        MAX-ACCESS      not-accessible
        STATUS          current
        DESCRIPTION
                "The alias IP address itself."
        ::= { cslbxAliasAddrEntry 3 }

cslbxAliasAddrRowStatus                   OBJECT-TYPE
        SYNTAX          RowStatus
        MAX-ACCESS      read-create
        STATUS          current
        DESCRIPTION
                "The object is used by a management station to create
                or delete the row entry in cslbxAliasAddrTable
                following the RowStatus textual convention."
        ::= { cslbxAliasAddrEntry 4 }


--  *************************************************************
--  *                                                           *
--  * SLB-EXT - IP Static Route Table                           *
--  *                                                           *
--  *************************************************************

cslbxStaticRouteTable                       OBJECT-TYPE
        SYNTAX          SEQUENCE OF CslbxStaticRouteEntry
        MAX-ACCESS      not-accessible
        STATUS          current
        DESCRIPTION
                "This table provides the configuration of static routes
                on the SLB device."
        ::= { cslbxVlans 3 }

cslbxStaticRouteEntry                       OBJECT-TYPE
        SYNTAX          CslbxStaticRouteEntry
        MAX-ACCESS      not-accessible
        STATUS          current
        DESCRIPTION
                "This entry is for configuring the static route used
                by the SLB device.  The SLB device will accept
                multiple destination gateways for the same route.
                The SLB should able to pick an active gateway for
                a given route.  In some case, the SLB device can
                load-balancing among the gateways of the same
                route."
        INDEX   { 
                slbEntity, 
                cslbxStaticRouteVlanId,
                cslbxStaticRouteSubnetAddrType,
                cslbxStaticRouteSubnetAddr,
                cslbxStaticRouteMaskAddrType,
                cslbxStaticRouteMaskAddr,
                cslbxStaticRouteGatewayAddrType,
                cslbxStaticRouteGatewayAddr
        }
        ::= { cslbxStaticRouteTable 1 }

CslbxStaticRouteEntry ::= SEQUENCE {
        cslbxStaticRouteVlanId                    Unsigned32,
        cslbxStaticRouteSubnetAddrType            InetAddressType,
        cslbxStaticRouteSubnetAddr                InetAddress,
        cslbxStaticRouteMaskAddrType              InetAddressType,
        cslbxStaticRouteMaskAddr                  InetAddress,
        cslbxStaticRouteGatewayAddrType           InetAddressType,
        cslbxStaticRouteGatewayAddr               InetAddress,
        cslbxStaticRouteRowStatus                 RowStatus
}

cslbxStaticRouteVlanId                    OBJECT-TYPE
        SYNTAX          Unsigned32
        MAX-ACCESS      not-accessible
        STATUS          current
        DESCRIPTION
                "The VLAN ID associated with this route."
        ::= { cslbxStaticRouteEntry 1 }

cslbxStaticRouteSubnetAddrType            OBJECT-TYPE
        SYNTAX          InetAddressType
        MAX-ACCESS      not-accessible
        STATUS          current
        DESCRIPTION
                "The type of address stored in
                cslbxStaticRouteSubnetAddr."
        ::= { cslbxStaticRouteEntry 2 }

cslbxStaticRouteSubnetAddr                OBJECT-TYPE
        SYNTAX          InetAddress (SIZE (1..20))
        MAX-ACCESS      not-accessible
        STATUS          current
        DESCRIPTION
                "The IP subnet of this route."
        ::= { cslbxStaticRouteEntry 3 }

cslbxStaticRouteMaskAddrType              OBJECT-TYPE
        SYNTAX          InetAddressType
        MAX-ACCESS      not-accessible
        STATUS          current
        DESCRIPTION
                "The type of address stored in
                cslbxStaticRouteMaskAddr."
        ::= { cslbxStaticRouteEntry 4 }

cslbxStaticRouteMaskAddr                  OBJECT-TYPE
        SYNTAX          InetAddress (SIZE (1..20))
        MAX-ACCESS      not-accessible
        STATUS          current
        DESCRIPTION
                "The IP network mask of this route."
        ::= { cslbxStaticRouteEntry 5 }

cslbxStaticRouteGatewayAddrType           OBJECT-TYPE
        SYNTAX          InetAddressType
        MAX-ACCESS      not-accessible
        STATUS          current
        DESCRIPTION
                "The type of address stored in
                cslbxStaticRouteGatewayAddr."
        ::= { cslbxStaticRouteEntry 6 }

cslbxStaticRouteGatewayAddr               OBJECT-TYPE
        SYNTAX          InetAddress (SIZE (1..20))
        MAX-ACCESS      not-accessible
        STATUS          current
        DESCRIPTION
                "The IP address of the next hop gateway."
        ::= { cslbxStaticRouteEntry 7 }

cslbxStaticRouteRowStatus                 OBJECT-TYPE
        SYNTAX          RowStatus
        MAX-ACCESS      read-create
        STATUS          current
        DESCRIPTION
                "The object is used by a management station to create
                or delete the row entry in cslbxStaticRouteTable
                following the RowStatus textual convention."
        ::= { cslbxStaticRouteEntry 8 }


--  *************************************************************
--  *                                                           *
--  * SLB-EXT - Fault Tolerance Table                           *
--  *                                                           *
--  *************************************************************

cslbxFtTable                              OBJECT-TYPE
        SYNTAX          SEQUENCE OF CslbxFtTableEntry
        MAX-ACCESS      not-accessible
        STATUS          current
        DESCRIPTION
                "Table of Fault Tolerance settings."
        ::= { cslbxFaultTolerance 1 }

cslbxFtTableEntry                         OBJECT-TYPE
        SYNTAX          CslbxFtTableEntry
        MAX-ACCESS      not-accessible
        STATUS          current
        DESCRIPTION
                "Information about Fault Tolerance settings
                for a particular local SLB entity."
        INDEX   {
                slbEntity        
        }
        ::= { cslbxFtTable 1 }

CslbxFtTableEntry ::= SEQUENCE {
        cslbxFtGroupId                            Unsigned32,
        cslbxFtVlanId                             Unsigned32,
        cslbxFtPreempt                            TruthValue,
        cslbxFtPriority                           Unsigned32,
        cslbxFtHeartBeatTimer                     TimeInterval,
        cslbxFtFailThreshold                      Unsigned32,
        cslbxFtState                              SlbFtState,
        cslbxFtStateChangeTime                    TimeStamp,
        cslbxFtRxHeartBeatMsgs                    Counter32,
        cslbxFtTxHeartBeatMsgs                    Counter32,
        cslbxFtRxUpdateMsgs                       Counter32,
        cslbxFtTxUpdateMsgs                       Counter32,
        cslbxFtRxCoupMsgs                         Counter32,
        cslbxFtTxCoupMsgs                         Counter32,
        cslbxFtRxElectMsgs                        Counter32,
        cslbxFtTxElectMsgs                        Counter32,
        cslbxFtRxConnReplMsgs                     Counter32,
        cslbxFtTxConnReplMsgs                     Counter32,
        cslbxFtRxPackets                          Counter32,
        cslbxFtDropPackets                        Counter32,
        cslbxFtDuplPackets                        Counter32,
        cslbxFtXsumErrPackets                     Counter32,
        cslbxFtBuffErrPackets                     Counter32,
        cslbxFtRowStatus                          RowStatus
}

cslbxFtGroupId                            OBJECT-TYPE
        SYNTAX          Unsigned32
        MAX-ACCESS      read-create
        STATUS          current
        DESCRIPTION
                "The Fault Tolerance group number."
        DEFVAL          { 0 }
        ::= { cslbxFtTableEntry 1 }

cslbxFtVlanId                             OBJECT-TYPE
        SYNTAX          Unsigned32
        MAX-ACCESS      read-create
        STATUS          current
        DESCRIPTION
                "The VLAN ID used by this Fault Tolerance group."
        DEFVAL          { 0 }
        ::= { cslbxFtTableEntry 2 }

cslbxFtPreempt                            OBJECT-TYPE
        SYNTAX          TruthValue
        MAX-ACCESS      read-create
        STATUS          current
        DESCRIPTION
                "The preemption setting for this Fault Tolerance
                group."
        DEFVAL          { false }
        ::= { cslbxFtTableEntry 3 }

cslbxFtPriority                           OBJECT-TYPE
        SYNTAX          Unsigned32
        MAX-ACCESS      read-create
        STATUS          current
        DESCRIPTION
                "The priority value of this SLB device for the
                Fault Tolerance group."
        DEFVAL        { 10 }
        ::= { cslbxFtTableEntry 4 }

cslbxFtHeartBeatTimer                     OBJECT-TYPE
        SYNTAX          TimeInterval
        MAX-ACCESS      read-create
        STATUS          current
        DESCRIPTION
                "The time interval of sending the keep-alive messages
                to the peer in the Fault Tolerance group."
        DEFVAL        { 100 }
        ::= { cslbxFtTableEntry 5 }

cslbxFtFailThreshold                      OBJECT-TYPE
        SYNTAX          Unsigned32
        MAX-ACCESS      read-create
        STATUS          current
        DESCRIPTION
                "The threshold for failing over to the standby SLB.
                If a standby SLB device has not received a keep-alive
                message from an active SLB device within
                cslbxFtFailThreshold consecutive periods
                of length cslbxFtHeartBeatTimer, the standby
                will become active."
        DEFVAL        { 3 }
        ::= { cslbxFtTableEntry 6 }

cslbxFtState                              OBJECT-TYPE
        SYNTAX          SlbFtState
        MAX-ACCESS      read-only
        STATUS          current
        DESCRIPTION
                "The current Fault Tolerance state of this SLB device."
        ::= { cslbxFtTableEntry 7 }

cslbxFtStateChangeTime                    OBJECT-TYPE
        SYNTAX          TimeStamp
        MAX-ACCESS      read-only
        STATUS          current
        DESCRIPTION
                "The time of the last change in the current
                Fault Tolerance state of the SLB device."
        ::= { cslbxFtTableEntry 8 }

cslbxFtRxHeartBeatMsgs                    OBJECT-TYPE
        SYNTAX          Counter32
        MAX-ACCESS      read-only
        STATUS          current
        DESCRIPTION
                "The number of the keep-alive messages ever received by
                this SLB device."
        ::= { cslbxFtTableEntry 9 }

cslbxFtTxHeartBeatMsgs                    OBJECT-TYPE
        SYNTAX          Counter32
        MAX-ACCESS      read-only
        STATUS          current
        DESCRIPTION
                "The number of the keep-alive messages ever sent
                by this SLB device."
        ::= { cslbxFtTableEntry 10 }

cslbxFtRxUpdateMsgs                       OBJECT-TYPE
        SYNTAX          Counter32
        MAX-ACCESS      read-only
        STATUS          current
        DESCRIPTION
                "The number of the state update (sticky) messages
                ever received by this SLB device."
        ::= { cslbxFtTableEntry 11 }

cslbxFtTxUpdateMsgs                       OBJECT-TYPE
        SYNTAX          Counter32
        MAX-ACCESS      read-only
        STATUS          current
        DESCRIPTION
                "The number of the state update (sticky) messages
                ever sent by this SLB device."
        ::= { cslbxFtTableEntry 12 }

cslbxFtRxCoupMsgs                         OBJECT-TYPE
        SYNTAX          Counter32
        MAX-ACCESS      read-only
        STATUS          current
        DESCRIPTION
                "The number of master override messages
                ever received by this SLB device."
        ::= { cslbxFtTableEntry 13 }

cslbxFtTxCoupMsgs                         OBJECT-TYPE
        SYNTAX          Counter32
        MAX-ACCESS      read-only
        STATUS          current
        DESCRIPTION
                "The number of master override messages
                ever sent by this SLB device."
        ::= { cslbxFtTableEntry 14 }

cslbxFtRxElectMsgs                        OBJECT-TYPE
        SYNTAX          Counter32
        MAX-ACCESS      read-only
        STATUS          current
        DESCRIPTION
                "The number of the master election messages
                ever received by this SLB device."
        ::= { cslbxFtTableEntry 15 }

cslbxFtTxElectMsgs                        OBJECT-TYPE
        SYNTAX          Counter32
        MAX-ACCESS      read-only
        STATUS          current
        DESCRIPTION
                "The number of the master election messages
                ever sent by this SLB device."
        ::= { cslbxFtTableEntry 16 }

cslbxFtRxConnReplMsgs                     OBJECT-TYPE
        SYNTAX          Counter32
        MAX-ACCESS      read-only
        STATUS          current
        DESCRIPTION
                "The number of the connection replication
                messages ever received by this SLB device."
        ::= { cslbxFtTableEntry 17 }

cslbxFtTxConnReplMsgs                     OBJECT-TYPE
        SYNTAX          Counter32
        MAX-ACCESS      read-only
        STATUS          current
        DESCRIPTION
                "The number of the connection replication
                messages ever sent by this SLB device."
        ::= { cslbxFtTableEntry 18 }

cslbxFtRxPackets                          OBJECT-TYPE
        SYNTAX          Counter32
        MAX-ACCESS      read-only
        STATUS          current
        DESCRIPTION
                "The total number of Fault Tolerance messages 
                ever received by this SLB device."
        ::= { cslbxFtTableEntry 19 }

cslbxFtDropPackets                        OBJECT-TYPE
        SYNTAX          Counter32
        MAX-ACCESS      read-only
        STATUS          current
        DESCRIPTION
                "The total number of Fault Tolerance messages 
                ever dropped by this SLB device."
        ::= { cslbxFtTableEntry 20 }

cslbxFtDuplPackets                        OBJECT-TYPE
        SYNTAX          Counter32
        MAX-ACCESS      read-only
        STATUS          current
        DESCRIPTION
                "The total number of duplicate Fault Tolerance
                messages ever received by this SLB device."
        ::= { cslbxFtTableEntry 21 }

cslbxFtXsumErrPackets                     OBJECT-TYPE
        SYNTAX          Counter32
        MAX-ACCESS      read-only
        STATUS          current
        DESCRIPTION
                "The total number of Fault Tolerance messages with
                a checksum error ever received by this SLB device."
        ::= { cslbxFtTableEntry 22 }

cslbxFtBuffErrPackets                     OBJECT-TYPE
        SYNTAX          Counter32
        MAX-ACCESS      read-only
        STATUS          current
        DESCRIPTION
                "The total number of Fault Tolerance messages dropped
                by this SLB device due to insufficient buffer memory."
        ::= { cslbxFtTableEntry 23 }

cslbxFtRowStatus                          OBJECT-TYPE
        SYNTAX          RowStatus
        MAX-ACCESS      read-create
        STATUS          current
        DESCRIPTION
                "The row status is used by a management station to
                create or delete the row entry in
                cslbxFtTable following the RowStatus
                textual convention."
        ::= { cslbxFtTableEntry 24 }


--  *************************************************************
--  *                                                           *
--  * SLB-EXT - XML Configuration Table                         *
--  *                                                           *
--  *************************************************************

cslbxXmlConfigTable                       OBJECT-TYPE
        SYNTAX          SEQUENCE OF CslbxXmlConfigTableEntry
        MAX-ACCESS      not-accessible
        STATUS          current
        DESCRIPTION
                "Table of XML interface settings."
        ::= { cslbxXmlConfig 1 }

cslbxXmlConfigTableEntry                  OBJECT-TYPE
        SYNTAX          CslbxXmlConfigTableEntry
        MAX-ACCESS      not-accessible
        STATUS          current
        DESCRIPTION
                "Information about XML interface settings
                for a particular local SLB entity."
        INDEX   {
                slbEntity        
        }
        ::= { cslbxXmlConfigTable 1 }

CslbxXmlConfigTableEntry ::= SEQUENCE {
        cslbxXmlConfigEnabled                      TruthValue,
        cslbxXmlConfigVlanId                       Unsigned32,
        cslbxXmlConfigListeningPort                CiscoPort,
        cslbxXmlConfigRowStatus                    RowStatus
}

cslbxXmlConfigEnabled                     OBJECT-TYPE
        SYNTAX          TruthValue
        MAX-ACCESS      read-create
        STATUS          current
        DESCRIPTION
                "The current setting for enabling XML interface.
                If this is set, the XML configuration is
                enabled for this SLB instance."
        DEFVAL          { false }
        ::= { cslbxXmlConfigTableEntry 1 }

cslbxXmlConfigVlanId                      OBJECT-TYPE
        SYNTAX          Unsigned32
        MAX-ACCESS      read-create
        STATUS          current
        DESCRIPTION
                "The VLAN ID on which to accept requests for
                configuration via XML.  If it set to zero, then
                connection from any VLAN is acceptable."
        DEFVAL          { 0 }
        ::= { cslbxXmlConfigTableEntry 2 }

cslbxXmlConfigListeningPort               OBJECT-TYPE
        SYNTAX          CiscoPort
        MAX-ACCESS      read-create
        STATUS          current
        DESCRIPTION
                "The TCP port on which this SLB instance
                listens for XML configuration requests."
        DEFVAL          { 80 }
        ::= { cslbxXmlConfigTableEntry 3 }

cslbxXmlConfigRowStatus                   OBJECT-TYPE
        SYNTAX          RowStatus
        MAX-ACCESS      read-create
        STATUS          current
        DESCRIPTION
                "The row status is used by a management station to
                create or delete the row entry in cslbxXmlConfigTable
                following the RowStatus textual convention."
        ::= { cslbxXmlConfigTableEntry 4 }


--  *************************************************************
--  *                                                           *
--  * SLB-EXT - Extended Connection Table                       *
--  *                                                           *
--  *************************************************************

cslbxConnTable                            OBJECT-TYPE
        SYNTAX          SEQUENCE OF CslbxConnTableEntry
        MAX-ACCESS      not-accessible
        STATUS          current
        DESCRIPTION
                "Table of Extended Connections being load-balanced
                by SLB.  This table supports the Content Switching
                Module (CSM) feature which is not supported by
                the slbConnectionTable in the CISCO-SLB-MIB."
        ::= { cslbxConnections 1 }

cslbxConnTableEntry                       OBJECT-TYPE
        SYNTAX          CslbxConnTableEntry
        MAX-ACCESS      not-accessible
        STATUS          current
        DESCRIPTION
                "A list of Extended Connections for a particular
                local SLB entity."
        INDEX   {
                slbEntity,
                cslbxConnIndex
        }
        ::= { cslbxConnTable 1 }

CslbxConnTableEntry ::= SEQUENCE {
        cslbxConnIndex                             Unsigned32,
        cslbxConnInDestAddrType                    InetAddressType,
        cslbxConnInDestAddr                        InetAddress,
        cslbxConnInDestPort                        CiscoPort,
        cslbxConnInSourceAddrType                  InetAddressType,
        cslbxConnInSourceAddr                      InetAddress,
        cslbxConnInSourcePort                      CiscoPort,
        cslbxConnProtocol                          CiscoIpProtocol,
        cslbxConnOutDestAddrType                   InetAddressType,
        cslbxConnOutDestAddr                       InetAddress,
        cslbxConnOutDestPort                       CiscoPort,
        cslbxConnOutSourceAddrType                 InetAddressType,
        cslbxConnOutSourceAddr                     InetAddress,
        cslbxConnOutSourcePort                     CiscoPort,
        cslbxConnState                             SlbConnectionState
}

cslbxConnIndex                            OBJECT-TYPE
        SYNTAX          Unsigned32
        MAX-ACCESS      not-accessible
        STATUS          current
        DESCRIPTION
                "The index to internal structures for the
                Extended Connection."
        ::= { cslbxConnTableEntry 1 }

cslbxConnInDestAddrType                   OBJECT-TYPE
        SYNTAX          InetAddressType
        MAX-ACCESS      read-only
        STATUS          current
        DESCRIPTION
                "The type of address stored in
                cslbxConnInDestAddr."
        ::= { cslbxConnTableEntry 2 }

cslbxConnInDestAddr                       OBJECT-TYPE
        SYNTAX          InetAddress (SIZE (0..20))
        MAX-ACCESS      read-only
        STATUS          current
        DESCRIPTION
                "The destination IP address of the incoming
                request."
        ::= { cslbxConnTableEntry 3 }

cslbxConnInDestPort                       OBJECT-TYPE
        SYNTAX          CiscoPort
        MAX-ACCESS      read-only
        STATUS          current
        DESCRIPTION
                "The destination port of the incoming request."
        ::= { cslbxConnTableEntry 4 }

cslbxConnInSourceAddrType                 OBJECT-TYPE
        SYNTAX          InetAddressType
        MAX-ACCESS      read-only
        STATUS          current
        DESCRIPTION
                "The type of address stored in
                cslbxConnInSourceAddr."
        ::= { cslbxConnTableEntry 5 }

cslbxConnInSourceAddr                     OBJECT-TYPE
        SYNTAX          InetAddress (SIZE (0..20))
        MAX-ACCESS      read-only
        STATUS          current
        DESCRIPTION
                "The source IP address of the incoming request."
        ::= { cslbxConnTableEntry 6 }

cslbxConnInSourcePort                     OBJECT-TYPE
        SYNTAX          CiscoPort
        MAX-ACCESS      read-only
        STATUS          current
        DESCRIPTION
                "The source port of the incoming request."
        ::= { cslbxConnTableEntry 7 }

cslbxConnProtocol                         OBJECT-TYPE
        SYNTAX          CiscoIpProtocol
        MAX-ACCESS      read-only
        STATUS          current
        DESCRIPTION
                "The IP protocol for the Extended Conn."
        ::= { cslbxConnTableEntry 8 }

cslbxConnOutDestAddrType                  OBJECT-TYPE
        SYNTAX          InetAddressType
        MAX-ACCESS      read-only
        STATUS          current
        DESCRIPTION
                "The type of address stored in
                cslbxConnOutDestIpAddr."
        ::= { cslbxConnTableEntry 9 }

cslbxConnOutDestAddr                      OBJECT-TYPE
        SYNTAX          InetAddress (SIZE (0..20))
        MAX-ACCESS      read-only
        STATUS          current
        DESCRIPTION
                "The destination IP address of the load-balanced
                 Extended Conn."
        ::= { cslbxConnTableEntry 10 }

cslbxConnOutDestPort                      OBJECT-TYPE
        SYNTAX          CiscoPort
        MAX-ACCESS      read-only
        STATUS          current
        DESCRIPTION
                "The destination port of the load-balanced
                Extended Conn."
        ::= { cslbxConnTableEntry 11 }

cslbxConnOutSourceAddrType                OBJECT-TYPE
        SYNTAX          InetAddressType
        MAX-ACCESS      read-only
        STATUS          current
        DESCRIPTION
                "The type of address stored in
                cslbxConnOutSourceAddr."
        ::= { cslbxConnTableEntry 12 }

cslbxConnOutSourceAddr                    OBJECT-TYPE
        SYNTAX          InetAddress (SIZE (0..20))
        MAX-ACCESS      read-only
        STATUS          current
        DESCRIPTION
                "The source IP address of the load-balanced
                Extended Conn."
        ::= { cslbxConnTableEntry 13 }

cslbxConnOutSourcePort                    OBJECT-TYPE
        SYNTAX          CiscoPort
        MAX-ACCESS      read-only
        STATUS          current
        DESCRIPTION
                "The source port of the load-balanced
                Extended Conn."
        ::= { cslbxConnTableEntry 14 }

cslbxConnState                            OBJECT-TYPE
        SYNTAX          SlbConnectionState
        MAX-ACCESS      read-only
        STATUS          current
        DESCRIPTION
                "The current state of this Extended Conn."
        ::= { cslbxConnTableEntry 15 }


--  *************************************************************
--  *                                                           *
--  * Notification Truth Values                                 *
--  *                                                           *
--  *************************************************************

cslbxFtStateChangeNotifEnabled            OBJECT-TYPE
        SYNTAX          TruthValue
        MAX-ACCESS      read-write
        STATUS          current
        DESCRIPTION 
                "This object controls the generation of
                cslbxFtStateChange notification.
                'true'  Indicates that cslbxFtStateChange
                        notification is to be generated when the state
                        changes. That is, notification generation 
                        is enabled.
                'false' Indicates that cslbxFtStateChange
                        notification generation is disabled."
        DEFVAL { false }
        ::= { cslbxNotifObjects 1 }


--
-- Notifications
--

cslbxFtStateChange NOTIFICATION-TYPE
        OBJECTS {
                cslbxFtState
        }
        STATUS  current
        DESCRIPTION
                "The notification generated when the Fault Tolerance
                process changes to a new state.  The value of
                cslbxFtState indicates the new state."
        ::= { ciscoSlbExtMIBNotifs 1 }


--
-- Conformance Information
--
cslbxMIBCompliances OBJECT IDENTIFIER ::=
        { ciscoSlbExtMIBConform 1 }
cslbxMIBGroups      OBJECT IDENTIFIER ::=
        { ciscoSlbExtMIBConform 2 }

-- Compliance

cslbxMIBCompliance MODULE-COMPLIANCE
        STATUS current
        DESCRIPTION
                "The compliance statement for entities which implement
                the Cisco SLB EXT MIB.  The Content Switching Module
                (CSM) product supports this revision."

        MODULE -- this module

--      Unconditionally Mandatory Groups 

                MANDATORY-GROUPS {
                        cslbxStickyGroupsGroup,
                        cslbxMapsGroup,
                        cslbxPoliciesGroup,
                        cslbxVirtualServersGroup
                }

--      Relaxation on IP addressing

                OBJECT  cslbxServerFarmHashMaskAddrType
                DESCRIPTION
                        "An implementation is only required to support
                        IPv4 addresses."

                OBJECT  cslbxServerFarmHashMaskAddr
                DESCRIPTION
                        "An implementation is only required to support
                        IPv4 addresses."

                OBJECT  cslbxNatPoolStartAddressType
                DESCRIPTION
                        "An implementation is only required to support
                        IPv4 addresses."

                OBJECT  cslbxNatPoolStartAddress
                DESCRIPTION
                        "An implementation is only required to support
                        IPv4 addresses."

                OBJECT  cslbxNatPoolEndAddressType
                DESCRIPTION
                        "An implementation is only required to support
                        IPv4 addresses."

                OBJECT  cslbxNatPoolEndAddress
                DESCRIPTION
                        "An implementation is only required to support
                        IPv4 addresses."

                OBJECT  cslbxStickyGroupMaskAddressType
                DESCRIPTION
                        "An implementation is only required to support
                        IPv4 addresses."

                OBJECT  cslbxStickyGroupMaskAddress
                DESCRIPTION
                        "An implementation is only required to support
                        IPv4 addresses."

                OBJECT  cslbxProbeAlternateDestAddrType
                DESCRIPTION
                        "An implementation is only required to support
                        IPv4 addresses."

                OBJECT  cslbxProbeAlternateDestAddr
                DESCRIPTION
                        "An implementation is only required to support
                        IPv4 addresses."

                OBJECT  cslbxVlanAddressType
                DESCRIPTION
                        "An implementation is only required to support
                        IPv4 addresses."

                OBJECT  cslbxVlanAddress
                DESCRIPTION
                        "An implementation is only required to support
                        IPv4 addresses."

                OBJECT  cslbxVlanMaskAddressType
                DESCRIPTION
                        "An implementation is only required to support
                        IPv4 addresses."

                OBJECT  cslbxVlanMaskAddress
                DESCRIPTION
                        "An implementation is only required to support
                        IPv4 addresses."

                OBJECT  cslbxConnInDestAddrType
                DESCRIPTION
                        "An implementation is only required to support
                        IPv4 addresses."

                OBJECT  cslbxConnInDestAddr
                DESCRIPTION
                        "An implementation is only required to support
                        IPv4 addresses."

                OBJECT  cslbxConnInSourceAddrType
                DESCRIPTION
                        "An implementation is only required to support
                        IPv4 addresses."

                OBJECT  cslbxConnInSourceAddr
                DESCRIPTION
                        "An implementation is only required to support
                        IPv4 addresses."

                OBJECT  cslbxConnOutDestAddrType
                DESCRIPTION
                        "An implementation is only required to support
                        IPv4 addresses."

                OBJECT  cslbxConnOutDestAddr
                DESCRIPTION
                        "An implementation is only required to support
                        IPv4 addresses."

                OBJECT  cslbxConnOutSourceAddrType
                DESCRIPTION
                        "An implementation is only required to support
                        IPv4 addresses."

                OBJECT  cslbxConnOutSourceAddr
                DESCRIPTION
                        "An implementation is only required to support
                        IPv4 addresses."

                OBJECT  cslbxStickyObjectRealAddressType
                DESCRIPTION
                        "An implementation is only required to support
                        IPv4 addresses."

                OBJECT  cslbxStickyObjectRealAddress
                DESCRIPTION
                        "An implementation is only required to support
                        IPv4 addresses."

--      Optional Groups 

                GROUP   cslbxStatsGroup
                DESCRIPTION
                        "This group supports the load-balancing
                         statistics for the Content Switching Module
                         (CSM) product."

                GROUP   cslbxServerFarmsGroup
                DESCRIPTION
                        "This group supports the HTTP redirect servers
                         in a SLB server farm."

                GROUP   cslbxClientNatPoolsGroup
                DESCRIPTION
                        "This group supports the client NAT feature
                         for a SLB device."

                GROUP   cslbxServerProbesGroup
                DESCRIPTION
                        "This group supports the Health Probe feature
                         within a SLB device.  An implementation is
                         only required to support IPv4 address
                         instances for the table cslbxDnsProbeIpTable
                         in this group."

                GROUP   cslbxVlansGroup
                DESCRIPTION
                        "This group supports the VLAN configuration
                         for the Content Switching Module (CSM)
                         product.  An implementation is
                         only required to support IPv4 address
                         instances for the table cslbxAliasAddrTable,
                         cslbxStaticRouteTable in this group."

                GROUP   cslbxFaultToleranceGroup
                DESCRIPTION
                        "This group supports the Fault Tolerance
                         feature for the Content Switching Module
                         (CSM) product."

                GROUP   cslbxNotifControlGroup
                DESCRIPTION
                        "This group supports the setting for enabling
                         the notifications of state changed in
                         a SLB device."

                GROUP   cslbxNotifGroup
                DESCRIPTION
                        "This group supports the notifications of
                         state changed in a SLB device."

                GROUP   cslbxConnsGroup
                DESCRIPTION
                        "This group supports the Connection table for
                        the Content Switching Module (CSM) product."

                GROUP   cslbxStickyObjectsGroup
                DESCRIPTION
                        "This group supports the Sticky Object table
                        for the Content Switching Module (CSM)
                        product."

                GROUP   cslbxXmlConfigGroup
                DESCRIPTION
                        "This group supports the XML Config table
                        for the Content Switching Module (CSM)
                        product."

        ::= { cslbxMIBCompliances 1 }

-- Units of Conformance

cslbxStatsGroup  OBJECT-GROUP
        OBJECTS {
                cslbxStatsServerInitConns,
                cslbxStatsServerInitHCConns,
                cslbxStatsCurrConnections,
                cslbxStatsCurrServerInitConns,
                cslbxStatsFailedConns,
                cslbxStatsFailedServerInitConns,
                cslbxStatsL4PolicyConns,
                cslbxStatsL7PolicyConns,
                cslbxStatsDroppedL4PolicyConns,
                cslbxStatsDroppedL7PolicyConns,
                cslbxStatsFtpConns,
                cslbxStatsHttpRedirectConns,
                cslbxStatsDroppedRedirectConns,
                cslbxStatsNoMatchPolicyRejects,
                cslbxStatsNoCfgPolicyRejects,
                cslbxStatsNoActiveServerRejects,
                cslbxStatsAclDenyRejects,
                cslbxStatsMaxParseLenRejects,
                cslbxStatsBadSslFormatRejects,
                cslbxStatsL7ParserErrorRejects,
                cslbxStatsVerMismatchRejects,
                cslbxStatsOutOfMemoryRejects,
                cslbxStatsTimedOutConnections,
                cslbxStatsTcpChecksumErrorPkts,
                cslbxStatsIpChecksumErrorPkts
        }
        STATUS current
        DESCRIPTION
                "A collection of additional global statistics objects
                for the SLB entity."
        ::= { cslbxMIBGroups 1 }

cslbxServerFarmsGroup  OBJECT-GROUP
        OBJECTS {
                cslbxServerFarmHashMaskAddrType,
                cslbxServerFarmHashMaskAddr,
                cslbxServerFarmClientNatPool,
                cslbxServerFarmFailAction,
                cslbxServerFarmHttpReturnCodeMap,
                cslbxServerFarmInFailedThreshold,
                cslbxServerFarmInbandResetTimer,
                cslbxRedirectSvrRelocationStr,
                cslbxRedirectSvrBackupString,
                cslbxRedirectSvrRedirectCode,
                cslbxRedirectSvrRedirectPort,
                cslbxRedirectSvrState,
                cslbxRedirectSvrNumberOfConns,
                cslbxRedirectSvrMaxConns,
                cslbxRedirectSvrAdminWeight,
                cslbxRedirectSvrOperWeight,
                cslbxRedirectSvrMetric,
                cslbxRedirectSvrTotalConns,
                cslbxRedirectSvrHCTotalConns,
                cslbxRedirectSvrRowStatus,
                cslbxServerFarmProbeRowStatus
        }
        STATUS current
        DESCRIPTION
                "A collection of cslbxServerFarmTable and
                cslbxRedirectSvrTable objects used to 
                further define an SLB server farm."
        ::= { cslbxMIBGroups 2 }

cslbxClientNatPoolsGroup  OBJECT-GROUP
        OBJECTS {
                cslbxNatPoolStartAddressType,
                cslbxNatPoolStartAddress,
                cslbxNatPoolEndAddressType,
                cslbxNatPoolEndAddress,
                cslbxNatPoolRowStatus
        }
        STATUS current
        DESCRIPTION
                "The SLB client NAT pool objects."
        ::= { cslbxMIBGroups 3 }

cslbxStickyGroupsGroup  OBJECT-GROUP
        OBJECTS {
                cslbxStickyGroupType,
                cslbxStickyGroupMaskAddressType,
                cslbxStickyGroupMaskAddress,
                cslbxStickyGroupCookieName,
                cslbxStickyGroupStickyTimer,
                cslbxStickyGroupRowStatus
         }
        STATUS current
        DESCRIPTION
                "The SLB sticky group objects."
        ::= { cslbxMIBGroups 4 }

cslbxStickyObjectsGroup  OBJECT-GROUP
        OBJECTS {
                cslbxStickyObjectGroupId,
                cslbxStickyObjectType,
                cslbxStickyObjectSourceInfo,
                cslbxStickyObjectRealAddressType,
                cslbxStickyObjectRealAddress,
                cslbxStickyObjectRealPort
        }
        STATUS current
        DESCRIPTION
                "The SLB Extended sticky objects."
        ::= { cslbxMIBGroups 5 }

cslbxMapsGroup  OBJECT-GROUP
        OBJECTS {
                cslbxMapType,
                cslbxMapRowStatus,
                cslbxHttpExpressionFieldName,
                cslbxHttpExpressionValue,
                cslbxHttpExpressionRowStatus,
                cslbxHttpReturnCodeMaxValue,
                cslbxHttpReturnCodeThreshold,
                cslbxHttpReturnCodeResetTimer,
                cslbxHttpReturnCodeType,
                cslbxHttpReturnCodeRowStatus                
        }
        STATUS current
        DESCRIPTION
                "The SLB map objects."
        ::= { cslbxMIBGroups 6 }

cslbxServerProbesGroup  OBJECT-GROUP
        OBJECTS {
                cslbxProbeType,
                cslbxProbeInterval,
                cslbxProbeRetries,
                cslbxProbeFailedInterval,
                cslbxProbeReceiveTimeout,
                cslbxProbeTcpOpenTimeout,
                cslbxProbeAlternateDestAddrType,
                cslbxProbeAlternateDestAddr,
                cslbxProbeDnsDomainName,
                cslbxProbeHttpRequestMethod,
                cslbxProbeHttpRequestUrl,
                cslbxProbeRowStatus,
                cslbxDnsProbeIpRowStatus,
                cslbxProbeHeaderFieldValue,
                cslbxProbeHeaderRowStatus,
                cslbxProbeExpectStatusMaxValue,
                cslbxProbeExpectStatusRowStatus
        }
        STATUS current
        DESCRIPTION
                "The SLB server health probe objects."
        ::= { cslbxMIBGroups 7 }

cslbxPoliciesGroup  OBJECT-GROUP
        OBJECTS {
                cslbxPolicyClientGroupNumber,
                cslbxPolicyClientGroupName,
                cslbxPolicyUrlMap,
                cslbxPolicyCookieMap,
                cslbxPolicyGenericHeaderMap,
                cslbxPolicyStickyGroup,
                cslbxPolicyDscpEnabled,
                cslbxPolicyDscpStamping,
                cslbxPolicyFarmName,
                cslbxPolicyRowStatus
        }
        STATUS current
        DESCRIPTION
                "The SLB policy objects."
        ::= { cslbxMIBGroups 8 }

cslbxVirtualServersGroup OBJECT-GROUP
        OBJECTS {
                cslbxVirtualAdvertiseOption,
                cslbxVirtualVlanId,
                cslbxVirtualReplicationMode,
                cslbxVirtualPendingTimer,
                cslbxVirtualL7MaxParseLength,
                cslbxVirtualHttpPersistenceSlb,
                cslbxVirtualURLHashBeginString,
                cslbxVirtualURLHashEndString,
                cslbxRuleCurrentConnections,
                cslbxRuleTotalConnections,
                cslbxRuleHCTotalConnections,
                cslbxRuleTotalClientPackets,
                cslbxRuleHCTotalClientPackets,
                cslbxRuleTotalServerPackets,
                cslbxRuleHCTotalServerPackets,
                cslbxRuleRowStatus
        }
        STATUS current
        DESCRIPTION
                "A collection of virtual server and rule objects
                used to further define layer 7 parameters for the
                SLB virtual server."
        ::= { cslbxMIBGroups 9 }

cslbxVlansGroup  OBJECT-GROUP
        OBJECTS {
                cslbxVlanType,
                cslbxVlanAddressType,
                cslbxVlanAddress,
                cslbxVlanMaskAddressType,
                cslbxVlanMaskAddress,
                cslbxVlanRowStatus,
                cslbxAliasAddrRowStatus,
                cslbxStaticRouteRowStatus
        }
        STATUS current
        DESCRIPTION
                "The SLB VLAN configuration objects."
        ::= { cslbxMIBGroups 10 }

cslbxFaultToleranceGroup  OBJECT-GROUP
        OBJECTS {
                cslbxFtGroupId,
                cslbxFtVlanId,
                cslbxFtPreempt,
                cslbxFtPriority,
                cslbxFtHeartBeatTimer,
                cslbxFtFailThreshold,
                cslbxFtState,
                cslbxFtStateChangeTime,
                cslbxFtRxHeartBeatMsgs,
                cslbxFtTxHeartBeatMsgs,
                cslbxFtRxUpdateMsgs,
                cslbxFtTxUpdateMsgs,
                cslbxFtRxCoupMsgs,
                cslbxFtTxCoupMsgs,
                cslbxFtRxElectMsgs,
                cslbxFtTxElectMsgs,
                cslbxFtRxConnReplMsgs,
                cslbxFtTxConnReplMsgs,
                cslbxFtRxPackets,
                cslbxFtDropPackets,
                cslbxFtDuplPackets,
                cslbxFtXsumErrPackets,
                cslbxFtBuffErrPackets,
                cslbxFtRowStatus
        }
        STATUS current
        DESCRIPTION
                "The SLB Fault Tolerance objects."
        ::= { cslbxMIBGroups 11 }

cslbxConnsGroup  OBJECT-GROUP
        OBJECTS {
                cslbxConnInDestAddrType,
                cslbxConnInDestAddr,
                cslbxConnInDestPort,
                cslbxConnInSourceAddrType,
                cslbxConnInSourceAddr,
                cslbxConnInSourcePort,
                cslbxConnProtocol,
                cslbxConnOutDestAddrType,
                cslbxConnOutDestAddr,
                cslbxConnOutDestPort,
                cslbxConnOutSourceAddrType,
                cslbxConnOutSourceAddr,
                cslbxConnOutSourcePort,
                cslbxConnState
        }
        STATUS current
        DESCRIPTION
                "The SLB Extended Conn objects."
        ::= { cslbxMIBGroups 12 }

cslbxXmlConfigGroup  OBJECT-GROUP
        OBJECTS {
                cslbxXmlConfigEnabled,
                cslbxXmlConfigVlanId,
                cslbxXmlConfigListeningPort,
                cslbxXmlConfigRowStatus
        }
        STATUS current
        DESCRIPTION
                "The SLB XML configuration objects."
        ::= { cslbxMIBGroups 13 }

cslbxNotifControlGroup  OBJECT-GROUP
        OBJECTS {
                cslbxFtStateChangeNotifEnabled
        }
        STATUS current
        DESCRIPTION
                "The collection of objects to control the
                notifications for state changed in a SLB
                device."
        ::= { cslbxMIBGroups 14 }

cslbxNotifGroup  NOTIFICATION-GROUP
        NOTIFICATIONS {
                cslbxFtStateChange
        }
        STATUS current
        DESCRIPTION
            "The collection of notifications of CISCO-SLB-EXT-MIB
            entity that are required to support."
        ::= { cslbxMIBGroups 15 }


END
