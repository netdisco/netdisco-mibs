-- *********************************************************************
-- CISCO-SYSTEM-EXT-MIB.my: System Extension MIB
--
-- October 2002, Vinay Gaonkar
--
-- Copyright (c) 2002, 2003 by cisco Systems, Inc.
-- All rights reserved.
-- 
-- *********************************************************************

CISCO-SYSTEM-EXT-MIB DEFINITIONS ::= BEGIN

IMPORTS        
     MODULE-IDENTITY, OBJECT-TYPE, 
     NOTIFICATION-TYPE, Unsigned32, 
     Gauge32                                FROM SNMPv2-SMI
     MODULE-COMPLIANCE, OBJECT-GROUP,
     NOTIFICATION-GROUP                     FROM SNMPv2-CONF
     TEXTUAL-CONVENTION, TruthValue,
     DateAndTime                            FROM SNMPv2-TC 
     SnmpAdminString                        FROM SNMP-FRAMEWORK-MIB    
     InetAddressType, InetAddress
                                            FROM INET-ADDRESS-MIB	 
     ciscoMgmt                              FROM CISCO-SMI;


ciscoSystemExtMIB MODULE-IDENTITY
        LAST-UPDATED "200305020000Z"
        ORGANIZATION "Cisco Systems Inc. "
        CONTACT-INFO
                "     Cisco Systems
                      Customer Service
                Postal: 170 W Tasman Drive
                      San Jose, CA  95134
                      USA
                Tel: +1 800 553 -NETS
                E-mail: cs-san@cisco.com"
        DESCRIPTION
		     "MIB module for monitoring High Availability, 
              SNMP SET errors and bandwidths."
        REVISION   "200305020000Z"
        DESCRIPTION
            "Added a new object cseWriteErase.
             Added a new group ciscoSystemExtInfoGroupOptional.
             A new compliance ciscoSystemExtMIBComplianceRev2 
             added to replace ciscoSystemExtMIBComplianceRev1." 
        REVISION   "200303020000Z"
        DESCRIPTION
            "Added cseSysAutoSync and cseSysAutoSyncState."      
        REVISION   "200211190000Z"
        DESCRIPTION
            "Added cseSysConfLastChange."      
        REVISION   "200210040000Z"
        DESCRIPTION
            "Initial version of this MIB module."
        ::= { ciscoMgmt 305 }  
        
ciscoSystemExtMIBNotifsPrefix OBJECT IDENTIFIER 
                                            ::= { ciscoSystemExtMIB 0 }
ciscoSystemExtMIBObjects OBJECT IDENTIFIER     
                                            ::= { ciscoSystemExtMIB 1 }
ciscoSystemExtMIBConformance OBJECT IDENTIFIER 
                                            ::= { ciscoSystemExtMIB 2 }

ciscoSysInfoGroup OBJECT IDENTIFIER  ::= { ciscoSystemExtMIBObjects 1 }
ciscoSysErrorGroup OBJECT IDENTIFIER ::= { ciscoSystemExtMIBObjects 2 }
ciscoHaGroup OBJECT IDENTIFIER       ::= { ciscoSystemExtMIBObjects 3 }
                                
-- Textual Conventions                                

CseHaRestartReason ::= TEXTUAL-CONVENTION
        STATUS    current
        DESCRIPTION
               "Reason codes for the restart of a service.
                  unknown (1)           - ungraceful exit
                  ungracefulExit (2)    - ungraceful exit
                  otherSignal (3)       - service got some other signal
                  sigterm (4)           - received SIGTERM
                  softwareUpgrade (5)   - software upgrade
                  configUpdate (6)     - config update
                  configRemove (7)      - config removal
                  shutdown (8)          - manually shutdown
                  aborted (9)           - aborted
                  heartbeatFailure (10) - heartbeat failure
                  userTerminate (11)    - user termnation
                  gracefulExit (12)     - graceful exit
               "
        SYNTAX    INTEGER {    
                     unknown (1), 
                     ungracefulExit (2),
                     otherSignal (3),
                     sigterm (4),
                     softwareUpgrade (5),
                     configUpdate (6),
                     configRemove (7),
                     shutdown (8),
                     aborted (9),
                     heartbeatFailure (10),
                     userTerminate (11),
                     gracefulExit (12)
                  }

-- System Information Group

cseSysCPUUtilization OBJECT-TYPE
        SYNTAX          Gauge32 (0..100)
        UNITS           "%"
        MAX-ACCESS      read-only
        STATUS          current
        DESCRIPTION
                "The average utilization of CPU on the active 
                supervisor."
    ::= { ciscoSysInfoGroup 1 }                       
      

-- Memory utilization

cseSysMemoryUtilization OBJECT-TYPE
        SYNTAX          Gauge32 (0..100)
        UNITS           "%"
        MAX-ACCESS      read-only
        STATUS          current
        DESCRIPTION
                "The average utilization of memory on the active 
                supervisor."
    ::= { ciscoSysInfoGroup 2 }

cseSysConfLastChange OBJECT-TYPE
        SYNTAX          DateAndTime
        MAX-ACCESS      read-only
        STATUS          current
        DESCRIPTION
               "The local date and time when the 
                configuration was last changed. This object will 
                be set to zero on power cycle or on reboot of 
                the system. Also, if the clock is changed on 
                local system it is set to zero. "
    ::= { ciscoSysInfoGroup 3 }   
    
cseSysAutoSync OBJECT-TYPE
        SYNTAX          INTEGER {
                                 sync(1),
                                 noSync(2)
                        } 
        MAX-ACCESS      read-write
        STATUS          current
        DESCRIPTION
               "The state of the auto synchronization of images
                between the active and standby supervisor.
                Setting the value to sync when the existing value
                is sync, has no effect on the operation. "
        DEFVAL { noSync }
    ::= { ciscoSysInfoGroup 4 }   

cseSysAutoSyncState OBJECT-TYPE
        SYNTAX          INTEGER {
                                 inProgress(1),
                                 succeeded(2),
                                 failed(3),
                                 notStarted(4)
                        }
        MAX-ACCESS      read-only
        STATUS          current
        DESCRIPTION
               "The status of the current auto synchronization 
                process, or if no such process is in progress,  
                then the state of the most recent one.  The 
                value 'notStarted' indicates no auto synchronization 
                process has occurred recently."
    ::= { ciscoSysInfoGroup 5 }   

cseWriteErase OBJECT-TYPE
        SYNTAX          INTEGER {
                                 noOp(1),
                                 eraseAll(2)
                        } 
        MAX-ACCESS      read-write
        STATUS          current
        DESCRIPTION
               "This object is used to initiate a write erase on the 
               device's saved configuration file(s) from which the 
               device loads its configuration when it restarts.

               If the value of this object is set to 'eraseAll', then
               all the saved configurations are removed.

               No action is taken when the this object is set to 
               'noOp'.
               When read, the value of this object is always 'noOp'."
    ::= { ciscoSysInfoGroup 6 }   


cseSnmpErrorTable  OBJECT-TYPE
    SYNTAX     SEQUENCE OF CseSnmpErrorEntry
    MAX-ACCESS not-accessible
    STATUS     current
    DESCRIPTION
         "A table containing information about the errors which have 
         recently caused the generation of a SNMP Response PDU with a 
         non-zero value in its error-status field for SNMP Set Response
         PDU. 

         This table serves as an extension to the SNMP's error status 
         when a SNMP Set request fails. SNMP returns only a pre-defined
         set of standard error codes which does not convey the specific 
         cause for an error. Typically, there is an incumbent and 
         sizable burden on the configuration application to determine 
         if the configuration request failure is the result of a 
         resource issue, a security issue, or an application error 
         (like an object depending on some other objects). So from a 
         user perspective, it is important that a specific error be 
         made known.

         Ideally, when a 'badValue' error occurs for a given set 
         request, an application can query the command responder for 
         more details on the error. 
  
         This table provides a framework for the command responders to 
         provide more information on the SET errors.
       
         It is upto the implementation to create entries in this table 
         for either only certain SNMP errors or all of the SNMP errors.

         Note that only most recent incarnation of an entry is kept in 
         this table."
    ::= { ciscoSysErrorGroup 1 }

cseSnmpErrorEntry OBJECT-TYPE
    SYNTAX     CseSnmpErrorEntry
    MAX-ACCESS not-accessible
    STATUS     current
    DESCRIPTION
        "An entry (conceptual row) in the  cseSnmpErrorTable, containing
        information about an error which has recently caused a SNMP 
        SetRequest to fail.  An entry is created by the agent 
        on the occurrence of an error, and is deleted approximately 5
        minutes later. The reasons for this are :
        - to prevent old entries clogging the table.
        - optimal utilization of the resources like memory."
    INDEX { cseSnmpErrorAddressType, cseSnmpErrorAddress, 
            cseSnmpErrorRequestId }
    ::= { cseSnmpErrorTable 1 }

CseSnmpErrorEntry ::= SEQUENCE {
        cseSnmpErrorAddressType     InetAddressType,
        cseSnmpErrorAddress         InetAddress,
        cseSnmpErrorRequestId       Unsigned32,
        cseSnmpErrorCode            Unsigned32,
        cseSnmpErrorDescription     SnmpAdminString
}

cseSnmpErrorAddressType OBJECT-TYPE
    SYNTAX      InetAddressType
    MAX-ACCESS  not-accessible 
    STATUS      current
    DESCRIPTION
        "The type of address from which the error-ed SetRequest 
        originated." 
    ::= { cseSnmpErrorEntry 1 }

cseSnmpErrorAddress OBJECT-TYPE
    SYNTAX      InetAddress
    MAX-ACCESS  not-accessible 
    STATUS      current             
    DESCRIPTION
        "The address from which the error-ed SetRequest originated."
    ::= { cseSnmpErrorEntry 2 }

cseSnmpErrorRequestId OBJECT-TYPE
    SYNTAX      Unsigned32
    MAX-ACCESS  not-accessible 
    STATUS      current             
    DESCRIPTION
        "The request-id of the error-ed SetRequest."
    ::= { cseSnmpErrorEntry 3 }

cseSnmpErrorCode  OBJECT-TYPE
    SYNTAX      Unsigned32
    MAX-ACCESS  read-only 
    STATUS      current             
    DESCRIPTION
           "The code for the Mib object specific error which 
           caused a SetRequest to fail.
           This error code is platform-specific and for debugging
           purposes only. For information on this code, the 
           corresponding instance of cseSnmpErrorDescription must be 
           used. 
           This code is not the same as the value contained
           in the error-status field of SNMP Response PDU."
    ::= { cseSnmpErrorEntry 4 }

cseSnmpErrorDescription  OBJECT-TYPE
    SYNTAX      SnmpAdminString
    MAX-ACCESS  read-only 
    STATUS      current             
    DESCRIPTION
           "The error description for the error happened for the 
           SetRequest."
    ::= { cseSnmpErrorEntry 5 }
        

-- Notification informations

cseHaRestartReason OBJECT-TYPE
        SYNTAX        CseHaRestartReason
        MAX-ACCESS    accessible-for-notify
        STATUS        current
        DESCRIPTION   
               "The reason for most recent restart of a service on the 
               'active' supervisor."
        ::= { ciscoHaGroup 2 }                         

cseHaRestartStateless OBJECT-TYPE
        SYNTAX        TruthValue
        MAX-ACCESS    accessible-for-notify
        STATUS        current
        DESCRIPTION   
               "Tells if the most recent restart of a service on the 
               'active' supervisor was 'stateless' or not.
                A 'stateless' restart of a service is where no runtime 
                information is preserved while restarting the service."
        ::= { ciscoHaGroup 3 }                         

cseHaRestartService  OBJECT-TYPE
        SYNTAX        SnmpAdminString (SIZE (0..255))
        MAX-ACCESS    accessible-for-notify
        STATUS        current
        DESCRIPTION   
               "Name of the service (or process) that was restarted on 
               the 'active' supervisor."
        ::= { ciscoHaGroup 4 }                         

-- Notifications
--        

-- High Availability Notifications        
cseHaNotification OBJECT IDENTIFIER          ::= {ciscoHaGroup  5 }
cseHaNotificationPrefix OBJECT IDENTIFIER    ::= { cseHaNotification 0 }

cseHaRestartNotify  NOTIFICATION-TYPE
            OBJECTS     { cseHaRestartReason, 
                          cseHaRestartService,
                          cseHaRestartStateless}
            STATUS      current
            DESCRIPTION
                 "A service restart notification is generated 
                 whenever a service (or a process) on the  'active' 
                 supervisor is restarted."

    ::= { cseHaNotificationPrefix 1 }

-- Conformance

ciscoSystemExtMIBCompliances
       OBJECT IDENTIFIER ::= { ciscoSystemExtMIBConformance 1 }

ciscoSystemExtMIBGroups
       OBJECT IDENTIFIER ::= { ciscoSystemExtMIBConformance 2 }

ciscoSystemExtMIBCompliance MODULE-COMPLIANCE
        STATUS   deprecated -- superceeded by 
                            -- ciscoSystemsExtMIBComplianceRev1
        DESCRIPTION
                "The compliance statement for entities which
                 implement the CISCO-SYTEM-EXT-MIB."
        MODULE MANDATORY-GROUPS { ciscoSystemExtInfoGroup,
                                  ciscoSystemExtErrorGroup,
                                  ciscoSystemExtHaGroup,
                                  ciscoSystemExtNotificationGroup }
--        OBJECT cseSnmpErrorAddressType
--        SYNTAX     INTEGER {
--                     ipv4 (1)
--                   }
--        DESCRIPTION 
--                "Only ipv4 (1) needs to be supported."

        ::= { ciscoSystemExtMIBCompliances 1 }

ciscoSystemExtMIBComplianceRev1 MODULE-COMPLIANCE
        STATUS   deprecated -- superceded by 
                            -- ciscoSystemExtMIBComplianceRev2 
        DESCRIPTION
                "The compliance statement for entities which
                 implement the CISCO-SYTEM-EXT-MIB."
        MODULE MANDATORY-GROUPS { ciscoSystemExtInfoGroupRev1,
                                  ciscoSystemExtErrorGroup,
                                  ciscoSystemExtHaGroup,
                                  ciscoSystemExtNotificationGroup }
--        OBJECT cseSnmpErrorAddressType
--        SYNTAX     INTEGER {
--                     ipv4 (1)
--                   }
--        DESCRIPTION
--                "Only ipv4 (1) needs to be supported."

        ::= { ciscoSystemExtMIBCompliances 2 }

ciscoSystemExtMIBComplianceRev2 MODULE-COMPLIANCE
        STATUS   deprecated -- superceded by 
                            -- ciscoSystemExtMIBComplianceRev3 
        DESCRIPTION
                "The compliance statement for entities which
                 implement the CISCO-SYTEM-EXT-MIB."
        MODULE MANDATORY-GROUPS { ciscoSystemExtInfoGroupRev1,
                                  ciscoSystemExtErrorGroup,
                                  ciscoSystemExtHaGroup,
                                  ciscoSystemExtNotificationGroup
                                  }
        GROUP ciscoSystemExtInfoGroupOptional
           DESCRIPTION
                 "Implementation of this group is optional."

--        OBJECT cseSnmpErrorAddressType
--        SYNTAX     INTEGER {
--                     ipv4 (1)
--                   }
--        DESCRIPTION
--                "Only ipv4 (1) needs to be supported."
          
        ::= { ciscoSystemExtMIBCompliances 3 }
        
-- Units of Conformance

ciscoSystemExtInfoGroup OBJECT-GROUP
        OBJECTS { cseSysCPUUtilization,
                  cseSysMemoryUtilization,
                  cseSysConfLastChange }
        STATUS   deprecated  -- superceeded by 
                             -- ciscoSystemExtInfoGroupRev1
        DESCRIPTION
                "A collection of objects for system information."
        ::= { ciscoSystemExtMIBGroups 1 }

ciscoSystemExtErrorGroup  OBJECT-GROUP
        OBJECTS  { cseSnmpErrorCode, cseSnmpErrorDescription }
        STATUS   current
        DESCRIPTION
                "A collection of objects for logging SNMP set error."
        ::= { ciscoSystemExtMIBGroups 2 }

ciscoSystemExtHaGroup  OBJECT-GROUP
        OBJECTS  { cseHaRestartReason,
                   cseHaRestartService,
                   cseHaRestartStateless 
                 }
        STATUS   current
        DESCRIPTION
                "A collection of objects for High Availability."
        ::= { ciscoSystemExtMIBGroups 3 }

ciscoSystemExtNotificationGroup  NOTIFICATION-GROUP
        NOTIFICATIONS  { cseHaRestartNotify }
        STATUS   current
        DESCRIPTION
                "A collection of notifications for the 
                High Availability."
        ::= { ciscoSystemExtMIBGroups 4 }

ciscoSystemExtInfoGroupRev1 OBJECT-GROUP
        OBJECTS { cseSysCPUUtilization,
                  cseSysMemoryUtilization,
                  cseSysConfLastChange,
                  cseSysAutoSync,
                  cseSysAutoSyncState }
        STATUS   current
        DESCRIPTION
                "A collection of objects for system information."
        ::= { ciscoSystemExtMIBGroups 5 }
        
ciscoSystemExtInfoGroupOptional OBJECT-GROUP
        OBJECTS { cseWriteErase }
        STATUS   current   
        DESCRIPTION
                "A collection of objects for system information
                which are optional."
        ::= { ciscoSystemExtMIBGroups 6 }
        
END
