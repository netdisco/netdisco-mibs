--**MOD+***********************************************************************
--* Module:    HPE-ANW-FLOW-TELEMETRY-PROFILE-MIB.mib
--*
--* (c) Copyright 2025 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains the MIB definition of
--*          HPE-ANW-FLOW-TELEMETRY-PROFILE-MIB
--*
--**MOD-***********************************************************************

HPE-ANW-FLOW-TELEMETRY-PROFILE-MIB DEFINITIONS ::= BEGIN

    IMPORTS
        OBJECT-TYPE, MODULE-IDENTITY, Unsigned32
            FROM SNMPv2-SMI
        DisplayString
            FROM SNMPv2-TC
        MODULE-COMPLIANCE, OBJECT-GROUP
            FROM SNMPv2-CONF
        wndFeatures
              FROM ARUBAWIRED-NETWORKING-OID;
    hpeAnwFlowTelemetryProfileMIB MODULE-IDENTITY
        LAST-UPDATED "202506150000Z" -- June 15, 2025
        ORGANIZATION "HPE/Aruba Networking Division"
        CONTACT-INFO "Hewlett-Packard Company
                      8000 Foothills Blvd.
                      Roseville, CA 95747"
        DESCRIPTION  "This MIB module contains the details for flow telemetry
                      features."
        REVISION     "202506150000Z" -- June 15, 2024
        DESCRIPTION  "Initial revision."
        ::= { wndFeatures 28 }

-- *************************************************************
-- Start of MIB Objects
-- *************************************************************
hpeAnwFlowTelemetryNotifications OBJECT IDENTIFIER
                                    ::= { hpeAnwFlowTelemetryProfileMIB 0 }
hpeAnwFlowTelemetryObjects       OBJECT IDENTIFIER
                                    ::= { hpeAnwFlowTelemetryProfileMIB 1 }
hpeAnwFlowTelemetryConformance   OBJECT IDENTIFIER
                                    ::= { hpeAnwFlowTelemetryProfileMIB 2 }

-- *************************************************************
-- Flow Telemetry Profile Table
-- *************************************************************
hpeAnwFlowTelemetryProfile    OBJECT IDENTIFIER
                                    ::= { hpeAnwFlowTelemetryObjects 1 }
    hpeAnwFlowTelemetryProfileTable OBJECT-TYPE
        SYNTAX      SEQUENCE OF ArubaWiredFlowTelemetryProfileEntry
        MAX-ACCESS  not-accessible
        STATUS      current
        DESCRIPTION "A table containing flow telemetry profile configuration."
        ::= { hpeAnwFlowTelemetryProfile 1 }

hpeAnwFlowTelemetryProfileEntry OBJECT-TYPE
    SYNTAX      ArubaWiredFlowTelemetryProfileEntry
    MAX-ACCESS  not-accessible
    STATUS      current
    DESCRIPTION "An entry containing flow telemetry profile configuration."
    INDEX       { hpeAnwFlowTelemetryProfileName }
    ::= { hpeAnwFlowTelemetryProfileTable 1 }

ArubaWiredFlowTelemetryProfileEntry ::= SEQUENCE {
        hpeAnwFlowTelemetryProfileName                  DisplayString,
        hpeAnwFlowTelemetryProfileIFAProgrammedDeviceId Unsigned32
    }

hpeAnwFlowTelemetryProfileName OBJECT-TYPE
    SYNTAX      DisplayString (SIZE (1..45))
    MAX-ACCESS  not-accessible
    STATUS      current
    DESCRIPTION "Specifies the telemetry configuration profile name."
    ::= { hpeAnwFlowTelemetryProfileEntry 1 }

hpeAnwFlowTelemetryProfileIFAProgrammedDeviceId OBJECT-TYPE
    SYNTAX      Unsigned32 (0..1048575)
    MAX-ACCESS  read-only
    STATUS      current
    DESCRIPTION "Specifies the programmed IFA device ID."
    ::= { hpeAnwFlowTelemetryProfileEntry 2 }

-- **********************************************************************
-- Flow Telemetry Conformance information
-- **********************************************************************
hpeAnwFlowTelemetryCompliances OBJECT IDENTIFIER
                                ::= { hpeAnwFlowTelemetryConformance 1 }
hpeAnwFlowTelemetryGroups      OBJECT IDENTIFIER
                                ::= { hpeAnwFlowTelemetryConformance 2 }

hpeAnwFlowTelemetryProfileGroup OBJECT-GROUP
    OBJECTS {
        hpeAnwFlowTelemetryProfileIFAProgrammedDeviceId
    }
    STATUS      current
    DESCRIPTION "A collection of objects providing flow telemetry 
                profile information."
    ::= { hpeAnwFlowTelemetryGroups 1 }

hpeAnwFlowTelemetryCompliance MODULE-COMPLIANCE
    STATUS      current
    DESCRIPTION "The compliance statement for devices implementing the
                 ARUBA WIRED FLOW TELEMETRY MIB."
    MODULE
    MANDATORY-GROUPS {
                      hpeAnwFlowTelemetryProfileGroup
                     }
    ::= { hpeAnwFlowTelemetryCompliances 1 }
END
