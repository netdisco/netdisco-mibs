--**MOD+***********************************************************************
--* Module:    ARUBAWIRED-NETWORKING-OID.mib
--*
--* (c) Copyright 2017-2026 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains MIB definition of ARUBAWIRED-NETWORKING-OID
--*
--**MOD-***********************************************************************

ARUBAWIRED-NETWORKING-OID DEFINITIONS ::= BEGIN

IMPORTS
        enterprises, MODULE-IDENTITY, OBJECT-IDENTITY
            FROM SNMPv2-SMI;

hpeNetworking MODULE-IDENTITY
         LAST-UPDATED "202512080000Z"  -- December 08, 2025

         ORGANIZATION "HPE/Aruba Networking Division"
         CONTACT-INFO "Hewlett Packard Company
                       8000 Foothills Blvd.
                       Roseville, CA 95747"

         DESCRIPTION  "This MIB module defines HPE Networking
                       product hardware MIBs and proprietary MIBs. "

         REVISION     "202512080000Z"  -- December 08, 2025
         DESCRIPTION  "Updated with new transceiver OID and
                       transceiver slot OIDs for 6300/6400"

         REVISION     "202507070000Z"  -- July 07, 2025
         DESCRIPTION  "Added JL669B Fantray OID for 6300"

         REVISION     "202506110000Z"  -- June 15, 2025
         DESCRIPTION  "Added Flow Telemetry Profile MIB"

         REVISION     "202503120000Z"  -- March 12, 2025
         DESCRIPTION  "Added new SKU OIDs for 10040"

         REVISION     "202502190000Z"  -- February 19, 2025
         DESCRIPTION  "Updated with new 6000 SKUs"

         REVISION     "202412050000Z"  -- December 5, 2024
         DESCRIPTION  "Added fan and PSU modules for 8325H SKUs"

         REVISION     "202411110000Z"  -- November 11, 2024
         DESCRIPTION  "Added MII SKUs for 6200F"

         REVISION     "202410250000Z"  -- October 25, 2024
         DESCRIPTION  "Added MII SKU OIDs for 6000 and 6100"

         REVISION     "202409110000Z"  -- September 11, 2024
         DESCRIPTION  "Updated Descriptions for 8325H SKUs"

         REVISION     "202408300000Z"  -- August 30, 2024
         DESCRIPTION  "Added new SKU OIDs for 6300M"

         REVISION     "202408210000Z"  -- August 21, 2024
         DESCRIPTION  "Added 8325H and 8325P SKUs"

         REVISION     "202408070000Z"  -- August 7, 2024
         DESCRIPTION  "Updated Descriptions for 5420 modules"

         REVISION     "202405290000Z"  -- May 29, 2024
         DESCRIPTION  "Added new switch S4K80A"

         REVISION     "202403060000Z"  -- March 6, 2024
         DESCRIPTION  "Updated with new SKU OIDs for 9300S"

         REVISION     "202402280000Z"  -- February 28, 2024
         DESCRIPTION  "Added new ARUBAWIRED-PM-MIB module"

         REVISION     "202402220000Z"  -- February 22, 2024
         DESCRIPTION  "Updated with new SKU OIDs for 5420"

         REVISION     "202402070000Z"  -- February 7, 2024
         DESCRIPTION  "Updated with new SKU OIDs for 6300L"

         REVISION     "202312180000Z"  -- December 18, 2023
         DESCRIPTION  "Updated with new SKU OIDs for 8325P"

         REVISION     "202312140000Z"  -- December 14, 2023
         DESCRIPTION  "Updated with new SKU OIDs for 6300"

         REVISION     "202312110000Z"  -- December 11, 2023
         DESCRIPTION  "Updated Descriptions for S0E48A and S1T83A"

	 REVISION     "202306280000Z"  -- June 28, 2023
         DESCRIPTION  "Updated line card long descriptions"

         REVISION     "202306230000Z"  -- June 23, 2023
         DESCRIPTION  "Added new SWITCH-IMAGE-MIB module"

         REVISION     "202305180000Z"  -- May 18, 2023
         DESCRIPTION  "Updated with new line card SKU OIDs for 6400"

         REVISION     "202304250000Z"  -- April 25, 2023
         DESCRIPTION  "Updated with new 1G TAA SKU OIDs for 6200F"

         REVISION     "202304190000Z"  -- April 19, 2023
         DESCRIPTION  "Updated with new SKU OIDs for 6300M"

         REVISION     "202304100000Z"  -- April 10, 2023
         DESCRIPTION  "Updated SKU description text for JL724B-JL728B
                       and S0M81A-S0M90A"

         REVISION     "202211290000Z"  -- November 29, 2022
         DESCRIPTION  "Updated with new SKU OIDs for 6200F"

         REVISION     "202211100000Z"  -- November 10, 2022
         DESCRIPTION  "Updated description text for R8Q71A and R8Q72A"

         REVISION     "202210270000Z"  -- October 27, 2022
         DESCRIPTION  "updated with 8100 fan and PSU slots"

         REVISION     "202206290000Z"  -- June 29, 2022
         DESCRIPTION  "Updated with new R9W94A-R8W97A SKUs belonging
                       to the 8100"

         REVISION     "202206270000Z"  -- June 27, 2022
         DESCRIPTION  "Updated with new R9Y04A and R9Y03A SKU's belonging
                       to 6100 and 6000 platforms respectively. Also updated
                       with new PSU used by R9Y03A and R9Y04A"

         REVISION     "202205260000Z"  -- May 26, 2022
         DESCRIPTION  "Updated with 6200M switch information"

         REVISION     "202201310000Z"  -- Jan 31, 2022
         DESCRIPTION  "Added new Distributed Services Module MIB"

         REVISION     "202111230000Z"  -- Nov 23, 2021
         DESCRIPTION  "Added new INTERFACE-MIB module"

         REVISION     "202111170000Z"  -- Nov 17, 2021
         DESCRIPTION  "Updated with 9300 SKU information"

         REVISION     "202111120000Z"  -- Nov 12, 2021
         DESCRIPTION  "Added new ProviderBridge-MIB info"

         REVISION     "202110220000Z"  -- Oct 22, 2021
         DESCRIPTION  "Updated with new 8325 PSU information"

         REVISION     "202108270000Z"  -- Aug 27, 2021
         DESCRIPTION  "Updated with 10000 SKU information"

         REVISION     "202108260000Z"  -- Aug 26, 2021
         DESCRIPTION  "Added 6400 Rev C chassis OID information."

         REVISION     "202106160000Z"  -- Jun 16, 2021"
         DESCRIPTION  "Updated with new SKU OIDs for Indy program"

         REVISION     "202105260000Z"  -- Mar 24, 2021
         DESCRIPTION  "Added MAC-NOTIFY MIB module."

         REVISION     "202104280000Z"  -- Apr 28, 2021
         DESCRIPTION  "Updated with 6000 switch information."

         REVISION     "202102240000Z"  -- Feb 24, 2021
         DESCRIPTION  "Updated with 6300M DC PSU OID information."

         REVISION     "202011200000Z"  -- Nov 20, 2020
         DESCRIPTION  "Added PORTVLAN MIB module."

         REVISION     "202011030000Z"  -- Nov 03, 2020
         DESCRIPTION  "Updated with 4100i PSU  OID information."

         REVISION     "202009210000Z"  -- Sep 21, 2020
         DESCRIPTION  "Updated with 6100 PSU  OID information."

         REVISION     "202008140000Z"  -- August 14, 2020
         DESCRIPTION  "Updated with fixed 8360 OID information."

         REVISION     "202006120000Z"  -- June 12, 2020
         DESCRIPTION  "Updated with fixed PSU OID information."

         REVISION     "202004130000Z"  -- Apr 13, 2020
         DESCRIPTION  "Updated with JL762A new Product OID information."

         REVISION     "202003170000Z"  -- Mar 17, 2020
         DESCRIPTION  "Added 8360 Product SKUs OID information."

         REVISION     "202001300000Z"  -- Jan 30, 2020
         DESCRIPTION  "Updated with JL687A new Product OID information."

         REVISION     "202001140000Z"  -- Jan 14, 2020
         DESCRIPTION  "Updated with 6200 switch information."

         REVISION     "202001060000Z"  -- Jan 06, 2020
         DESCRIPTION  "Updated with 6400 switch information."

         REVISION     "201911210000Z"  -- Nov 21, 2019
         DESCRIPTION  "Updated with 6100 switch information."

         REVISION     "201909260000Z"  -- Sep 26, 2019
         DESCRIPTION  "Updated with 6200 switch information."

         REVISION     "201908260000Z"  -- Aug 26, 2019
         DESCRIPTION  "Updated with 6400 switch information."

         REVISION     "201905140000Z"  -- May 14, 2019
         DESCRIPTION  "Updated with 6400 switch information."

         REVISION     "201904160000Z"  -- Apr 16, 2019
         DESCRIPTION  "Updated port vendor types."

         REVISION     "201904150000Z"  -- Apr 15, 2019
         DESCRIPTION  "Added LLDP MIB module."

         REVISION     "201812190000Z"  -- Dec 19, 2018
         DESCRIPTION  "Updated with 6300 switch information."

         REVISION     "201810100000Z"  -- Oct 10, 2018
         DESCRIPTION  "Added new 8325 switches and updated description
                       text for all 8325 switches"

         REVISION     "201804120000Z"  -- Apr 12, 2018
         DESCRIPTION  "Made changes to move VSX MIB under new OID tree."

         REVISION     "201804090000Z"  -- Apr 09, 2018
         DESCRIPTION  "Added new 8320 switches and updated description
                       text for all 8320 switches"

         REVISION     "201711280000Z"  -- Nov 28, 2017
         DESCRIPTION  "Added port vendor types"

         REVISION     "201711140000Z"  -- Nov 14, 2017
         DESCRIPTION  "Added RPM and Power sensors"

         REVISION     "201711020000Z"  -- Nov 2, 2017
         DESCRIPTION  "Added 8400 Rear Display Module"

         REVISION     "201710240000Z"  -- Oct 24, 2017
         DESCRIPTION  "Updated Aruba Wired MIB Object Names with a
                       standard convention"

         REVISION     "201708300000Z"  -- Aug 30, 2017
         DESCRIPTION  "Updated with 8320 switch information"

         REVISION     "201704110000Z"  -- Apr 11, 2017
         DESCRIPTION  "Updated with 8400 SKU information"

         ::= { hpe 4 }

hpe    OBJECT IDENTIFIER ::= { enterprises  47196 }

-- definition of HPENetworking Objects
-- reserving object with zero
reservedhpeNetworking OBJECT IDENTIFIER ::=  { hpeNetworking 0 }

-- grouping all wired devices under a separate group
wiredNetworkingDevices OBJECT IDENTIFIER ::= { hpeNetworking 1 }

-- categorization of MIB portions
arubaOS-CX OBJECT IDENTIFIER ::= { wiredNetworkingDevices 1 }

wndDeviceIds OBJECT IDENTIFIER ::= { arubaOS-CX 1 }

wndComponentIds OBJECT IDENTIFIER ::= { arubaOS-CX 2 }

wndFeatures OBJECT IDENTIFIER ::= { arubaOS-CX 3 }

-- detailing of products

arubaWiredSwitchJL375A OBJECT-IDENTITY
        STATUS      current
        DESCRIPTION "The authoritative identifier for the
                     JL375A Aruba 8400 8-slot chassis switch."
        ::= { wndDeviceIds 1 }

arubaWiredSwitchJL479A OBJECT-IDENTITY
        STATUS      current
        DESCRIPTION "The authoritative identifier for the
                     JL479A Aruba 8320 48p 10G SFP/SFP+ and 6p 40G QSFP+ chassis switch."
        ::= { wndDeviceIds 2 }

arubaWiredSwitchJL579A OBJECT-IDENTITY
        STATUS      current
        DESCRIPTION "The authoritative identifier for the
                     JL579A Aruba 8320 32p QSFP+ chassis switch."
        ::= { wndDeviceIds 3 }

arubaWiredSwitchJL581A OBJECT-IDENTITY
        STATUS      current
        DESCRIPTION "The authoritative identifier for the
                     JL581A Aruba 8320 48p 1G/10GBASE-T and 6p 40G QSFP+ chassis switch."
        ::= { wndDeviceIds 5 }

arubaWiredSwitchJL635A OBJECT-IDENTITY
        STATUS      current
        DESCRIPTION "The authoritative identifier for the
                     JL635A Aruba 8325 8325-48Y8C chassis switch."
        ::= { wndDeviceIds 50 }

arubaWiredSwitchS0G12A OBJECT-IDENTITY
        STATUS      current
        DESCRIPTION "The authoritative identifier for the
                     S0G12A HPE ANW 8325P-32C TAA Switch"
        ::= { wndDeviceIds 51 }

arubaWiredSwitchS4A48A OBJECT-IDENTITY
        STATUS      current
        DESCRIPTION "The authoritative identifier for the
                     S4A48A HPE ANW 8325P-32C Switch"
        ::= { wndDeviceIds 52 }

arubaWiredSwitchJL636A OBJECT-IDENTITY
        STATUS      current
        DESCRIPTION "The authoritative identifier for the
                     JL636A Aruba 8325 8325-32C chassis switch."
        ::= { wndDeviceIds 70 }

arubaWiredSwitchS4B20A OBJECT-IDENTITY
        STATUS      current
        DESCRIPTION "The authoritative identifier for thes
                     S4B20A HPE ANW 8325H 18Y 4C FB 4Fs 2PS Sw"
        ::= { wndDeviceIds 80 }

arubaWiredSwitchS4B21A OBJECT-IDENTITY
        STATUS      current
        DESCRIPTION "The authoritative identifier for the
                     S4B21A HPE ANW 8325H 18Y 4C BF 4Fs 2PS Sw"
        ::= { wndDeviceIds 81 }

arubaWiredSwitchS4B22A OBJECT-IDENTITY
        STATUS      current
        DESCRIPTION "The authoritative identifier for the
                     S4B22A HPE ANW 8325H 16C FB 4Fs 2PS Sw"
        ::= { wndDeviceIds 82 }

arubaWiredSwitchS4B23A OBJECT-IDENTITY
        STATUS      current
        DESCRIPTION "The authoritative identifier for the
                     S4B23A HPE ANW 8325H 16C BF 4Fs 2PS Sw"
        ::= { wndDeviceIds 83 }

arubaWiredSwitchS2T42A OBJECT-IDENTITY
        STATUS      current
        DESCRIPTION "The authoritative identifier for the
                     S2T42A HPE ANW 8325H 18Y 4C FB 4Fs 2PS TAA Sw"
        ::= { wndDeviceIds 84 }

arubaWiredSwitchS2T46A OBJECT-IDENTITY
        STATUS      current
        DESCRIPTION "The authoritative identifier for the
                     S2T46A HPE ANW 8325H 18Y 4C BF 4Fs 2PS TAA Sw"
        ::= { wndDeviceIds 85 }

arubaWiredSwitchS2T47A OBJECT-IDENTITY
        STATUS      current
        DESCRIPTION "The authoritative identifier for the
                     S2T47A HPE ANW 8325H 16C FB 4Fs 2PS TAA Sw"
        ::= { wndDeviceIds 86 }

arubaWiredSwitchS2T48A OBJECT-IDENTITY
        STATUS      current
        DESCRIPTION "The authoritative identifier for the
                     S2T48A HPE ANW 8325H 16C BF 4Fs 2PS TAA Sw"
        ::= { wndDeviceIds 87 }

arubaWiredSwitchJL658A OBJECT-IDENTITY
        STATUS      current
        DESCRIPTION "The authoritative identifier for the
                     Aruba 6300M 24SFP+/4SFP56 Swch."
        ::= { wndDeviceIds 100 }

arubaWiredSwitchJL659A OBJECT-IDENTITY
        STATUS      current
        DESCRIPTION "The authoritative identifier for the
                     Aruba 6300M 48SR PoE CLS6 /4SFP56 Swch."
        ::= { wndDeviceIds 101 }

arubaWiredSwitchJL660A OBJECT-IDENTITY
        STATUS      current
        DESCRIPTION "The authoritative identifier for the
                     Aruba 6300M 24SR PoECLS 6 /4SFP56 Swch."
       ::= { wndDeviceIds 102 }

arubaWiredSwitchJL661A OBJECT-IDENTITY
        STATUS      current
        DESCRIPTION "The authoritative identifier for the
                     Aruba 6300M 48G PoE CLS 4 /4SFP56 Swch."
       ::= { wndDeviceIds 103 }

arubaWiredSwitchJL662A OBJECT-IDENTITY
        STATUS      current
        DESCRIPTION "The authoritative identifier for the
                     Aruba 6300M 24G PoE CLS 4 /4SFP56 Swch."
       ::= { wndDeviceIds 104 }

arubaWiredSwitchJL663A OBJECT-IDENTITY
        STATUS      current
        DESCRIPTION "The authoritative identifier for the
                     Aruba 6300M 248G /4SFP56 Swch."
       ::= { wndDeviceIds 105 }

arubaWiredSwitchJL664A OBJECT-IDENTITY
        STATUS      current
        DESCRIPTION "The authoritative identifier for the
                     Aruba 6300M 24G /4SFP56 Swch."
       ::= { wndDeviceIds 106 }

arubaWiredSwitchJL665A OBJECT-IDENTITY
        STATUS      current
        DESCRIPTION "The authoritative identifier for the
                     Aruba 6300F 48G PoE CLS 4 /4SFP56 Swch."
       ::= { wndDeviceIds 107 }

arubaWiredSwitchJL666A OBJECT-IDENTITY
        STATUS      current
        DESCRIPTION "The authoritative identifier for the
                     Aruba 6300F 24G PoE CLS 4 /4SFP56 Swch."
       ::= { wndDeviceIds 108 }

arubaWiredSwitchJL667A OBJECT-IDENTITY
        STATUS      current
        DESCRIPTION "The authoritative identifier for the
                     Aruba 6300F 48G /4SFP56 Swch."
       ::= { wndDeviceIds 109 }

arubaWiredSwitchJL668A OBJECT-IDENTITY
        STATUS      current
        DESCRIPTION "The authoritative identifier for the
                     Aruba 6300F 24G /4SFP56 Swch."
       ::= { wndDeviceIds 110 }

arubaWiredSwitchJL762A OBJECT-IDENTITY
        STATUS      current
        DESCRIPTION "The authoritative identifier for the
                     Aruba 6300M 48G /4SFP56 BF Swch."
       ::= { wndDeviceIds 111 }

arubaWiredSwitchR8S89A OBJECT-IDENTITY
        STATUS      current
        DESCRIPTION "The authoritative identifier for the
                     Aruba 6300M 24SR CL6 PoE 2p50G 2p25G Sw."
       ::= { wndDeviceIds 116 }

arubaWiredSwitchR8S90A OBJECT-IDENTITY
        STATUS      current
        DESCRIPTION "The authoritative identifier for the
                     Aruba 6300M 48SR5 CL8 PoE 2p50G 2p25G Sw."
       ::= { wndDeviceIds 117 }

arubaWiredSwitchR8S91A OBJECT-IDENTITY
        STATUS      current
        DESCRIPTION "The authoritative identifier for the
                     Aruba 6300M 48SR5 CL6/CL8 2p50G 2p10G Sw."
       ::= { wndDeviceIds 118 }

arubaWiredSwitchR8S92A OBJECT-IDENTITY
        STATUS      current
        DESCRIPTION "The authoritative identifier for the
                     Aruba 6300M 24p SFP+ LRM 2p50G 2p25G Sw."
       ::= { wndDeviceIds 119 }

arubaWiredSwitchS3L75A OBJECT-IDENTITY
        STATUS      current
        DESCRIPTION "The authoritative identifier for the
                     HPE ANW 6300L 24SRX CL6 2L2Y Layer2 Sw."
       ::= { wndDeviceIds 1000 }

arubaWiredSwitchS3L76A OBJECT-IDENTITY
        STATUS      current
        DESCRIPTION "The authoritative identifier for the
                     HPE ANW 6300L 48SR5 CL8 2L2Y Layer2 Sw."
       ::= { wndDeviceIds 1001 }

arubaWiredSwitchS3L77A OBJECT-IDENTITY
        STATUS      current
        DESCRIPTION "The authoritative identifier for the
                     HPE ANW 6300L 48SR5 CL8/6 2L2P L2 Sw."
       ::= { wndDeviceIds 1002 }

arubaWiredSwitchS2P49A OBJECT-IDENTITY
        STATUS      current
        DESCRIPTION "The authoritative identifier for the
                     HPE ANW 6300L 24SRX CL6 2L2Y Layer2 TAA."
       ::= { wndDeviceIds 1003 }

arubaWiredSwitchS2P50A OBJECT-IDENTITY
        STATUS      current
        DESCRIPTION "The authoritative identifier for the
                     HPE ANW 6300L 48SR5 CL8 2L2Y Layer2 TAA."
       ::= { wndDeviceIds 1004 }

arubaWiredSwitchS2P51A OBJECT-IDENTITY
        STATUS      current
        DESCRIPTION "The authoritative identifier for the
                     HPE ANW 6300L 48SR5 CL8/6 2L2P L2 TAA."
       ::= { wndDeviceIds 1005 }

arubaWiredSwitchS0E91A OBJECT-IDENTITY
        STATUS      current
        DESCRIPTION "The authoritative identifier for the
                     Aruba 6300M 48SR10 CL8 PoE 4p100G Sw."
       ::= { wndDeviceIds 120 }

arubaWiredSwitchS0X44A OBJECT-IDENTITY
        STATUS      current
        DESCRIPTION "The authoritative identifier for the
                     Aruba 6300M 48SR10 CL8 PoE 4p100G TAA Sw."
       ::= { wndDeviceIds 121 }

arubaWiredSwitchS0F99A OBJECT-IDENTITY
        STATUS      current
        DESCRIPTION "The authoritative identifier for the
                     HPE ANW 6300M 24G CL4 PoE 4L TAA Sw."
        ::= { wndDeviceIds 122 }

arubaWiredSwitchS0G00A OBJECT-IDENTITY
        STATUS      current
        DESCRIPTION "The authoritative identifier for the
                     HPE ANW 6300M 48G 4L TAA Switch."
        ::= { wndDeviceIds 123 }

arubaWiredSwitchS0G01A OBJECT-IDENTITY
        STATUS      current
        DESCRIPTION "The authoritative identifier for the
                     HPE ANW 6300M 24G 4L TAA Switch."
        ::= { wndDeviceIds 124 }

arubaWiredSwitchS0G02A OBJECT-IDENTITY
        STATUS      current
        DESCRIPTION "The authoritative identifier for the
                     HPE ANW 6300M 48G 4L Pwr2Prt 2Fs TAA Bdl."
        ::= { wndDeviceIds 125 }

arubaWiredSwitchS0G03A OBJECT-IDENTITY
        STATUS      current
        DESCRIPTION "The authoritative identifier for the
                     HPE ANW 6300M 24P 4L TAA Switch."
        ::= { wndDeviceIds 126 }

arubaWiredSwitchS0G04A OBJECT-IDENTITY
        STATUS      current
        DESCRIPTION "The authoritative identifier for the
                     HPE ANW 6300M 48SR5 CL6 PoE 4L TAA Sw."
        ::= { wndDeviceIds 127 }

arubaWiredSwitchS0G05A OBJECT-IDENTITY
        STATUS      current
        DESCRIPTION "The authoritative identifier for the
                     HPE ANW 6300M 24SR5 CL6 PoE 4L TAA Sw."
        ::= { wndDeviceIds 128 }

arubaWiredSwitchS0G06A OBJECT-IDENTITY
        STATUS      current
        DESCRIPTION "The authoritative identifier for the
                     HPE ANW 6300M 48G CL4 PoE 4L TAA Sw."
        ::= { wndDeviceIds 129 }

arubaWiredSwitchS0G95A OBJECT-IDENTITY
        STATUS      current
        DESCRIPTION "The authoritative identifier for the
                     HPE ANW 6300F 48G CL4 4L TAA Sw."
        ::= { wndDeviceIds 130 }

arubaWiredSwitchS0G96A OBJECT-IDENTITY
        STATUS      current
        DESCRIPTION "The authoritative identifier for the
                     HPE ANW 6300F 24G CL4 4L TAA Sw."
        ::= { wndDeviceIds 131 }

arubaWiredSwitchS0G97A OBJECT-IDENTITY
        STATUS      current
        DESCRIPTION "The authoritative identifier for the
                     HPE ANW 6300F 48G 4L TAA Sw."
        ::= { wndDeviceIds 132 }

arubaWiredSwitchS0G98A OBJECT-IDENTITY
        STATUS      current
        DESCRIPTION "The authoritative identifier for the
                     HPE ANW 6300F 24G 4L TAA Sw."
        ::= { wndDeviceIds 133 }

arubaWiredSwitchS4P41A OBJECT-IDENTITY
        STATUS      current
        DESCRIPTION "The authoritative identifier for the
                     HPE ANW 6300M 32G 16SR5 2L 2Y Msec Sw."
        ::= { wndDeviceIds 1050 }

arubaWiredSwitchS4P42A OBJECT-IDENTITY
        STATUS      current
        DESCRIPTION "The authoritative identifier for the
                     HPE ANW 6300M 32SR5 8P 2L 2Y Msec Sw."
        ::= { wndDeviceIds 1051 }

arubaWiredSwitchS4P43A OBJECT-IDENTITY
        STATUS      current
        DESCRIPTION "The authoritative identifier for the
                     HPE ANW 6300M 48F 2L 2Y Sw."
        ::= { wndDeviceIds 1052 }

arubaWiredSwitchS4P44A OBJECT-IDENTITY
        STATUS      current
        DESCRIPTION "The authoritative identifier for the
                     HPE ANW 6300M 24F 2L 2Y Sw."
        ::= { wndDeviceIds 1053 }

arubaWiredSwitchS4P45A OBJECT-IDENTITY
        STATUS      current
        DESCRIPTION "The authoritative identifier for the
                     HPE ANW 6300M 32G 16SR5 CL8 2L 2Y TAA Sw."
        ::= { wndDeviceIds 1054 }

arubaWiredSwitchS4P46A OBJECT-IDENTITY
        STATUS      current
        DESCRIPTION "The authoritative identifier for the
                     HPE ANW 6300M 32SR5 8P 2L 2Y Msec TAA Sw."
        ::= { wndDeviceIds 1055 }

arubaWiredSwitchS4P47A OBJECT-IDENTITY
        STATUS      current
        DESCRIPTION "The authoritative identifier for the
                     HPE ANW 6300M 48F 2L 2Y TAA Sw."
        ::= { wndDeviceIds 1056 }

arubaWiredSwitchS4P48A OBJECT-IDENTITY
        STATUS      current
        DESCRIPTION "The authoritative identifier for the
                     HPE ANW 6300M 24F 2L 2Y TAA Sw."
        ::= { wndDeviceIds 1057 }

arubaWiredSwitchR0X24A OBJECT-IDENTITY
        STATUS      current
        DESCRIPTION "The authoritative identifier for the
                     Aruba 6405 Chassis."
        ::= { wndDeviceIds 150 }

arubaWiredSwitchR0X25A OBJECT-IDENTITY
        STATUS      current
        DESCRIPTION "The authoritative identifier for the
                     Aruba 6410 Chassis."
        ::= { wndDeviceIds 151 }

arubaWiredSwitchR0X24C OBJECT-IDENTITY
        STATUS      current
        DESCRIPTION "The authoritative identifier for the
                     Aruba 6405 Chassis."
        ::= { wndDeviceIds 160 }

arubaWiredSwitchR0X25C OBJECT-IDENTITY
        STATUS      current
        DESCRIPTION "The authoritative identifier for the
                     Aruba 6410 Chassis."
        ::= { wndDeviceIds 161 }

arubaWiredSwitchJL675A OBJECT-IDENTITY
        STATUS      current
        DESCRIPTION "The authoritative identifier for the
                     Aruba 6100 48G CLS4 4SFP+ 370W."
       ::= { wndDeviceIds 250 }

arubaWiredSwitchJL676A OBJECT-IDENTITY
        STATUS      current
        DESCRIPTION "The authoritative identifier for the
                     Aruba 6100 48G 4SFP+."
       ::= { wndDeviceIds 251 }

arubaWiredSwitchJL677A OBJECT-IDENTITY
        STATUS      current
        DESCRIPTION "The authoritative identifier for the
                     Aruba 6100 24G CLS4 4SFP+ 370W."
       ::= { wndDeviceIds 252 }

arubaWiredSwitchJL678A OBJECT-IDENTITY
        STATUS      current
        DESCRIPTION "The authoritative identifier for the
                     Aruba 6100 24G 4SFP+."
       ::= { wndDeviceIds 253 }

arubaWiredSwitchJL679A OBJECT-IDENTITY
        STATUS      current
        DESCRIPTION "The authoritative identifier for the
                     Aruba 6100 12G CLS4 2G/2SFP+ 139W."
       ::= { wndDeviceIds 254 }

arubaWiredSwitchR9Y04A OBJECT-IDENTITY
        STATUS      current
        DESCRIPTION "The authoritative identifier for the
                     Aruba 6100 48G Class4 PoE 4SFP+ 740W Switch."
       ::= { wndDeviceIds 260 }

arubaWiredSwitchS4U55A OBJECT-IDENTITY
        STATUS      current
        DESCRIPTION "The authoritative identifier for the
                     HPE ANW 6100 48G CL4 4P 370W MII Switch."
       ::= { wndDeviceIds 261 }

arubaWiredSwitchS4U56A OBJECT-IDENTITY
        STATUS      current
        DESCRIPTION "The authoritative identifier for the
                     HPE ANW 6100 48G 4P MII Switch."
       ::= { wndDeviceIds 262 }

arubaWiredSwitchS4U57A OBJECT-IDENTITY
        STATUS      current
        DESCRIPTION "The authoritative identifier for the
                     HPE ANW 6100 24G CL4 4P 370W MII Switch."
       ::= { wndDeviceIds 263 }

arubaWiredSwitchS4U58A OBJECT-IDENTITY
        STATUS      current
        DESCRIPTION "The authoritative identifier for the
                     HPE ANW 6100 24G 4P MII Switch."
       ::= { wndDeviceIds 264 }

arubaWiredSwitchR8N85A OBJECT-IDENTITY
        STATUS      current
        DESCRIPTION "The authoritative identifier for the
                     Aruba 6000 48G CLS4 4SFP 370W."
       ::= { wndDeviceIds 270 }

arubaWiredSwitchR8N86A OBJECT-IDENTITY
        STATUS      current
        DESCRIPTION "The authoritative identifier for the
                     Aruba 6000 48G 4SFP."
       ::= { wndDeviceIds 271 }

arubaWiredSwitchR8N87A OBJECT-IDENTITY
        STATUS      current
        DESCRIPTION "The authoritative identifier for the
                     Aruba 6000 24G CLS4 4SFP 370W."
       ::= { wndDeviceIds 272 }

arubaWiredSwitchR8N88A OBJECT-IDENTITY
        STATUS      current
        DESCRIPTION "The authoritative identifier for the
                     Aruba 6000 24G 4SFP."
       ::= { wndDeviceIds 273 }

arubaWiredSwitchR8N89A OBJECT-IDENTITY
        STATUS      current
        DESCRIPTION "The authoritative identifier for the
                     Aruba 6000 12G CLS4 2G/2SFP 139W."
       ::= { wndDeviceIds 274 }

arubaWiredSwitchR8N85B OBJECT-IDENTITY
        STATUS      current
        DESCRIPTION "The authoritative identifier for the
                     HPE ANW 6000 48G CL4 4F 370W Sw."
       ::= { wndDeviceIds 275 }

arubaWiredSwitchR8N86B OBJECT-IDENTITY
        STATUS      current
        DESCRIPTION "The authoritative identifier for the
                     HPE ANW 6000 48G 4F Sw."
       ::= { wndDeviceIds 276 }

arubaWiredSwitchR8N87B OBJECT-IDENTITY
        STATUS      current
        DESCRIPTION "The authoritative identifier for the
                     HPE ANW 6000 24G CL4 4F 370W Sw."
       ::= { wndDeviceIds 277 }

arubaWiredSwitchR8N88B OBJECT-IDENTITY
        STATUS      current
        DESCRIPTION "The authoritative identifier for the
                     HPE ANW 6000 24G 4F Sw."
       ::= { wndDeviceIds 278 }

arubaWiredSwitchR8N89B OBJECT-IDENTITY
        STATUS      current
        DESCRIPTION "The authoritative identifier for the
                     HPE ANW 6000 12G CL4 2F 139W Sw."
       ::= { wndDeviceIds 279 }

arubaWiredSwitchR9Y03A OBJECT-IDENTITY
        STATUS      current
        DESCRIPTION "The authoritative identifier for the
                     Aruba 6000 48G Class4 PoE 4SFP 740W Switch."
       ::= { wndDeviceIds 280 }

arubaWiredSwitchS4U59A OBJECT-IDENTITY
        STATUS      current
        DESCRIPTION "The authoritative identifier for the
                     HPE ANW 6000 48G CL4 4F 370W MII Switch."
       ::= { wndDeviceIds 281 }

arubaWiredSwitchS4U60A OBJECT-IDENTITY
        STATUS      current
        DESCRIPTION "The authoritative identifier for the
                     HPE ANW 6000 48G 4F MII Switch."
       ::= { wndDeviceIds 282 }

arubaWiredSwitchS4U61A OBJECT-IDENTITY
        STATUS      current
        DESCRIPTION "The authoritative identifier for the
                     HPE ANW 6000 24G CL4 4F 370W MII Switch."
       ::= { wndDeviceIds 283 }

arubaWiredSwitchS4U62A OBJECT-IDENTITY
        STATUS      current
        DESCRIPTION "The authoritative identifier for the
                     HPE ANW 6000 24G 4F MII Switch."
       ::= { wndDeviceIds 284 }

arubaWiredSwitchR9Y03B OBJECT-IDENTITY
        STATUS      current
        DESCRIPTION "The authoritative identifier for the
                     HPE ANW 6000 48G CL4 4F 740W Sw."
       ::= { wndDeviceIds 285 }

arubaWiredSwitchS4R20A OBJECT-IDENTITY
        STATUS      current
        DESCRIPTION "The authoritative identifier for the
                     HPE ANW 6000 48G CL4 4F 740W TAA Sw."
       ::= { wndDeviceIds 286 }

arubaWiredSwitchS4R21A OBJECT-IDENTITY
        STATUS      current
        DESCRIPTION "The authoritative identifier for the
                     HPE ANW 6000 12G CL4 2F 139W TAA Sw."
       ::= { wndDeviceIds 287 }

arubaWiredSwitchS4R22A OBJECT-IDENTITY
        STATUS      current
        DESCRIPTION "The authoritative identifier for the
                     HPE ANW 6000 8G 2F Sw."
       ::= { wndDeviceIds 288 }

arubaWiredSwitchS4R23A OBJECT-IDENTITY
        STATUS      current
        DESCRIPTION "The authoritative identifier for the
                     HPE ANW 6000 8G CL4 2F 67W Sw."
       ::= { wndDeviceIds 289 }

arubaWiredSwitchS4R24A OBJECT-IDENTITY
        STATUS      current
        DESCRIPTION "The authoritative identifier for the
                     HPE ANW 6000 48G CL4 4F 370W TAA Sw."
       ::= { wndDeviceIds 290 }

arubaWiredSwitchS4R25A OBJECT-IDENTITY
        STATUS      current
        DESCRIPTION "The authoritative identifier for the
                     HPE ANW 6000 48G 4F TAA Sw."
       ::= { wndDeviceIds 291 }

arubaWiredSwitchS4R26A OBJECT-IDENTITY
        STATUS      current
        DESCRIPTION "The authoritative identifier for the
                     HPE ANW 6000 24G CL4 4F 370W TAA Sw."
       ::= { wndDeviceIds 292 }

arubaWiredSwitchS4R27A OBJECT-IDENTITY
        STATUS      current
        DESCRIPTION "The authoritative identifier for the
                     HPE ANW 6000 24G 4F TAA Sw."
       ::= { wndDeviceIds 293 }

arubaWiredSwitchS4R28A OBJECT-IDENTITY
        STATUS      current
        DESCRIPTION "The authoritative identifier for the
                     HPE ANW 6000 8G 2F TAA Sw."
       ::= { wndDeviceIds 294 }

arubaWiredSwitchS4R29A OBJECT-IDENTITY
        STATUS      current
        DESCRIPTION "The authoritative identifier for the
                     HPE ANW 6000 8G CL4 2F 67W TAA Sw."
       ::= { wndDeviceIds 295 }

arubaWiredSwitchJL724A OBJECT-IDENTITY
        STATUS      current
        DESCRIPTION "The authoritative identifier for the
                     Aruba 6200F 24G 4SFP+ Swch."
       ::= { wndDeviceIds 300 }

arubaWiredSwitchJL725A OBJECT-IDENTITY
        STATUS      current
        DESCRIPTION "The authoritative identifier for the
                     Aruba 6200F 24G CL4 4SFP+370W Swch."
       ::= { wndDeviceIds 301 }

arubaWiredSwitchJL726A OBJECT-IDENTITY
        STATUS      current
        DESCRIPTION "The authoritative identifier for the
                     Aruba 6200F 48G 4SFP+ Swch."
       ::= { wndDeviceIds 302 }

arubaWiredSwitchJL727A OBJECT-IDENTITY
        STATUS      current
        DESCRIPTION "The authoritative identifier for the
                     Aruba 6200F 48G CL4 4SFP+370W Swch."
       ::= { wndDeviceIds 303 }

arubaWiredSwitchJL728A OBJECT-IDENTITY
        STATUS      current
        DESCRIPTION "The authoritative identifier for the
                     Aruba 6200F 48G CL4 4SFP+740W Swch."
       ::= { wndDeviceIds 304 }

arubaWiredSwitchJL724B OBJECT-IDENTITY
        STATUS      current
        DESCRIPTION "The authoritative identifier for the
                     HPE ANW 6200F 24G 4SFP+ Sw."
       ::= { wndDeviceIds 305 }

arubaWiredSwitchJL725B OBJECT-IDENTITY
        STATUS      current
        DESCRIPTION "The authoritative identifier for the
                     HPE ANW 6200F 24G C4 4SFP+370W Sw."
       ::= { wndDeviceIds 306 }

arubaWiredSwitchJL726B OBJECT-IDENTITY
        STATUS      current
        DESCRIPTION "The authoritative identifier for the
                     HPE ANW 6200F 48G 4SFP+ Sw."
       ::= { wndDeviceIds 307 }

arubaWiredSwitchJL727B OBJECT-IDENTITY
        STATUS      current
        DESCRIPTION "The authoritative identifier for the
                     HPE ANW 6200F 48G C4 4SFP+370W Sw."
       ::= { wndDeviceIds 308 }

arubaWiredSwitchJL728B OBJECT-IDENTITY
        STATUS      current
        DESCRIPTION "The authoritative identifier for the
                     HPE ANW 6200F 48G C4 4SFP+740W Sw."
       ::= { wndDeviceIds 309 }

arubaWiredSwitchS0M81A OBJECT-IDENTITY
        STATUS      current
        DESCRIPTION "The authoritative identifier for the
                     HPE ANW 6200F 24G 4SFP Sw."
       ::= { wndDeviceIds 310 }

arubaWiredSwitchS0M82A OBJECT-IDENTITY
        STATUS      current
        DESCRIPTION "The authoritative identifier for the
                     HPE ANW 6200F 24G C4 4SFP 370W Sw."
       ::= { wndDeviceIds 311 }

arubaWiredSwitchS0M83A OBJECT-IDENTITY
        STATUS      current
        DESCRIPTION "The authoritative identifier for the
                     HPE ANW 6200F 48G 4SFP Sw."
       ::= { wndDeviceIds 312 }

arubaWiredSwitchS0M84A OBJECT-IDENTITY
        STATUS      current
        DESCRIPTION "The authoritative identifier for the
                     HPE ANW 6200F 48G C4 4SFP 370W Sw."
       ::= { wndDeviceIds 313 }

arubaWiredSwitchS0M85A OBJECT-IDENTITY
        STATUS      current
        DESCRIPTION "The authoritative identifier for the
                     HPE ANW 6200F 48G C4 4SFP 740W Sw."
       ::= { wndDeviceIds 314 }

arubaWiredSwitchS0M86A OBJECT-IDENTITY
        STATUS      current
        DESCRIPTION "The authoritative identifier for the
                     HPE NW 6200F 24G 4SFP+ T Sw."
       ::= { wndDeviceIds 315 }

arubaWiredSwitchS0M87A OBJECT-IDENTITY
        STATUS      current
        DESCRIPTION "The authoritative identifier for the
                     HPE NW 6200F 24G C4 4SFP+370W T Sw."
       ::= { wndDeviceIds 316 }

arubaWiredSwitchS0M88A OBJECT-IDENTITY
        STATUS      current
        DESCRIPTION "The authoritative identifier for the
                     HPE NW 6200F 48G 4SFP+ T Sw."
       ::= { wndDeviceIds 317 }

arubaWiredSwitchS0M89A OBJECT-IDENTITY
        STATUS      current
        DESCRIPTION "The authoritative identifier for the
                     HPE NW 6200F 48G C4 4SFP+370W T Sw."
       ::= { wndDeviceIds 318 }

arubaWiredSwitchS0M90A OBJECT-IDENTITY
        STATUS      current
        DESCRIPTION "The authoritative identifier for the
                     HPE NW 6200F 48G C4 4SFP+740W T Sw."
       ::= { wndDeviceIds 319 }

arubaWiredSwitchS4U63A OBJECT-IDENTITY
        STATUS      current
        DESCRIPTION "The authoritative identifier for the
                     HPE ANW 6200F 24G 4P MII Switch."
       ::= { wndDeviceIds 333 }

arubaWiredSwitchS4U64A OBJECT-IDENTITY
        STATUS      current
        DESCRIPTION "The authoritative identifier for the
                     HPE ANW 6200F 24G CL4 4P 370W MII Switch."
       ::= { wndDeviceIds 334 }

arubaWiredSwitchS4U65A OBJECT-IDENTITY
        STATUS      current
        DESCRIPTION "The authoritative identifier for the
                     HPE ANW 2930F 48G 4P MII Switch."
       ::= { wndDeviceIds 335 }

arubaWiredSwitchS4U66A OBJECT-IDENTITY
        STATUS      current
        DESCRIPTION "The authoritative identifier for the
                     HPE ANW 2930F 48G CL4 4P 370W MII Switch."
       ::= { wndDeviceIds 336 }

arubaWiredSwitchS4U67A OBJECT-IDENTITY
        STATUS      current
        DESCRIPTION "The authoritative identifier for the
                     HPE ANW 2930F 48G CL4 4P 740W MII Switch."
       ::= { wndDeviceIds 337 }

arubaWiredSwitchS0G13A OBJECT-IDENTITY
        STATUS      current
        DESCRIPTION "The authoritative identifier for the
                     HPE NW 6200F 24G 4SFP T Sw."
       ::= { wndDeviceIds 341 }

arubaWiredSwitchS0G14A OBJECT-IDENTITY
        STATUS      current
        DESCRIPTION "The authoritative identifier for the
                     HPE NW 6200F 24G C4 4SFP 370W T Sw."
       ::= { wndDeviceIds 342 }

arubaWiredSwitchS0G15A OBJECT-IDENTITY
        STATUS      current
        DESCRIPTION "The authoritative identifier for the
                     HPE NW 6200F 48G 4SFP T Sw."
       ::= { wndDeviceIds 343 }

arubaWiredSwitchS0G16A OBJECT-IDENTITY
        STATUS      current
        DESCRIPTION "The authoritative identifier for the
                     HPE NW 6200F 48G C4 4SFP370W T Sw."
       ::= { wndDeviceIds 344 }

arubaWiredSwitchS0G17A OBJECT-IDENTITY
        STATUS      current
        DESCRIPTION "The authoritative identifier for the
                     HPE NW 6200F 48G C4 4SFP740W T Sw."
       ::= { wndDeviceIds 345 }

arubaWiredSwitchR8Q67A OBJECT-IDENTITY
        STATUS      current
        DESCRIPTION "The authoritative identifier for the
                     Aruba 6200M 24G 4SFP+ Sw."
       ::= { wndDeviceIds 321 }

arubaWiredSwitchR8Q68A OBJECT-IDENTITY
        STATUS      current
        DESCRIPTION "The authoritative identifier for the
                     Aruba 6200M 24G CL4 PoE 4SFP+ Sw."
       ::= { wndDeviceIds 322 }

arubaWiredSwitchR8Q69A OBJECT-IDENTITY
        STATUS      current
        DESCRIPTION "The authoritative identifier for the
                     Aruba 6200M 48G 4SFP+ Sw."
       ::= { wndDeviceIds 323 }

arubaWiredSwitchR8Q70A OBJECT-IDENTITY
        STATUS      current
        DESCRIPTION "The authoritative identifier for the
                     Aruba 6200M 48G CL4 PoE 4SFP+ Sw."
       ::= { wndDeviceIds 324 }

arubaWiredSwitchR8Q71A OBJECT-IDENTITY
        STATUS      current
        DESCRIPTION "The authoritative identifier for the
                     Aruba 6200M 36G 12SR5 CL6 PoE 4SFP+ Sw."
       ::= { wndDeviceIds 325 }

arubaWiredSwitchR8Q72A OBJECT-IDENTITY
        STATUS      current
        DESCRIPTION "The authoritative identifier for the
                     Aruba 6200F 12G CL4 2G/2SFP+ 139W."
       ::= { wndDeviceIds 326 }

arubaWiredSwitchR8V08A OBJECT-IDENTITY
        STATUS      current
        DESCRIPTION "The authoritative identifier for the
                     Aruba 6200M 24G 4SFP+ TAA Sw."
       ::= { wndDeviceIds 327 }

arubaWiredSwitchR8V09A OBJECT-IDENTITY
        STATUS      current
        DESCRIPTION "The authoritative identifier for the
                     Aruba 6200M 24G CL4 PoE 4SFP+ TAA Sw."
       ::= { wndDeviceIds 328 }

arubaWiredSwitchR8V10A OBJECT-IDENTITY
        STATUS      current
        DESCRIPTION "The authoritative identifier for the
                     Aruba 6200M 48G 4SFP+ TAA Sw."
       ::= { wndDeviceIds 329 }

arubaWiredSwitchR8V11A OBJECT-IDENTITY
        STATUS      current
        DESCRIPTION "The authoritative identifier for the
                     Aruba 6200M 48G CL4 PoE 4SFP+ TAA Sw."
       ::= { wndDeviceIds 330 }

arubaWiredSwitchR8V12A OBJECT-IDENTITY
        STATUS      current
        DESCRIPTION "The authoritative identifier for the
                     Aruba 6200M 36G 12SR5 CL6 4SFP+ TAA Sw."
       ::= { wndDeviceIds 331 }

arubaWiredSwitchR8V13A OBJECT-IDENTITY
        STATUS      current
        DESCRIPTION "The authoritative identifier for the
                     Aruba 6200F 12G CL4 2G/2SFP+TAA Sw."
       ::= { wndDeviceIds 332 }

arubaWiredSwitchJL717A OBJECT-IDENTITY
        STATUS      current
        DESCRIPTION "The authoritative identifier for the Aruba 8360
        32p 1/10/25G SFP/SFP+/SFP28 and 4p 40/100G QSFP+/QSFP28 switch."
       ::= { wndDeviceIds 400 }

arubaWiredSwitchJL718A OBJECT-IDENTITY
        STATUS      current
        DESCRIPTION "The authoritative identifier for the Aruba 8360
        16p 1/10/25G SFP/SFP+/SFP28 and 2p 40/100G QSFP+/QSFP28 switch."
       ::= { wndDeviceIds 401 }

arubaWiredSwitchJL719A OBJECT-IDENTITY
        STATUS      current
        DESCRIPTION "The authoritative identifier for the Aruba 8360
        48p 1/10/25G SFP/SFP+/SFP28 and 6p 40/100G QSFP+/QSFP28 switch."
        ::= { wndDeviceIds 402 }

arubaWiredSwitchJL720A OBJECT-IDENTITY
        STATUS      current
        DESCRIPTION "The authoritative identifier for the Aruba 8360
        48p 10GBASE-T and 4p 40/100G QSFP+/QSFP28 switch."
       ::= { wndDeviceIds 403 }

arubaWiredSwitchJL721A OBJECT-IDENTITY
        STATUS      current
        DESCRIPTION "The authoritative identifier for the Aruba 8360
        12p 40/100G QSFP+/QSFP28 switch."
       ::= { wndDeviceIds 404 }

arubaWiredSwitchJL722A OBJECT-IDENTITY
        STATUS      current
        DESCRIPTION "The authoritative identifier for the Aruba 8360
        24p 10G SFP/SFP+ and 2p 40/100G QSFP+/QSFP28 switch."
       ::= { wndDeviceIds 405 }

arubaWiredSwitchJL717C OBJECT-IDENTITY
        STATUS      current
        DESCRIPTION "The authoritative identifier for the Aruba 8360
        32p 1/10/25G SFP/SFP+/SFP28 and 4p 40/100G QSFP+/QSFP28 switch."
       ::= { wndDeviceIds 420 }

arubaWiredSwitchJL718C OBJECT-IDENTITY
        STATUS      current
        DESCRIPTION "The authoritative identifier for the Aruba 8360
        16p 1/10/25G SFP/SFP+/SFP28 and 2p 40/100G QSFP+/QSFP28 switch."
       ::= { wndDeviceIds 421 }

arubaWiredSwitchJL719C OBJECT-IDENTITY
        STATUS      current
        DESCRIPTION "The authoritative identifier for the Aruba 8360
        48p 1/10/25G SFP/SFP+/SFP28 and 6p 40/100G QSFP+/QSFP28 switch."
        ::= { wndDeviceIds 422 }

arubaWiredSwitchJL720C OBJECT-IDENTITY
        STATUS      current
        DESCRIPTION "The authoritative identifier for the Aruba 8360
        48p 10GBASE-T and 4p 40/100G QSFP+/QSFP28 switch."
       ::= { wndDeviceIds 423 }

arubaWiredSwitchJL721C OBJECT-IDENTITY
        STATUS      current
        DESCRIPTION "The authoritative identifier for the Aruba 8360
        12p 40/100G QSFP+/QSFP28 switch."
       ::= { wndDeviceIds 424 }

arubaWiredSwitchJL722C OBJECT-IDENTITY
        STATUS      current
        DESCRIPTION "The authoritative identifier for the Aruba 8360
        24p 10G SFP/SFP+ and 2p 40/100G QSFP+/QSFP28 switch."
       ::= { wndDeviceIds 425 }

arubaWiredSwitchJL817A OBJECT-IDENTITY
        STATUS      current
        DESCRIPTION "The authoritative identifier for the Aruba 4100i
        12-port 1GbE (8-port Class 4 POE and 4-port Class 6 POE)
        2-port SFP+ DIN Mount Switch."
       ::= { wndDeviceIds 450 }

arubaWiredSwitchJL818A OBJECT-IDENTITY
        STATUS      current
        DESCRIPTION "The authoritative identifier for the Aruba 4100i
        24-port 1GbE (20-port Class 4 POE and 4-port Class 6 POE)
        4-port SFP+ Switch."
       ::= { wndDeviceIds 451 }

arubaWiredSwitchR8S96A OBJECT-IDENTITY
        STATUS      current
        DESCRIPTION "The authoritative identifier for the Aruba CX
        10000-48Y6C Distributed Services Switch"
       ::= { wndDeviceIds 600 }

arubaWiredSwitchS4K80A OBJECT-IDENTITY
        STATUS      current
        DESCRIPTION "The authoritative identifier for the HPE Aruba
        Networking CX 10000-48p SFP28 10G/25G 6p QSFP28 100G TAA switch"
       ::= { wndDeviceIds 601 }

arubaWiredSwitchS4R58A OBJECT-IDENTITY
        STATUS      current
        DESCRIPTION "The authoritative identifier for the HPE Aruba
        Networking CX 10040 Field Replacement Unit Switch"
       ::= { wndDeviceIds 630 }

arubaWiredSwitchS4R59A OBJECT-IDENTITY
        STATUS      current
        DESCRIPTION "The authoritative identifier for the HPE Aruba
        Networking CX 10040 TAA Field Replacement Unit Switch"
       ::= { wndDeviceIds 631 }

arubaWiredSwitchR8Z96A OBJECT-IDENTITY
        STATUS      current
        DESCRIPTION "The authoritative identifier for the Aruba
        9300-32D 32p 400G 2p 10g Switch"
       ::= { wndDeviceIds 700 }

arubaWiredSwitchS0F95A OBJECT-IDENTITY
        STATUS      current
        DESCRIPTION "The authoritative identifier for the HPE Aruba Networking
                    9300S 32P QSFP28 100G 8p QSFP-DD 400G TAA Switch"
       ::= { wndDeviceIds 710 }

arubaWiredSwitchS0F96A OBJECT-IDENTITY
        STATUS      current
        DESCRIPTION "The authoritative identifier for the HPE Aruba Networking
                     9300S 32P QSFP28 100G 8p QSFP-DD 400G Switch"
       ::= { wndDeviceIds 711 }

arubaWiredSwitchR9W94A OBJECT-IDENTITY
        STATUS      current
        DESCRIPTION "The authoritative identifier for the Aruba
        8100 24x10G SFP+ 4x40/100G QSFP28 Switch"
       ::= { wndDeviceIds 800 }

arubaWiredSwitchR9W95A OBJECT-IDENTITY
        STATUS      current
        DESCRIPTION "The authoritative identifier for the Aruba
        8100 24x10G Base-T 4x10G SFP+ 4x40/100G QSFP28 Switch"
       ::= { wndDeviceIds 801 }

arubaWiredSwitchR9W96A OBJECT-IDENTITY
        STATUS      current
        DESCRIPTION "The authoritative identifier for the Aruba
        8100 48x10G SFP+ 4x40/100G QSFP28 Switch"
       ::= { wndDeviceIds 802 }

arubaWiredSwitchR9W97A OBJECT-IDENTITY
        STATUS      current
        DESCRIPTION "The authoritative identifier for the Aruba
        8100 40x10G Base-T 8x10G SFP+ 4x40/100G QSFP28 Switch"
       ::= { wndDeviceIds 803 }

arubaWiredSwitchS0U60A OBJECT-IDENTITY
        STATUS      current
        DESCRIPTION "The authoritative identifier for the
                     HPE ANW 5420 6-slot Chassis."
        ::= { wndDeviceIds 900 }

arubaWiredSwitchS0U70A OBJECT-IDENTITY
        STATUS      current
        DESCRIPTION "The authoritative identifier for the
                     HPE ANW 5420 6-slot TAA Chassis."
        ::= { wndDeviceIds 901 }

-- sensors are sub type of parts

wndSensors  OBJECT IDENTIFIER ::= { wndComponentIds 1 }

arubaWiredTemperatureSensor OBJECT-IDENTITY
        STATUS      current
        DESCRIPTION "Identifier for a temperature sensor type."
        ::= { wndSensors 1 }

arubaWiredRPMSensor OBJECT-IDENTITY
        STATUS      current
        DESCRIPTION "Identifier for a fan RPM sensor type."
        ::= { wndSensors 2 }

arubaWiredPowerSensor OBJECT-IDENTITY
        STATUS      current
        DESCRIPTION "Identifier for a PSU power sensor type."
        ::= { wndSensors 3 }

-- slots are sub-type of parts

wndSlots  OBJECT IDENTIFIER ::= { wndComponentIds 2 }

arubaWiredSwitch8400FanTraySlot OBJECT-IDENTITY
        STATUS      current
        DESCRIPTION "Represents slot for Aruba X731 Fan Tray. "
        ::= { wndSlots 1 }

arubaWiredSwitch8400PowerSupplySlot OBJECT-IDENTITY
        STATUS      current
        DESCRIPTION "The authoritative identifier for a
                    power supply bay in an Aruba 8400 switch
                    chassis. "
        ::= { wndSlots 2 }

arubaWiredSwitch8400ManagementModuleSlot OBJECT-IDENTITY
        STATUS      current
        DESCRIPTION "The authoritative identifier for a
                    Management Module bay in a Aruba 8400 switch. "
        ::= { wndSlots 3 }

arubaWiredSwitch8400LineCardSlot OBJECT-IDENTITY
        STATUS      current
        DESCRIPTION "The authoritative identifier for a line card
                    module slot in an Aruba 8400 switch chassis. "
        ::= { wndSlots 4 }

arubaWiredSwitch8400FabricCardSlot OBJECT-IDENTITY
        STATUS      current
        DESCRIPTION "The authoritative identifier for a fabric
                    module slot in an Aruba 8400 switch chassis. "
        ::= { wndSlots 5 }

arubaWiredSwitch8400RearDisplayCardSlot OBJECT-IDENTITY
        STATUS      current
        DESCRIPTION "The authoritative identifier for a fabric
                    module slot in an Aruba 8400 switch chassis. "
        ::= { wndSlots 6 }

arubaWiredSwitch8320FanTraySlot OBJECT-IDENTITY
        STATUS      current
        DESCRIPTION "Represents slot for Aruba F2B Fan Tray. "
        ::= { wndSlots 7 }

arubaWiredSwitch8320PowerSupplySlot OBJECT-IDENTITY
        STATUS      current
        DESCRIPTION "The authoritative identifier for a
                    power supply bay in an Aruba 8320 switch
                    chassis. "
        ::= { wndSlots 8 }

arubaWiredSwitch8325FanTraySlot OBJECT-IDENTITY
        STATUS      current
        DESCRIPTION "Represents slot for Aruba Fan Tray. "
        ::= { wndSlots 9 }

arubaWiredSwitch8325PowerSupplySlot OBJECT-IDENTITY
        STATUS      current
        DESCRIPTION "The authoritative identifier for a
                    power supply bay in an Aruba 8325 switch
                    chassis. "
        ::= { wndSlots 10 }

arubaWiredSwitch6300FanTraySlot OBJECT-IDENTITY
        STATUS      current
        DESCRIPTION "Represents slot for Aruba 6300M Switch Fan Tray. "
        ::= { wndSlots 11 }

arubaWiredSwitch6300PowerSupplySlot OBJECT-IDENTITY
        STATUS      current
        DESCRIPTION "The authoritative identifier for a
                    power supply bay in an Aruba 6300M switch.  "
        ::= { wndSlots 12 }

arubaWiredSwitch6400ManagementModuleSlot OBJECT-IDENTITY
        STATUS      current
        DESCRIPTION "The authoritative identifier for a
                    Management Module slot in a Aruba 6400 switch. "
        ::= { wndSlots 13 }

arubaWiredSwitch6400LineCardSlot OBJECT-IDENTITY
        STATUS      current
        DESCRIPTION "The authoritative identifier for a line card
                    module slot in an Aruba 6400 switch chassis. "
        ::= { wndSlots 14 }

arubaWiredSwitch6400FanTraySlot OBJECT-IDENTITY
        STATUS      current
        DESCRIPTION "Represents slot for Aruba 6400 Fan Tray. "
        ::= { wndSlots 15 }

arubaWiredSwitch6400PowerSupplySlot OBJECT-IDENTITY
        STATUS      current
        DESCRIPTION "The authoritative identifier for a
                    power supply slot in an Aruba 6400 switch
                    chassis. "
        ::= { wndSlots 16 }

arubaWiredSwitch8360FanTraySlot OBJECT-IDENTITY
        STATUS      current
        DESCRIPTION "Represents slot for Aruba 8360 Fan Tray. "
        ::= { wndSlots 17 }

arubaWiredSwitch8360PowerSupplySlot OBJECT-IDENTITY
        STATUS      current
        DESCRIPTION "The authoritative identifier for a
                    power supply slot in an Aruba 8360 switch. "
        ::= { wndSlots 18 }

arubaWiredSwitch10000FanTraySlot OBJECT-IDENTITY
        STATUS      current
        DESCRIPTION "Represents slot for Aruba CX 10000 Fan Tray. "
        ::= { wndSlots 19 }

arubaWiredSwitch10000PowerSupplySlot OBJECT-IDENTITY
        STATUS      current
        DESCRIPTION "The authoritative identifier for a
                    power supply slot in an Aruba CX 10000 switch. "
        ::= { wndSlots 20 }

arubaWiredSwitch9300FanTraySlot OBJECT-IDENTITY
        STATUS      current
        DESCRIPTION "Represents slot for Aruba 9300 Fan Tray. "
        ::= { wndSlots 21 }

arubaWiredSwitch9300PowerSupplySlot OBJECT-IDENTITY
        STATUS      current
        DESCRIPTION "The authoritative identifier for a
                    power supply slot in an Aruba 9300 switch. "
        ::= { wndSlots 22 }

arubaWiredSwitch6200FanTraySlot OBJECT-IDENTITY
        STATUS      current
        DESCRIPTION "Represents slot for Aruba 6200M Switch Fan Tray. "
        ::= { wndSlots 23 }

arubaWiredSwitch6200PowerSupplySlot OBJECT-IDENTITY
        STATUS      current
        DESCRIPTION "The authoritative identifier for a
                    power supply bay in an Aruba 6200M switch.  "
        ::= { wndSlots 24 }

arubaWiredSwitch8100FanTraySlot OBJECT-IDENTITY
        STATUS      current
        DESCRIPTION "Represents slot for Aruba 8100 Switch Fan Tray. "
        ::= { wndSlots 25 }

arubaWiredSwitch8100PowerSupplySlot OBJECT-IDENTITY
        STATUS      current
        DESCRIPTION "The authoritative identifier for a
                    power supply bay in an Aruba 8100 switch.  "
        ::= { wndSlots 26 }

arubaWiredSwitch5420ManagementModuleSlot OBJECT-IDENTITY
        STATUS      current
        DESCRIPTION "The authoritative identifier for a
                    Management Module slot in a Aruba 5420 switch. "
        ::= { wndSlots 27 }

arubaWiredSwitch5420LineCardSlot OBJECT-IDENTITY
        STATUS      current
        DESCRIPTION "The authoritative identifier for a line card
                    module slot in an Aruba 5420 switch chassis. "
        ::= { wndSlots 28 }

arubaWiredSwitch5420FanTraySlot OBJECT-IDENTITY
        STATUS      current
        DESCRIPTION "Represents slot for Aruba 5420 Fan Tray. "
        ::= { wndSlots 29 }

arubaWiredSwitch5420PowerSupplySlot OBJECT-IDENTITY
        STATUS      current
        DESCRIPTION "The authoritative identifier for a
                    power supply slot in an Aruba 5420 switch
                    chassis. "
        ::= { wndSlots 30 }

arubaWiredSwitchTransceiverSlot OBJECT-IDENTITY
        STATUS      current
        DESCRIPTION "Represents slot for Aruba Switch Transceiver. "
        ::= { wndSlots 31 }

-- modules are sub types of parts

wndModules  OBJECT IDENTIFIER ::= { wndComponentIds 3 }

arubaWiredSwitchManagementModuleJL368A OBJECT-IDENTITY
        STATUS      current
        DESCRIPTION "The authoritative identifier for Aruba 8400 Management Module. "
        ::= { wndModules 1 }

arubaWiredSwitchModuleJL363A OBJECT-IDENTITY
        STATUS      current
        DESCRIPTION "The authoritative identifier for Aruba 8400X 32-port 10GbE SFP/SFP+ with MACsec Advanced Module. "
        ::= { wndModules 2 }

arubaWiredSwitchModuleJL365A OBJECT-IDENTITY
        STATUS      current
        DESCRIPTION "The authoritative identifier for Aruba 8400X 8-port 40GbE QSFP+ Advanced Module."
        ::= { wndModules 3 }

arubaWiredSwitchModuleJL366A OBJECT-IDENTITY
        STATUS      current
        DESCRIPTION "The authoritative identifier for Aruba 8400X 6-port 40GbE/100GbE QSFP28 Advanced Module. "
        ::= { wndModules 4 }

arubaWiredSwitchFabricModuleJL367A OBJECT-IDENTITY
        STATUS      current
        DESCRIPTION "The authoritative identifier for Aruba 8400X 7.2Tbps Fabric Module. "
        ::= { wndModules 5 }

arubaWiredSwitchFanModuleJL370A OBJECT-IDENTITY
        STATUS      current
        DESCRIPTION "The authoritative identifier for Aruba 8400 Fan for X731 Fan Tray. "
        ::= { wndModules 6 }

arubaWiredSwitchPowerSupplyUnitJL372A OBJECT-IDENTITY
        STATUS      current
        DESCRIPTION "The authoritative identifier for Aruba X382 54VDC 2700W AC Power Supply. "
        ::= { wndModules 7 }

arubaWiredSwitchJL369AFanTray OBJECT-IDENTITY
        STATUS      current
        DESCRIPTION "The authoritative identifier for Aruba X731 Fan Tray. "
        ::= { wndModules 8 }

arubaWiredSwitchModuleJL479A OBJECT-IDENTITY
        STATUS      current
        DESCRIPTION "The authoritative identifier for Aruba 8320 48p 10G SFP/SFP+ and 6p 40G QSFP+ Advanced Module."
        ::= { wndModules 9 }

arubaWiredSwitchPowerSupplyUnitJL480A OBJECT-IDENTITY
        STATUS      current
        DESCRIPTION "The authoritative identifier for Aruba 8320 400W AC Power Supply. "
        ::= { wndModules 10 }

arubaWiredSwitchJL481AFanTray OBJECT-IDENTITY
        STATUS      current
        DESCRIPTION "The authoritative identifier for Aruba 8320 Fan Tray. "
        ::= { wndModules 11 }

arubaWiredSwitchRearDisplayModule8400 OBJECT-IDENTITY
        STATUS      current
        DESCRIPTION "The authoritative identifier for Aruba 8400 Rear Display Module. "
        ::= { wndModules 12 }

arubaWiredSwitch1GbMaxPort OBJECT-IDENTITY
        STATUS      current
        DESCRIPTION "The authoritative identifier for a 1Gb maximum speed port."
        ::= { wndModules 13 }

arubaWiredSwitch10GbMaxPort OBJECT-IDENTITY
        STATUS      current
        DESCRIPTION "The authoritative identifier for a 10Gb maximum speed port."
        ::= { wndModules 14 }

arubaWiredSwitch25GbMaxPort OBJECT-IDENTITY
        STATUS      current
        DESCRIPTION "The authoritative identifier for a 25Gb maximum speed port."
        ::= { wndModules 15 }

arubaWiredSwitch40GbMaxPort OBJECT-IDENTITY
        STATUS      current
        DESCRIPTION "The authoritative identifier for a 40Gb maximum speed port."
        ::= { wndModules 16 }

arubaWiredSwitch100GbMaxPort OBJECT-IDENTITY
        STATUS      current
        DESCRIPTION "The authoritative identifier for a 100Gb maximum speed port."
        ::= { wndModules 17 }

arubaWiredSwitchSmartRatePort OBJECT-IDENTITY
        STATUS      current
        DESCRIPTION "The authoritative identifier for a Smart Rate multi-gigabit port."
        ::= { wndModules 18 }

arubaWiredSwitchModuleJL579A OBJECT-IDENTITY
        STATUS      current
        DESCRIPTION "The authoritative identifier for Aruba 8320 32p 40GbE QSFP+ Advanced Module."
        ::= { wndModules 19 }

arubaWiredSwitchModuleJL581A OBJECT-IDENTITY
        STATUS      current
        DESCRIPTION "The authoritative identifier for Aruba 8320 48p 1G/10GBASE-T and 6p 40G QSFP+ Advanced Module."
        ::= { wndModules 20 }

arubaWiredSwitchModuleJL635A OBJECT-IDENTITY
        STATUS      current
        DESCRIPTION "The authoritative identifier for Aruba 8325-48Y8C Module."
        ::= { wndModules 21 }

arubaWiredSwitchModuleJL624A OBJECT-IDENTITY
        STATUS      current
        DESCRIPTION "The authoritative identifier for Aruba 8325-48Y8C FB Module."
        ::= { wndModules 22 }

arubaWiredSwitchModuleJL625A OBJECT-IDENTITY
        STATUS      current
        DESCRIPTION "The authoritative identifier for Aruba 8325-48Y8C BF Module."
        ::= { wndModules 23 }

arubaWiredSwitchModuleJL636A OBJECT-IDENTITY
        STATUS      current
        DESCRIPTION "The authoritative identifier for Aruba 8325-32C Module."
        ::= { wndModules 24 }

arubaWiredSwitchModuleJL626A OBJECT-IDENTITY
        STATUS      current
        DESCRIPTION "The authoritative identifier for Aruba 8325-32C FB Module."
        ::= { wndModules 25 }

arubaWiredSwitchModuleJL627A OBJECT-IDENTITY
        STATUS      current
        DESCRIPTION "The authoritative identifier for Aruba 8325-32C BF Module."
        ::= { wndModules 26 }

arubaWiredSwitchPowerSupplyUnitJL632A OBJECT-IDENTITY
        STATUS      current
        DESCRIPTION "The authoritative identifier for Aruba 8325 650W 100-240V FB AC Power Supply. "
        ::= { wndModules 27 }

arubaWiredSwitchPowerSupplyUnitJL633A OBJECT-IDENTITY
        STATUS      current
        DESCRIPTION "The authoritative identifier for Aruba 8325 650W 100-240V BF AC Power Supply. "
        ::= { wndModules 28 }

arubaWiredSwitchFanTrayJL628A OBJECT-IDENTITY
        STATUS      current
        DESCRIPTION "The authoritative identifier for Aruba 8325-48Y8C F2B Fan Tray. "
        ::= { wndModules 29 }

arubaWiredSwitchFanTrayJL629A OBJECT-IDENTITY
        STATUS      current
        DESCRIPTION "The authoritative identifier for Aruba 8325-48Y8C B2F Fan Tray. "
        ::= { wndModules 30 }

arubaWiredSwitchFanTrayJL630A OBJECT-IDENTITY
        STATUS      current
        DESCRIPTION "The authoritative identifier for Aruba 8325-32C F2B Fan Tray. "
        ::= { wndModules 31 }

arubaWiredSwitchFanTrayJL631A OBJECT-IDENTITY
        STATUS      current
        DESCRIPTION "The authoritative identifier for Aruba 8325-32C B2F Fan Tray. "
        ::= { wndModules 32 }

arubaWiredSwitchModuleJL658A OBJECT-IDENTITY
        STATUS      current
        DESCRIPTION "The authoritative identifier for Aruba 6300M 24SFP+ 4SFP56 Advanced Module."
        ::= { wndModules 33 }

arubaWiredSwitchModuleJL659A OBJECT-IDENTITY
        STATUS      current
        DESCRIPTION "The authoritative identifier for Aruba 6300M 48SR5 CL6 PoE 4SFP56 Advanced Module."
        ::= { wndModules 34 }

arubaWiredSwitchModuleJL660A OBJECT-IDENTITY
        STATUS      current
        DESCRIPTION "The authoritative identifier for Aruba 6300M 24SR5 CL6 PoE 4SFP56 Advanced Module."
       ::= { wndModules 35 }

arubaWiredSwitchModuleJL661A OBJECT-IDENTITY
        STATUS      current
        DESCRIPTION "The authoritative identifier for Aruba 6300M 48G CL4 PoE 4SFP56 Advanced Module."
       ::= { wndModules 36 }

arubaWiredSwitchModuleJL662A OBJECT-IDENTITY
        STATUS      current
        DESCRIPTION "The authoritative identifier for Aruba 6300M 24G CL4 PoE 4SFP56 Advanced Module."
       ::= { wndModules 37 }

arubaWiredSwitchModuleJL663A OBJECT-IDENTITY
        STATUS      current
        DESCRIPTION "The authoritative identifier for Aruba 6300M 48G 4SFP56 Advanced Module."
       ::= { wndModules 38 }

arubaWiredSwitchModuleJL664A OBJECT-IDENTITY
        STATUS      current
        DESCRIPTION "The authoritative identifier for Aruba 6300M 24G 4SFP56 Advanced Module."
       ::= { wndModules 39 }

arubaWiredSwitchModuleJL665A OBJECT-IDENTITY
        STATUS      current
        DESCRIPTION "The authoritative identifier for Aruba 6300F 48G CL4 PoE 4SFP56 Advanced Module."
       ::= { wndModules 40 }

arubaWiredSwitchModuleJL666A OBJECT-IDENTITY
        STATUS      current
        DESCRIPTION "The authoritative identifier for Aruba 6300F 24G CL4 PoE 4SFP56 Advanced Module."
       ::= { wndModules 41 }

arubaWiredSwitchModuleJL667A OBJECT-IDENTITY
        STATUS      current
        DESCRIPTION "The authoritative identifier for Aruba 6300F 48G 4SFP56 Advanced Module."
       ::= { wndModules 42 }

arubaWiredSwitchModuleJL668A OBJECT-IDENTITY
        STATUS      current
        DESCRIPTION "The authoritative identifier for Aruba 6300F 24G 4SFP56 Advanced Module."
       ::= { wndModules 43 }

arubaWiredSwitchFanTrayJL669A OBJECT-IDENTITY
        STATUS      current
        DESCRIPTION "The authoritative identifier for Aruba X751 Front to Back Fan Tray."
        ::= { wndModules 44 }

arubaWiredSwitchPowerSupplyUnitJL085A OBJECT-IDENTITY
        STATUS      current
        DESCRIPTION "The authoritative identifier for Aruba X371 12VDC 250W100-240VAC Power Supply. "
        ::= { wndModules 45 }

arubaWiredSwitchPowerSupplyUnitJL086A OBJECT-IDENTITY
        STATUS      current
        DESCRIPTION "The authoritative identifier for Aruba X372 54VDC 680W 100-240VAC Power Supply. "
        ::= { wndModules 46 }

arubaWiredSwitchPowerSupplyUnitJL087A OBJECT-IDENTITY
        STATUS      current
        DESCRIPTION "The authoritative identifier for Aruba X372 54VDC 1050W 110-240VAC Power Supply. "
        ::= { wndModules 47 }

arubaWiredSwitchPowerSupplyUnitJL670A OBJECT-IDENTITY
        STATUS      current
        DESCRIPTION "The authoritative identifier for Aruba X372 54VDC 1600W 110-240VAC Power Supply. "
        ::= { wndModules 48 }

arubaWiredSwitchModuleJL687A OBJECT-IDENTITY
        STATUS      current
        DESCRIPTION "The authoritative identifier for Aruba 8400X-32Y 32p 1/10/25G SFP/SFP+/SFP28 Module. "
        ::= { wndModules 350 }

arubaWiredSwitch50GbMaxPort OBJECT-IDENTITY
        STATUS      current
        DESCRIPTION "The authoritative identifier for a 50Gb maximum speed port."
        ::= { wndModules 50 }

arubaWiredSwitchR0X31A OBJECT-IDENTITY
        STATUS      current
        DESCRIPTION "The authoritative identifier for the
                     Aruba 6400 Management Module."
        ::= { wndModules 51 }

arubaWiredSwitchR0X32A OBJECT-IDENTITY
        STATUS      current
        DESCRIPTION "The authoritative identifier for the
                     Aruba 6400 Fan Tray."
        ::= { wndModules 52 }

arubaWiredSwitchR0X33A OBJECT-IDENTITY
        STATUS      current
        DESCRIPTION "The authoritative identifier for the
                     Aruba 6400 C16 Inlet Adapter."
        ::= { wndModules 53 }

arubaWiredSwitchR0X34A OBJECT-IDENTITY
        STATUS      current
        DESCRIPTION "The authoritative identifier for the
                     Aruba 6400 C20 Inlet Adapter."
        ::= { wndModules 54 }

arubaWiredSwitchR0X35A OBJECT-IDENTITY
        STATUS      current
        DESCRIPTION "The authoritative identifier for the
                     Aruba 6400 1800W Power Supply with C16 Inlet Adapter."
        ::= { wndModules 55 }

arubaWiredSwitchR0X36A OBJECT-IDENTITY
        STATUS      current
        DESCRIPTION "The authoritative identifier for the
                     Aruba 6400 3000W Power Supply with C20 Inlet Adapter."
        ::= { wndModules 56 }

arubaWiredSwitchR0X37A OBJECT-IDENTITY
        STATUS      current
        DESCRIPTION "The authoritative identifier for the
                     Aruba 6400 4-post Rack Mount Kit."
        ::= { wndModules 57 }

arubaWiredSwitchR0X38A OBJECT-IDENTITY
        STATUS      current
        DESCRIPTION "The authoritative identifier for the
                     Aruba 6400 48-port 1GbE PoE Class 4 Module."
        ::= { wndModules 58 }

arubaWiredSwitchR0X39A OBJECT-IDENTITY
        STATUS      current
        DESCRIPTION "The authoritative identifier for the
                     Aruba 6400 48-port 1GbE PoE Class 4 and 4-port SFP56 Module."
        ::= { wndModules 59 }

arubaWiredSwitchR0X40A OBJECT-IDENTITY
        STATUS      current
        DESCRIPTION "The authoritative identifier for the
                     Aruba 6400 48-port 1GbE PoE Class 6 and 4-port SFP56 Module."
        ::= { wndModules 60 }

arubaWiredSwitchR0X41A OBJECT-IDENTITY
        STATUS      current
        DESCRIPTION "The authoritative identifier for the
                     Aruba 6400 48-port HPE Smart Rate PoE Class 6 and 4-port SFP56 Module."
        ::= { wndModules 61 }

arubaWiredSwitchR0X42A OBJECT-IDENTITY
        STATUS      current
        DESCRIPTION "The authoritative identifier for the
                     Aruba 6400 24-port HPE Smart Rate and 4-port SFP56 Module."
        ::= { wndModules 62 }

arubaWiredSwitchR0X43A OBJECT-IDENTITY
        STATUS      current
        DESCRIPTION "The authoritative identifier for the
                     Aruba 6400 24-port SFP+ and 4-port SFP56 Module."
        ::= { wndModules 63 }

arubaWiredSwitchR0X44A OBJECT-IDENTITY
        STATUS      current
        DESCRIPTION "The authoritative identifier for the
                     Aruba 6400 48-port 10/25GbE SFP28 Module."
        ::= { wndModules 64 }

arubaWiredSwitchR0X45A OBJECT-IDENTITY
        STATUS      current
        DESCRIPTION "The authoritative identifier for the
                     Aruba 6400 12-Port 40/100GbE QSFP28 Module."
        ::= { wndModules 65 }

arubaWiredSwitchModuleJL762A OBJECT-IDENTITY
        STATUS      current
        DESCRIPTION "The authoritative identifier for Aruba 6300M 48G 4SFP56 BF Advanced Module."
       ::= { wndModules 70 }

arubaWiredSwitchFanTrayJL761A OBJECT-IDENTITY
        STATUS      current
        DESCRIPTION "The authoritative identifier for Aruba X752 Back to Front Fan Tray."
        ::= { wndModules 71 }

arubaWiredSwitchPowerSupplyUnitJL760A OBJECT-IDENTITY
        STATUS      current
        DESCRIPTION "The authoritative identifier for Aruba X371 12VDC 250W Back to Front Power Supply."
        ::= { wndModules 72 }

arubaWiredSwitchModuleR8S89A OBJECT-IDENTITY
        STATUS      current
        DESCRIPTION "The authoritative identifier for Aruba 6300M 24SR CL6 PoE 2p50G 2p25G Advanced Module."
       ::= { wndModules 73 }

arubaWiredSwitchModuleR8S90A OBJECT-IDENTITY
        STATUS      current
        DESCRIPTION "The authoritative identifier for Aruba 6300M 48SR5 CL8 PoE 2p50G 2p25G Advanced Module."
       ::= { wndModules 74 }

arubaWiredSwitchModuleR8S91A OBJECT-IDENTITY
        STATUS      current
        DESCRIPTION "The authoritative identifier for Aruba 6300M 48SR5 CL6/CL8 2p50G 2p25G Advanced Module."
       ::= { wndModules 75 }

arubaWiredSwitchModuleR8S92A OBJECT-IDENTITY
        STATUS      current
        DESCRIPTION "The authoritative identifier for Aruba 6300M 24p SFP+ LRM 2p50G 2p25G Advanced Module."
       ::= { wndModules 76 }

arubaWiredSwitchModuleS0E91A OBJECT-IDENTITY
        STATUS      current
        DESCRIPTION "The authoritative identifier for Aruba 6300M 48SR10 CL8 PoE 4p100G Module."
       ::= { wndModules 77 }

arubaWiredSwitchModuleS0X44A OBJECT-IDENTITY
        STATUS      current
        DESCRIPTION "The authoritative identifier for Aruba 6300M 48SR10 CL8 PoE 4p100G TAA Module."
       ::= { wndModules 78 }

arubaWiredSwitchModuleS3L75A OBJECT-IDENTITY
        STATUS      current
        DESCRIPTION "The authoritative identifier for HPE ANW 6300L 24SRX CL6 2L2Y Layer2 Advanced Module."
       ::= { wndModules 79 }

arubaWiredSwitchModuleS3L76A OBJECT-IDENTITY
        STATUS      current
        DESCRIPTION "The authoritative identifier for HPE ANW 6300L 48SR5 CL8 2L2Y Layer2 Advanced Module."
       ::= { wndModules 80 }

arubaWiredSwitchModuleS3L77A OBJECT-IDENTITY
        STATUS      current
        DESCRIPTION "The authoritative identifier for HPE ANW 6300L 48SR5 CL8/6 2L2P Layer2 Advanced Module."
       ::= { wndModules 81 }

arubaWiredSwitchModuleS2P49A OBJECT-IDENTITY
        STATUS      current
        DESCRIPTION "The authoritative identifier for HPE ANW 6300L 24SRX CL6 2L2Y Layer2 Advanced Module."
       ::= { wndModules 82 }

arubaWiredSwitchModuleS2P50A OBJECT-IDENTITY
        STATUS      current
        DESCRIPTION "The authoritative identifier for HPE ANW 6300L 48SR5 CL8 2L2Y Layer2 Advanced Module."
       ::= { wndModules 83 }

arubaWiredSwitchModuleS2P51A OBJECT-IDENTITY
        STATUS      current
        DESCRIPTION "The authoritative identifier for HPE ANW 6300L 48SR5 CL8/6 2L2P Layer2 Advanced Module."
       ::= { wndModules 84 }

arubaWiredSwitchModuleJL724A OBJECT-IDENTITY
        STATUS      current
        DESCRIPTION "The authoritative identifier for Aruba 6200F 24G 4SFP+ Module."
       ::= { wndModules 90 }

arubaWiredSwitchModuleJL725A OBJECT-IDENTITY
        STATUS      current
        DESCRIPTION "The authoritative identifier for Aruba 6200F 24G CL4 4SFP+370W Module."
       ::= { wndModules 91 }

arubaWiredSwitchModuleJL726A OBJECT-IDENTITY
        STATUS      current
        DESCRIPTION "The authoritative identifier for Aruba 6200F 48G 4SFP+ Module."
       ::= { wndModules 92 }

arubaWiredSwitchModuleJL727A OBJECT-IDENTITY
        STATUS      current
        DESCRIPTION "The authoritative identifier for Aruba 6200F 48G CL4 4SFP+370W Module."
       ::= { wndModules 93 }

arubaWiredSwitchModuleJL728A OBJECT-IDENTITY
        STATUS      current
        DESCRIPTION "The authoritative identifier for Aruba 6200F 48G CL4 4SFP+740W Module."
       ::= { wndModules 94 }

arubaWiredSwitchModuleR8N85A OBJECT-IDENTITY
        STATUS      current
        DESCRIPTION "The authoritative identifier for the Aruba 6000 48G CLS4 4SFP 370W Module."
       ::= { wndModules 98 }

arubaWiredSwitchModuleR8N86A OBJECT-IDENTITY
        STATUS      current
        DESCRIPTION "The authoritative identifier for the Aruba 6000 48G 4SFP Module."
       ::= { wndModules 99 }

arubaWiredSwitchModuleR8N87A OBJECT-IDENTITY
        STATUS      current
        DESCRIPTION "The authoritative identifier for the Aruba 6000 24G CLS4 4SFP 370W Module."
       ::= { wndModules 100 }

arubaWiredSwitchModuleR8N88A OBJECT-IDENTITY
        STATUS      current
        DESCRIPTION "The authoritative identifier for the Aruba 6000 24G 4SFP Module."
       ::= { wndModules 101 }

arubaWiredSwitchModuleR8N89A OBJECT-IDENTITY
        STATUS      current
        DESCRIPTION "The authoritative identifier for the Aruba 6000 12G CLS4 2G/2SFP 139W Module."
       ::= { wndModules 102 }

arubaWiredSwitchR0X38B OBJECT-IDENTITY
        STATUS      current
        DESCRIPTION "The authoritative identifier for the
                     Aruba 6400 48-port 1GbE PoE Class 4 Module."
        ::= { wndModules 103 }

arubaWiredSwitchR0X39B OBJECT-IDENTITY
        STATUS      current
        DESCRIPTION "The authoritative identifier for the
                     Aruba 6400 48-port 1GbE PoE Class 4 and 4-port SFP56 Module."
        ::= { wndModules 104 }

arubaWiredSwitchR0X40B OBJECT-IDENTITY
        STATUS      current
        DESCRIPTION "The authoritative identifier for the
                     Aruba 6400 48-port 1GbE PoE Class 6 and 4-port SFP56 Module."
        ::= { wndModules 105 }

arubaWiredSwitchModuleJL675A OBJECT-IDENTITY
        STATUS      current
        DESCRIPTION "The authoritative identifier for the Aruba 6100 48G CLS4 4SFP+ 370W Module."
       ::= { wndModules 106 }

arubaWiredSwitchModuleJL676A OBJECT-IDENTITY
        STATUS      current
        DESCRIPTION "The authoritative identifier for the Aruba 6100 48G 4SFP+ Module."
       ::= { wndModules 107 }

arubaWiredSwitchModuleJL677A OBJECT-IDENTITY
        STATUS      current
        DESCRIPTION "The authoritative identifier for the Aruba 6100 24G CLS4 4SFP+ 370W Module."
       ::= { wndModules 108 }

arubaWiredSwitchModuleJL678A OBJECT-IDENTITY
        STATUS      current
        DESCRIPTION "The authoritative identifier for the Aruba 6100 24G 4SFP+ Module."
       ::= { wndModules 109 }

arubaWiredSwitchModuleJL679A OBJECT-IDENTITY
        STATUS      current
        DESCRIPTION "The authoritative identifier for the Aruba 6100 12G CLS4 2G/2SFP+ 139W Module."
       ::= { wndModules 110 }

arubaWiredSwitchNonPoEPowerSupplyUnit OBJECT-IDENTITY
        STATUS      current
        DESCRIPTION "The authoritative identifier for Aruba 12VDC and 200W Power Supply. "
        ::= { wndModules 111 }

arubaWiredSwitchPoEPowerSupplyUnit OBJECT-IDENTITY
        STATUS      current
        DESCRIPTION "The authoritative identifier for Aruba 12VDC and 54VDC 950W Power Supply. "
        ::= { wndModules 112 }

arubaWiredSwitchModuleJL717A OBJECT-IDENTITY
        STATUS      current
        DESCRIPTION "The authoritative identifier for the Aruba 8360
        32p 1/10/25G SFP/SFP+/SFP28 and 4p 40/100G QSFP+/QSFP28 advanced module."
        ::= { wndModules 113 }

arubaWiredSwitchModuleJL718A OBJECT-IDENTITY
        STATUS      current
        DESCRIPTION "The authoritative identifier for the Aruba 8360
        16p 1/10/25G SFP/SFP+/SFP28 and 2p 40/100G QSFP+/QSFP28 advanced module."
        ::= { wndModules 114 }

arubaWiredSwitchModuleJL719A OBJECT-IDENTITY
        STATUS      current
        DESCRIPTION "The authoritative identifier for the Aruba 8360
        48p 1/10/25G SFP/SFP+/SFP28 and 6p 40/100G QSFP+/QSFP28 advanced module."
        ::= { wndModules 115 }

arubaWiredSwitchModuleJL720A OBJECT-IDENTITY
        STATUS      current
        DESCRIPTION "The authoritative identifier for the Aruba 8360
        48p 1/10G BASE-T and 4p 40/100G QSFP+/QSFP28 advanced module."
        ::= { wndModules 116 }

arubaWiredSwitchModuleJL721A OBJECT-IDENTITY
        STATUS      current
        DESCRIPTION "The authoritative identifier for the Aruba 8360
        12p 40/100G QSFP+/QSFP28 advanced module."
        ::= { wndModules 117 }

arubaWiredSwitchModuleJL722A OBJECT-IDENTITY
        STATUS      current
        DESCRIPTION "The authoritative identifier for the Aruba 8360
        48p 1/10G SFP/SFP+ and 2p 40/100G QSFP+/QSFP28 advanced module."
        ::= { wndModules 118 }

arubaWiredSwitchPowerSupplyUnitJL600A OBJECT-IDENTITY
        STATUS      current
        DESCRIPTION "The authoritative identifier for the Aruba 550W 12V F2B Power Supply. "
        ::= { wndModules 119 }

arubaWiredSwitchPowerSupplyUnitJL601A OBJECT-IDENTITY
        STATUS      current
        DESCRIPTION "The authoritative identifier for the Aruba 850W 12V F2B Power Supply. "
        ::= { wndModules 120 }

arubaWiredSwitchPowerSupplyUnitJL712A OBJECT-IDENTITY
        STATUS      current
        DESCRIPTION "The authoritative identifier for the Aruba 550W 12V B2F Power Supply. "
        ::= { wndModules 121 }

arubaWiredSwitchPowerSupplyUnitJL713A OBJECT-IDENTITY
        STATUS      current
        DESCRIPTION "The authoritative identifier for the Aruba 850W 12V B2F Power Supply. "
        ::= { wndModules 122 }

arubaWiredSwitchFanTrayJL714A OBJECT-IDENTITY
        STATUS      current
        DESCRIPTION "The authoritative identifier for Aruba X741 F2B Fan Tray. "
        ::= { wndModules 123 }

arubaWiredSwitchFanTrayJL715A OBJECT-IDENTITY
        STATUS      current
        DESCRIPTION "The authoritative identifier for Aruba X742 B2F Fan Tray. "
        ::= { wndModules 124 }

arubaWiredSwitch36WPowerSupplyUnit OBJECT-IDENTITY
        STATUS      current
        DESCRIPTION "The authoritative identifier for Aruba 12VDC and 36W Power Supply. "
        ::= { wndModules 125 }

arubaWiredSwitch65WPowerSupplyUnit OBJECT-IDENTITY
        STATUS      current
        DESCRIPTION "The authoritative identifier for Aruba 12VDC and 65W Power Supply. "
        ::= { wndModules 126 }

arubaWiredSwitch165WPowerSupplyUnit OBJECT-IDENTITY
        STATUS      current
        DESCRIPTION "The authoritative identifier for Aruba 12VDC and 165W Power Supply. "
        ::= { wndModules 127 }

arubaWiredSwitch500WPowerSupplyUnit OBJECT-IDENTITY
        STATUS      current
        DESCRIPTION "The authoritative identifier for Aruba 12VDC and 500W Power Supply. "
        ::= { wndModules 128 }

arubaWiredSwitchModuleJL817A OBJECT-IDENTITY
        STATUS      current
        DESCRIPTION "The authoritative identifier for the Aruba 4100i
        12-port 1GbE (8-port Class 4 POE and 4-port Class 6 POE)
        2-port SFP+ DIN Mount Switch."
        ::= { wndModules 129 }

arubaWiredSwitchModuleJL818A OBJECT-IDENTITY
        STATUS      current
        DESCRIPTION "The authoritative identifier for the Aruba 4100i
        24-port 1GbE (20-port Class 4 POE and 4-port Class 6 POE)
        4-port SFP+ Switch."
        ::= { wndModules 130 }

arubaWiredSwitch300WPowerSupplyUnit OBJECT-IDENTITY
        STATUS      current
        DESCRIPTION "The authoritative identifier for Aruba 54VDC 300W Power Supply. "
        ::= { wndModules 131 }

arubaWiredSwitchExternalPowerSupplyUnit OBJECT-IDENTITY
        STATUS      current
        DESCRIPTION "The authoritative identifier for generic External Power Supply. "
        ::= { wndModules 132 }

arubaWiredSwitchPowerSupplyUnitJL757A OBJECT-IDENTITY
        STATUS      current
        DESCRIPTION "The authoritative identifier for Aruba 6300M 250W 36-72VDC Power Supply. "
        ::= { wndModules 133 }

arubaWiredSwitchPowerSupplyUnitJL758A OBJECT-IDENTITY
        STATUS      current
        DESCRIPTION "The authoritative identifier for Aruba 6300M 1050W 36-72VDC Power Supply."
        ::= { wndModules 134 }

arubaWiredSwitchPowerSupplyUnitR8R51A OBJECT-IDENTITY
        STATUS      current
        DESCRIPTION "The authoritative identifier for Aruba CX
        10000-48Y6C Port to Power (FB) AC Power Supply Unit"
        ::= { wndModules 135 }

arubaWiredSwitchPowerSupplyUnitR8R52A OBJECT-IDENTITY
        STATUS      current
        DESCRIPTION "The authoritative identifier for Aruba CX
        10000-48Y6C Power to Port (BF) AC Power Supply Unit"
        ::= { wndModules 136 }

arubaWiredSwitchFanTrayR8R53A OBJECT-IDENTITY
        STATUS      current
        DESCRIPTION "The authoritative identifier for the Aruba CX
        10000-48Y6C Port to Power (FB) Fan Tray"
        ::= { wndModules 137 }

arubaWiredSwitchFanTrayR8R54A OBJECT-IDENTITY
        STATUS      current
        DESCRIPTION "The authoritative identifier for the Aruba CX
        10000-48Y6C Power to Port (BF) Fan Tray"
        ::= { wndModules 138 }

arubaWiredSwitchModuleR8S96A OBJECT-IDENTITY
        STATUS      current
        DESCRIPTION "The authoritative identifier for the Aruba CX
        10000-48Y6C Distributed Services Switch."
        ::= { wndModules 139 }

arubaWiredSwitchPowerSupplyUnitJL861A OBJECT-IDENTITY
        STATUS      current
        DESCRIPTION "The authoritative identifier for Aruba 8325
        850W 48VDC Front-to-Back Power Supply"
        ::= { wndModules 140 }

arubaWiredSwitchPowerSupplyUnitJL862A OBJECT-IDENTITY
        STATUS      current
        DESCRIPTION "The authoritative identifier for Aruba 8325
        850W 48VDC Back-to-Front Power Supply"
        ::= { wndModules 141 }

arubaWiredSwitchModuleJL717C OBJECT-IDENTITY
        STATUS      current
        DESCRIPTION "The authoritative identifier for the Aruba 8360
        32p 1/10/25G SFP/SFP+/SFP28 and 4p 40/100G QSFP+/QSFP28 advanced module."
        ::= { wndModules 142 }

arubaWiredSwitchModuleJL718C OBJECT-IDENTITY
        STATUS      current
        DESCRIPTION "The authoritative identifier for the Aruba 8360
        16p 1/10/25G SFP/SFP+/SFP28 and 2p 40/100G QSFP+/QSFP28 advanced module."
        ::= { wndModules 143 }

arubaWiredSwitchModuleJL719C OBJECT-IDENTITY
        STATUS      current
        DESCRIPTION "The authoritative identifier for the Aruba 8360
        48p 1/10/25G SFP/SFP+/SFP28 and 6p 40/100G QSFP+/QSFP28 advanced module."
        ::= { wndModules 144 }

arubaWiredSwitchModuleJL720C OBJECT-IDENTITY
        STATUS      current
        DESCRIPTION "The authoritative identifier for the Aruba 8360
        48p 1/10G BASE-T and 4p 40/100G QSFP+/QSFP28 advanced module."
        ::= { wndModules 145 }

arubaWiredSwitchModuleJL721C OBJECT-IDENTITY
        STATUS      current
        DESCRIPTION "The authoritative identifier for the Aruba 8360
        12p 40/100G QSFP+/QSFP28 advanced module."
        ::= { wndModules 146 }

arubaWiredSwitchModuleJL722C OBJECT-IDENTITY
        STATUS      current
        DESCRIPTION "The authoritative identifier for the Aruba 8360
        48p 1/10G SFP/SFP+ and 2p 40/100G QSFP+/QSFP28 advanced module."
        ::= { wndModules 147 }

arubaWiredSwitchModuleR8Z96A OBJECT-IDENTITY
        STATUS      current
        DESCRIPTION "The authoritative identifier for the
        Aruba 9300-32D 32p 400G 2p 10G Switch."
        ::= { wndModules 148 }

arubaWiredSwitchPowerSupplyUnitR8Z97A OBJECT-IDENTITY
        STATUS      current
        DESCRIPTION "The authoritative identifier for the Aruba 9300
        1500W F2B AC PS"
        ::= { wndModules 149 }

arubaWiredSwitchPowerSupplyUnitR8Z98A OBJECT-IDENTITY
        STATUS      current
        DESCRIPTION "The authoritative identifier for the Aruba 9300
        1500W B2F AC PS"
        ::= { wndModules 150 }

arubaWiredSwitchFanTrayR8Z99A OBJECT-IDENTITY
        STATUS      current
        DESCRIPTION "The authoritative identifier for the Aruba 9300
        F2B Fan"
        ::= { wndModules 151 }

arubaWiredSwitchFanTrayR9A00A OBJECT-IDENTITY
        STATUS      current
        DESCRIPTION "The authoritative identifier for the Aruba 9300
        B2F Fan"
        ::= { wndModules 152 }

arubaWiredSwitch400GbMaxPort OBJECT-IDENTITY
        STATUS      current
        DESCRIPTION "The authoritative identifier for a 400Gb maximum speed port."
        ::= { wndModules 155 }

arubaWiredSwitchModuleR8Q67A OBJECT-IDENTITY
        STATUS      current
        DESCRIPTION "The authoritative identifier for Aruba 6200M 24G 4SFP+ Module."
       ::= { wndModules 156 }

arubaWiredSwitchModuleR8Q68A OBJECT-IDENTITY
        STATUS      current
        DESCRIPTION "The authoritative identifier for Aruba 6200M 24G CL4 PoE 4SFP+ Module."
       ::= { wndModules 157 }

arubaWiredSwitchModuleR8Q69A OBJECT-IDENTITY
        STATUS      current
        DESCRIPTION "The authoritative identifier for Aruba 6200M 48G 4SFP+ Module."
       ::= { wndModules 158 }

arubaWiredSwitchModuleR8Q70A OBJECT-IDENTITY
        STATUS      current
        DESCRIPTION "The authoritative identifier for Aruba 6200M 48G CL4 PoE 4SFP+ Module."
       ::= { wndModules 159 }

arubaWiredSwitchModuleR8Q71A OBJECT-IDENTITY
        STATUS      current
        DESCRIPTION "The authoritative identifier for Aruba 6200M 36G 12SR5 CL6 PoE 4SFP+ Module."
       ::= { wndModules 160 }

arubaWiredSwitchModuleR8Q72A OBJECT-IDENTITY
        STATUS      current
        DESCRIPTION "The authoritative identifier for Aruba 6200F 12G CL4 2G/2SFP+ 139W Module."
       ::= { wndModules 161 }

arubaWiredSwitchModuleR8V08A OBJECT-IDENTITY
        STATUS      current
        DESCRIPTION "The authoritative identifier for Aruba 6200M 24G 4SFP+ TAA Module."
       ::= { wndModules 162 }

arubaWiredSwitchModuleR8V09A OBJECT-IDENTITY
        STATUS      current
        DESCRIPTION "The authoritative identifier for Aruba 6200M 24G CL4 PoE 4SFP+ TAA Module."
       ::= { wndModules 163 }

arubaWiredSwitchModuleR8V10A OBJECT-IDENTITY
        STATUS      current
        DESCRIPTION "The authoritative identifier for Aruba 6200M 48G 4SFP+ TAA Module."
       ::= { wndModules 164 }

arubaWiredSwitchModuleR8V11A OBJECT-IDENTITY
        STATUS      current
        DESCRIPTION "The authoritative identifier for Aruba 6200M 48G CL4 PoE 4SFP+ TAA Module."
       ::= { wndModules 165 }

arubaWiredSwitchModuleR8V12A OBJECT-IDENTITY
        STATUS      current
        DESCRIPTION "The authoritative identifier for Aruba 6200M 36G 12SR5 CL6 4SFP+ TAA Module."
       ::= { wndModules 166 }

arubaWiredSwitchModuleR8V13A OBJECT-IDENTITY
        STATUS      current
        DESCRIPTION "The authoritative identifier for Aruba Aruba 6200F 12G CL4 2G/2SFP+TAA Module."
       ::= { wndModules 167 }

arubaWiredSwitchModuleR9Y04A OBJECT-IDENTITY
        STATUS      current
        DESCRIPTION "The authoritative identifier for the Aruba 6100 48G CLS4 4SFP+ 740W Module."
       ::= { wndModules 168 }

arubaWiredSwitchModuleR9Y03A OBJECT-IDENTITY
        STATUS      current
        DESCRIPTION "The authoritative identifier for the Aruba 6000 48G CLS4 4SFP 740W Module."
       ::= { wndModules 169 }

arubaWiredSwitch740WPowerSupplyUnit OBJECT-IDENTITY
        STATUS      current
        DESCRIPTION "The authoritative identifier for the Aruba PoE 740W 100-240VAC Power Supply."
       ::= { wndModules 170 }

arubaWiredSwitchModuleR9W94A OBJECT-IDENTITY
        STATUS      current
        DESCRIPTION "The authoritative identifier for the Aruba 8100 24x10G SFP+ 4x40/100G QSFP28 Module"
       ::= { wndModules 171 }

arubaWiredSwitchModuleR9W95A OBJECT-IDENTITY
        STATUS      current
        DESCRIPTION "The authoritative identifier for the Aruba 8100 24x10G Base-T 4x10G SFP+ 4x40/100G QSFP28 Modulej"
       ::= { wndModules 172 }

arubaWiredSwitchModuleR9W96A OBJECT-IDENTITY
        STATUS      current
        DESCRIPTION "The authoritative identifier for the Aruba 8100 48x10G SFP+ 4x40/100G QSFP28 Module"
       ::= { wndModules 173 }

arubaWiredSwitchModuleR9W97A OBJECT-IDENTITY
        STATUS      current
        DESCRIPTION "The authoritative identifier for the Aruba 8100 40x10G Base-T 8x10G SFP+ 4x40/100G QSFP28 Module"
       ::= { wndModules 174 }

arubaWiredSwitchModuleJL724B OBJECT-IDENTITY
        STATUS      current
        DESCRIPTION "The authoritative identifier for HPE ANW 6200F 24G 4SFP+ Module."
       ::= { wndModules 175 }

arubaWiredSwitchModuleJL725B OBJECT-IDENTITY
        STATUS      current
        DESCRIPTION "The authoritative identifier for HPE ANW 6200F 24G C4 4SFP+370W Module."
       ::= { wndModules 176 }

arubaWiredSwitchModuleJL726B OBJECT-IDENTITY
        STATUS      current
        DESCRIPTION "The authoritative identifier for HPE ANW 6200F 48G 4SFP+ Module."
       ::= { wndModules 177 }

arubaWiredSwitchModuleJL727B OBJECT-IDENTITY
        STATUS      current
        DESCRIPTION "The authoritative identifier for HPE ANW 6200F 48G C4 4SFP+370W Module."
       ::= { wndModules 178 }

arubaWiredSwitchModuleJL728B OBJECT-IDENTITY
        STATUS      current
        DESCRIPTION "The authoritative identifier for HPE ANW 6200F 48G C4 4SFP+740W Module."
       ::= { wndModules 179 }

arubaWiredSwitchModuleS0M81A OBJECT-IDENTITY
        STATUS      current
        DESCRIPTION "The authoritative identifier for HPE ANW 6200F 24G 4SFP Module."
       ::= { wndModules 180 }

arubaWiredSwitchModuleS0M82A OBJECT-IDENTITY
        STATUS      current
        DESCRIPTION "The authoritative identifier for HPE ANW 6200F 24G C4 4SFP 370W Module."
       ::= { wndModules 181 }

arubaWiredSwitchModuleS0M83A OBJECT-IDENTITY
        STATUS      current
        DESCRIPTION "The authoritative identifier for HPE ANW 6200F 48G 4SFP Module."
       ::= { wndModules 182 }

arubaWiredSwitchModuleS0M84A OBJECT-IDENTITY
        STATUS      current
        DESCRIPTION "The authoritative identifier for HPE ANW 6200F 48G C4 4SFP 370W Module."
       ::= { wndModules 183 }

arubaWiredSwitchModuleS0M85A OBJECT-IDENTITY
        STATUS      current
        DESCRIPTION "The authoritative identifier for HPE ANW 6200F 48G C4 4SFP 740W Module."
       ::= { wndModules 184 }

arubaWiredSwitchModuleS0M86A OBJECT-IDENTITY
        STATUS      current
        DESCRIPTION "The authoritative identifier for HPE NW 6200F 24G 4SFP+ T Module."
       ::= { wndModules 185 }

arubaWiredSwitchModuleS0M87A OBJECT-IDENTITY
        STATUS      current
        DESCRIPTION "The authoritative identifier for HPE NW 6200F 24G C4 4SFP+370W T Module."
       ::= { wndModules 186 }

arubaWiredSwitchModuleS0M88A OBJECT-IDENTITY
        STATUS      current
        DESCRIPTION "The authoritative identifier for HPE NW 6200F 48G 4SFP+ T Module."
       ::= { wndModules 187 }

arubaWiredSwitchModuleS0M89A OBJECT-IDENTITY
        STATUS      current
        DESCRIPTION "The authoritative identifier for HPE NW 6200F 48G C4 4SFP+370W T Module."
       ::= { wndModules 188 }

arubaWiredSwitchModuleS0M90A OBJECT-IDENTITY
        STATUS      current
        DESCRIPTION "The authoritative identifier for HPE NW 6200F 48G C4 4SFP+740W T Module."
       ::= { wndModules 189 }

arubaWiredSwitchModuleS0G13A OBJECT-IDENTITY
        STATUS      current
        DESCRIPTION "The authoritative identifier for HPE NW 6200F 24G 4SFP T Module."
       ::= { wndModules 190 }

arubaWiredSwitchModuleS0G14A OBJECT-IDENTITY
        STATUS      current
        DESCRIPTION "The authoritative identifier for HPE NW 6200F 24G C4 4SFP 370W T Module."
       ::= { wndModules 191 }

arubaWiredSwitchModuleS0G15A OBJECT-IDENTITY
        STATUS      current
        DESCRIPTION "The authoritative identifier for HPE NW 6200F 48G 4SFP T Module."
       ::= { wndModules 192 }

arubaWiredSwitchModuleS0G16A OBJECT-IDENTITY
        STATUS      current
        DESCRIPTION "The authoritative identifier for HPE NW 6200F 48G C4 4SFP370W T Module."
       ::= { wndModules 193 }

arubaWiredSwitchModuleS0G17A OBJECT-IDENTITY
        STATUS      current
        DESCRIPTION "The authoritative identifier for HPE NW 6200F 48G C4 4SFP740W T Module."
       ::= { wndModules 194 }

arubaWiredSwitchModuleS0E48A OBJECT-IDENTITY
        STATUS      current
        DESCRIPTION "The authoritatuive identifier for HPE Aruba Networking CX 6400 v2 32p SFP28 25G 4p QSFP28 100G MACsec Extended Tables Module"
       ::= { wndModules 195 }

arubaWiredSwitchModuleS1T83A OBJECT-IDENTITY
        STATUS      current
        DESCRIPTION "The authoritative identifier for HPE Aruba Networking CX 6400 v2 24p Smart Rate 1G/2.5G/5G/10G Class8 PoE 4p SFP56 50G Module"
       ::= { wndModules 196 }

arubaWiredSwitchModuleS0F99A OBJECT-IDENTITY
        STATUS      current
        DESCRIPTION "The authoritative identifier for HPE ANW 6300M 24G CL4 PoE 4L TAA Module."
       ::= { wndModules 197 }

arubaWiredSwitchModuleS0G00A OBJECT-IDENTITY
        STATUS      current
        DESCRIPTION "The authoritative identifier for HPE ANW 6300M 48G 4L TAA Module."
       ::= { wndModules 198 }

arubaWiredSwitchModuleS0G01A OBJECT-IDENTITY
        STATUS      current
        DESCRIPTION "The authoritative identifier for HPE ANW 6300M 24G 4L TAA Module."
       ::= { wndModules 199 }

arubaWiredSwitchModuleS0G02A OBJECT-IDENTITY
        STATUS      current
        DESCRIPTION "The authoritative identifier for HPE ANW 6300M 48G 4L Pwr2Prt 2Fs TAA Bdl Module."
       ::= { wndModules 200 }

arubaWiredSwitchModuleS0G03A OBJECT-IDENTITY
        STATUS      current
        DESCRIPTION "The authoritative identifier for HPE ANW 6300M 24P 4L TAA Module."
       ::= { wndModules 201 }

arubaWiredSwitchModuleS0G04A OBJECT-IDENTITY
        STATUS      current
        DESCRIPTION "The authoritative identifier for HPE ANW 6300M 48SR5 CL6 PoE 4L TAA Module."
       ::= { wndModules 202 }

arubaWiredSwitchModuleS0G05A OBJECT-IDENTITY
        STATUS      current
        DESCRIPTION "The authoritative identifier for HPE ANW 6300M 24SR5 CL6 PoE 4L TAA Module."
       ::= { wndModules 203 }

arubaWiredSwitchModuleS0G06A OBJECT-IDENTITY
        STATUS      current
        DESCRIPTION "The authoritative identifier for HPE ANW 6300M 48G CL4 PoE 4L TAA Module."
       ::= { wndModules 204 }

arubaWiredSwitchModuleS0G95A OBJECT-IDENTITY
        STATUS      current
        DESCRIPTION "The authoritative identifier for HPE ANW 6300F 48G CL4 4L TAA Module."
       ::= { wndModules 205 }

arubaWiredSwitchModuleS0G96A OBJECT-IDENTITY
        STATUS      current
        DESCRIPTION "The authoritative identifier for HPE ANW 6300F 24G CL4 4L TAA Module."
       ::= { wndModules 206 }

arubaWiredSwitchModuleS0G97A OBJECT-IDENTITY
        STATUS      current
        DESCRIPTION "The authoritative identifier for HPE ANW 6300F 48G 4L TAA Module."
       ::= { wndModules 207 }

arubaWiredSwitchModuleS0G98A OBJECT-IDENTITY
        STATUS      current
        DESCRIPTION "The authoritative identifier for HPE ANW 6300F 24G 4L TAA Module."
       ::= { wndModules 208 }

arubaWiredSwitchModuleS0G12A OBJECT-IDENTITY
        STATUS      current
        DESCRIPTION "The authoritative identifier for HPE ANW 8325P-32C TAA Switch"
       ::= { wndModules 209 }

arubaWiredSwitchModuleS0G27A OBJECT-IDENTITY
        STATUS      current
        DESCRIPTION "The authoritative identifier for the HPE Aruba Networking X3B1
                     650W 100-240VAC Front-to-Back Power Supply"
       ::= { wndModules 210 }

arubaWiredSwitchModuleS0G28A OBJECT-IDENTITY
        STATUS      current
        DESCRIPTION "The authoritative identifier for the HPE Aruba Networking X3B1
                     650W 100-240VAC Back-to-Front Power Supply"
       ::= { wndModules 211 }

arubaWiredSwitchModuleS0G29A OBJECT-IDENTITY
        STATUS      current
        DESCRIPTION "The authoritative identifier for the HPE Aruba Networking X3B4
                     48VDC Front-to-Back Power Supply"
       ::= { wndModules 212 }

arubaWiredSwitchModuleS0G30A OBJECT-IDENTITY
        STATUS      current
        DESCRIPTION "The authoritative identifier for the HPE Aruba Networking X3B4
                     48VDC Back-to-Front Power Supply"
       ::= { wndModules 213 }

arubaWiredSwitchS0U55A OBJECT-IDENTITY
        STATUS      current
        DESCRIPTION "The authoritative identifier for the
                     HPE ANW 5420 Mgmt Module."
        ::= { wndModules 214 }

arubaWiredSwitchS0U58A OBJECT-IDENTITY
        STATUS      current
        DESCRIPTION "The authoritative identifier for the
                     HPE ANW 5420 TAA Mgmt Module."
        ::= { wndModules 215 }

arubaWiredSwitchS0U54A OBJECT-IDENTITY
        STATUS      current
        DESCRIPTION "The authoritative identifier for the
                     HPE ANW 5420 6-slot Fan Tray."
        ::= { wndModules 216 }

arubaWiredSwitchS0U53A OBJECT-IDENTITY
        STATUS      current
        DESCRIPTION "The authoritative identifier for the
                     HPE ANW 5420 1600W AC Power Supply."
        ::= { wndModules 217 }

arubaWiredSwitchS0U61A OBJECT-IDENTITY
        STATUS      current
        DESCRIPTION "The authoritative identifier for the
                     HPE ANW 5420 24G Module."
        ::= { wndModules 218 }

arubaWiredSwitchS0U62A OBJECT-IDENTITY
        STATUS      current
        DESCRIPTION "The authoritative identifier for the
                     HPE ANW 5420 24G CL4 Module."
        ::= { wndModules 219 }

arubaWiredSwitchS0U63A OBJECT-IDENTITY
        STATUS      current
        DESCRIPTION "The authoritative identifier for the
                     HPE ANW 5420 20G CL4 4P Module."
        ::= { wndModules 220 }

arubaWiredSwitchS0U64A OBJECT-IDENTITY
        STATUS      current
        DESCRIPTION "The authoritative identifier for the
                     HPE ANW 5420 20G CL4 2Y Module."
        ::= { wndModules 221 }

arubaWiredSwitchS0U65A OBJECT-IDENTITY
        STATUS      current
        DESCRIPTION "The authoritative identifier for the
                     HPE ANW 5420 8SR10 CL8 Module."
        ::= { wndModules 222 }

arubaWiredSwitchS0U66A OBJECT-IDENTITY
        STATUS      current
        DESCRIPTION "The authoritative identifier for the
                     HPE ANW 5420 16SR5 CL6 Module."
        ::= { wndModules 223 }

arubaWiredSwitchS0U67A OBJECT-IDENTITY
        STATUS      current
        DESCRIPTION "The authoritative identifier for the
                     HPE ANW 5420 24F Module."
        ::= { wndModules 224 }

arubaWiredSwitchS0U68A OBJECT-IDENTITY
        STATUS      current
        DESCRIPTION "The authoritative identifier for the
                     HPE ANW 5420 8P LRM Module."
        ::= { wndModules 225 }

arubaWiredSwitchS0U71A OBJECT-IDENTITY
        STATUS      current
        DESCRIPTION "The authoritative identifier for the
                     HPE ANW 5420 24G TAA Module."
        ::= { wndModules 226 }

arubaWiredSwitchS0U72A OBJECT-IDENTITY
        STATUS      current
        DESCRIPTION "The authoritative identifier for the
                     HPE ANW 5420 24G CL4 TAA Module."
        ::= { wndModules 227 }

arubaWiredSwitchS0U73A OBJECT-IDENTITY
        STATUS      current
        DESCRIPTION "The authoritative identifier for the
                     HPE ANW 5420 20G CL4 4P TAA Module."
        ::= { wndModules 228 }

arubaWiredSwitchS0U74A OBJECT-IDENTITY
        STATUS      current
        DESCRIPTION "The authoritative identifier for the
                     HPE ANW 5420 20G CL4 2Y TAA Module."
        ::= { wndModules 229 }

arubaWiredSwitchS0U75A OBJECT-IDENTITY
        STATUS      current
        DESCRIPTION "The authoritative identifier for the
                     HPE ANW 5420 8SR10 CL8 TAA Module."
        ::= { wndModules 230 }

arubaWiredSwitchS0U76A OBJECT-IDENTITY
        STATUS      current
        DESCRIPTION "The authoritative identifier for the
                     HPE ANW 5420 16SR5 CL6 TAA Module."
        ::= { wndModules 231 }

arubaWiredSwitchS0U77A OBJECT-IDENTITY
        STATUS      current
        DESCRIPTION "The authoritative identifier for the
                     HPE ANW 5420 24F TAA Module."
        ::= { wndModules 232 }

arubaWiredSwitchS0U78A OBJECT-IDENTITY
        STATUS      current
        DESCRIPTION "The authoritative identifier for the
                     HPE ANW 5420 8P LRM TAA Module."
        ::= { wndModules 233 }

arubaWiredSwitchPowerSupplyS0F91A OBJECT-IDENTITY
        STATUS      current
        DESCRIPTION "The authoritative identifier for the HPE ANW X3A13 1600W
                     Front-to-Back AC Power Supply"
       ::= { wndModules 234 }

arubaWiredSwitchPowerSupplyS0F92A OBJECT-IDENTITY
        STATUS      current
        DESCRIPTION "The authoritative identifier for the HPE ANW X3A13 1600W
                     Back-to-Front AC Power Supply"
       ::= { wndModules 235 }

arubaWiredSwitchFanTrayS0F93A OBJECT-IDENTITY
        STATUS      current
        DESCRIPTION "The authoritative identifier for the HPE ANW X761
                     Front-to-Back Fan Tray"
       ::= { wndModules 236 }

arubaWiredSwitchFanTrayS0F94A OBJECT-IDENTITY
        STATUS      current
        DESCRIPTION "The authoritative identifier for the HPE ANW X761
                     Back-to-Front Fan Tray"
       ::= { wndModules 237 }

arubaWiredSwitchModuleS0F95A OBJECT-IDENTITY
        STATUS      current
        DESCRIPTION "The authoritative identifier for the HPE Aruba Networking
                     9300S 32P QSFP28 100G 8p QSFP-DD 400G TAA Switch"
       ::= { wndModules 238 }

arubaWiredSwitchModuleS0F96A OBJECT-IDENTITY
        STATUS      current
        DESCRIPTION "The authoritative identifier for the HPE Aruba Networking
                     9300S 32P QSFP28 100G 8p QSFP-DD 400G Switch"
       ::= { wndModules 239 }

arubaWiredSwitchModuleS4K80A OBJECT-IDENTITY
        STATUS      current
        DESCRIPTION "The authoritative identifier for the HPE Aruba Networking
                     CX 10000 48p SFP28 10G/25G 6p QSFP28 100G TAA Switch."
       ::= { wndModules 240 }

arubaWiredSwitchModuleS4B20A OBJECT-IDENTITY
        STATUS      current
        DESCRIPTION "The authoritative identifier for the HPE ANW Networking
                     8325H-18Y4C 18p 25G 4p 100G QSFP28 Front to Back 2 PS 4 Fans Switch"
       ::= { wndModules 241 }

arubaWiredSwitchModuleS4B21A OBJECT-IDENTITY
        STATUS      current
        DESCRIPTION "The authoritative identifier for the HPE ANW Networking
                     8325H-18Y4C 18p 25G 4p 100G QSFP28 Back to Front 2 PS 4 Fans Switch"
       ::= { wndModules 242 }

arubaWiredSwitchModuleS4B22A OBJECT-IDENTITY
        STATUS      current
        DESCRIPTION "The authoritative identifier for the HPE ANW Networking
                     8325H-16C 16p 25G 4p 100G QSFP28 Front to Back 2 PS 4 Fans Switch"
       ::= { wndModules 243 }

arubaWiredSwitchModuleS4B23A OBJECT-IDENTITY
        STATUS      current
        DESCRIPTION "The authoritative identifier for the HPE ANW Networking
                     8325H-16C 16p 25G 4p 100G QSFP28 Back to Front 2 PS 4 Fans Switch"
       ::= { wndModules 244 }

arubaWiredSwitchModuleS2T42A OBJECT-IDENTITY
        STATUS      current
        DESCRIPTION "The authoritative identifier for the HPE ANW Networking
                     8325H-18Y4C 18p 25G 4p 100G QSFP28 Front to Back 2 PS 4 Fans TAA Switch"
       ::= { wndModules 245 }

arubaWiredSwitchModuleS2T46A OBJECT-IDENTITY
        STATUS      current
        DESCRIPTION "The authoritative identifier for the HPE ANW Networking
                     8325H-18Y4C 18p 25G 4p 100G QSFP28 Back to Front 2 PS 4 Fans TAA Switch"
       ::= { wndModules 246 }

arubaWiredSwitchModuleS2T47A OBJECT-IDENTITY
        STATUS      current
        DESCRIPTION "The authoritative identifier for the HPE ANW Networking
                     8325H-16C 16p 25G 4p 100G QSFP28 Front to Back 2 PS 4 Fans TAA Switch"
       ::= { wndModules 247 }

arubaWiredSwitchModuleS2T48A  OBJECT-IDENTITY
        STATUS      current
        DESCRIPTION "The authoritative identifier for the HPE ANW Networking
                     8325H-16C 16p 25G 4p 100G QSFP28 Back to Front 2 PS 4 Fans TAA Switch"
       ::= { wndModules 248 }

arubaWiredSwitchModuleS4A48A OBJECT-IDENTITY
        STATUS      current
        DESCRIPTION "The authoritative identifier for the HPE Aruba Networking
                     8325P 32p QSFP28 40G/100G Switch"
       ::= { wndModules 249 }

arubaWiredSwitchModuleS4P41A OBJECT-IDENTITY
        STATUS      current
        DESCRIPTION "The authoritative identifier for the HPE Aruba Networking
                     6300M 32G 16SR5 2L 2Y Msec Sw"
       ::= { wndModules 250 }

arubaWiredSwitchModuleS4P42A OBJECT-IDENTITY
        STATUS      current
        DESCRIPTION "The authoritative identifier for the HPE Aruba Networking
                     6300M 32SR5 8P 2L 2Y Msec Sw"
       ::= { wndModules 251 }

arubaWiredSwitchModuleS4P43A OBJECT-IDENTITY
        STATUS      current
        DESCRIPTION "The authoritative identifier for the HPE Aruba Networking
                     6300M 48F 2L 2Y Sw"
       ::= { wndModules 252 }

arubaWiredSwitchModuleS4P44A OBJECT-IDENTITY
        STATUS      current
        DESCRIPTION "The authoritative identifier for the HPE Aruba Networking
                     6300M 24F 2L 2Y Sw"
       ::= { wndModules 253 }

arubaWiredSwitchModuleS4P45A OBJECT-IDENTITY
        STATUS      current
        DESCRIPTION "The authoritative identifier for the HPE Aruba Networking
                     6300M 32G 16SR5 CL8 2L 2Y TAA Sw"
       ::= { wndModules 254 }

arubaWiredSwitchModuleS4P46A OBJECT-IDENTITY
        STATUS      current
        DESCRIPTION "The authoritative identifier for the HPE Aruba Networking
                     6300M 32SR5 8P 2L 2Y Msec TAA Sw"
       ::= { wndModules 255 }

arubaWiredSwitchModuleS4P47A OBJECT-IDENTITY
        STATUS      current
        DESCRIPTION "The authoritative identifier for the HPE Aruba Networking
                     6300M 48F 2L 2Y TAA Sw"
       ::= { wndModules 256 }

arubaWiredSwitchModuleS4P48A OBJECT-IDENTITY
        STATUS      current
        DESCRIPTION "The authoritative identifier for the HPE Aruba Networking
                     6300M 24F 2L 2Y TAA Sw"
       ::= { wndModules 257 }

arubaWiredSwitchModuleS4U55A OBJECT-IDENTITY
        STATUS      current
        DESCRIPTION "The authoritative identifier for the HPE ANW 6100 48G CL4 4P 370W MII Switch."
       ::= { wndModules 258 }

arubaWiredSwitchModuleS4U56A OBJECT-IDENTITY
        STATUS      current
        DESCRIPTION "The authoritative identifier for the HPE ANW 6100 48G 4P MII Switch."
       ::= { wndModules 259 }

arubaWiredSwitchModuleS4U57A OBJECT-IDENTITY
        STATUS      current
        DESCRIPTION "The authoritative identifier for the HPE ANW 6100 24G CL4 4P 370W MII Switch."
       ::= { wndModules 260 }

arubaWiredSwitchModuleS4U58A OBJECT-IDENTITY
        STATUS      current
        DESCRIPTION "The authoritative identifier for the HPE ANW 6100 24G 4P MII Switch."
       ::= { wndModules 261 }

arubaWiredSwitchModuleS4U59A OBJECT-IDENTITY
        STATUS      current
        DESCRIPTION "The authoritative identifier for the HPE ANW 6000 48G CL4 4F 370W MII Switch."
       ::= { wndModules 262 }

arubaWiredSwitchModuleS4U60A OBJECT-IDENTITY
        STATUS      current
        DESCRIPTION "The authoritative identifier for the HPE ANW 6000 48G 4F MII Switch."
       ::= { wndModules 263 }

arubaWiredSwitchModuleS4U61A OBJECT-IDENTITY
        STATUS      current
        DESCRIPTION "The authoritative identifier for the HPE ANW 6000 24G CL4 4F 370W MII Switch."
       ::= { wndModules 264 }

arubaWiredSwitchModuleS4U62A OBJECT-IDENTITY
        STATUS      current
        DESCRIPTION "The authoritative identifier for the HPE ANW 6000 24G 4F MII Switch."
       ::= { wndModules 265 }
arubaWiredSwitchModuleS4U63A OBJECT-IDENTITY
        STATUS      current
        DESCRIPTION "The authoritative identifier for the HPE ANW 6200F 24G 4P MII Switch."
       ::= { wndModules 266 }

arubaWiredSwitchModuleS4U64A OBJECT-IDENTITY
        STATUS      current
        DESCRIPTION "The authoritative identifier for the HPE ANW 6200F 24G CL4 4P 370W MII Switch."
       ::= { wndModules 267 }

arubaWiredSwitchModuleS4U65A OBJECT-IDENTITY
        STATUS      current
        DESCRIPTION "The authoritative identifier for the HPE ANW 2930F 48G 4P MII Switch."
       ::= { wndModules 268 }

arubaWiredSwitchModuleS4U66A OBJECT-IDENTITY
        STATUS      current
        DESCRIPTION "The authoritative identifier for the HPE ANW 2930F 48G CL4 4P 370W MII Switch."
       ::= { wndModules 269 }

arubaWiredSwitchModuleS4U67A OBJECT-IDENTITY
        STATUS      current
        DESCRIPTION "The authoritative identifier for the HPE ANW 2930F 48G CL4 4P 740W MII Switch."
       ::= { wndModules 270 }

arubaWiredSwitchModule8325HPowerSupply OBJECT-IDENTITY
        STATUS      current
        DESCRIPTION "The authoritative identifier for the HPE Aruba Networking
                     8325H Power Supply"
       ::= { wndModules 271 }

arubaWiredSwitchModule8325HFanTray OBJECT-IDENTITY
        STATUS      current
        DESCRIPTION "The authoritative identifier for the HPE Aruba Networking
                     8325H Fan"
       ::= { wndModules 272 }

arubaWiredSwitchModuleR8N85B OBJECT-IDENTITY
        STATUS      current
        DESCRIPTION "The authoritative identifier for the HPE ANW 6000 48G CL4 4F 370W Sw."
       ::= { wndModules 273 }

arubaWiredSwitchModuleR8N86B OBJECT-IDENTITY
        STATUS      current
        DESCRIPTION "The authoritative identifier for the HPE ANW 6000 48G 4F Sw."
       ::= { wndModules 274 }

arubaWiredSwitchModuleR8N87B OBJECT-IDENTITY
        STATUS      current
        DESCRIPTION "The authoritative identifier for the HPE ANW 6000 24G CL4 4F 370W Sw."
       ::= { wndModules 275 }

arubaWiredSwitchModuleR8N88B OBJECT-IDENTITY
        STATUS      current
        DESCRIPTION "The authoritative identifier for the HPE ANW 6000 24G 4F Sw."
       ::= { wndModules 276 }

arubaWiredSwitchModuleR8N89B OBJECT-IDENTITY
        STATUS      current
        DESCRIPTION "The authoritative identifier for the HPE ANW 6000 12G CL4 2F 139W Sw."
       ::= { wndModules 277 }

arubaWiredSwitchModuleR9Y03B OBJECT-IDENTITY
        STATUS      current
        DESCRIPTION "The authoritative identifier for the HPE ANW 6000 48G CL4 4F 740W Sw."
       ::= { wndModules 278 }

arubaWiredSwitchModuleS4R20A OBJECT-IDENTITY
        STATUS      current
        DESCRIPTION "The authoritative identifier for the HPE ANW 6000 48G CL4 4F 740W TAA Sw."
       ::= { wndModules 279 }

arubaWiredSwitchModuleS4R21A OBJECT-IDENTITY
        STATUS      current
        DESCRIPTION "The authoritative identifier for the HPE ANW 6000 12G CL4 2F 139W TAA Sw."
       ::= { wndModules 280 }

arubaWiredSwitchModuleS4R22A OBJECT-IDENTITY
        STATUS      current
        DESCRIPTION "The authoritative identifier for the HPE ANW 6000 8G 2F Sw."
       ::= { wndModules 281 }

arubaWiredSwitchModuleS4R23A OBJECT-IDENTITY
        STATUS      current
        DESCRIPTION "The authoritative identifier for the HPE ANW 6000 8G CL4 2F 67W Sw."
       ::= { wndModules 282 }

arubaWiredSwitchModuleS4R24A OBJECT-IDENTITY
        STATUS      current
        DESCRIPTION "The authoritative identifier for the HPE ANW 6000 48G CL4 4F 370W TAA Sw."
       ::= { wndModules 283 }

arubaWiredSwitchModuleS4R25A OBJECT-IDENTITY
        STATUS      current
        DESCRIPTION "The authoritative identifier for the HPE ANW 6000 48G 4F TAA Sw."
       ::= { wndModules 284 }

arubaWiredSwitchModuleS4R26A OBJECT-IDENTITY
        STATUS      current
        DESCRIPTION "The authoritative identifier for the HPE ANW 6000 24G CL4 4F 370W TAA Sw."
       ::= { wndModules 285 }

arubaWiredSwitchModuleS4R27A OBJECT-IDENTITY
        STATUS      current
        DESCRIPTION "The authoritative identifier for the HPE ANW 6000 24G 4F TAA Sw."
       ::= { wndModules 286 }

arubaWiredSwitchModuleS4R28A OBJECT-IDENTITY
        STATUS      current
        DESCRIPTION "The authoritative identifier for the HPE ANW 6000 8G 2F TAA Sw."
       ::= { wndModules 287 }

arubaWiredSwitchModuleS4R29A OBJECT-IDENTITY
        STATUS      current
        DESCRIPTION "The authoritative identifier for the HPE ANW 6000 8G CL4 2F 67W TAA Sw."
       ::= { wndModules 288 }

arubaWiredSwitchModuleS4R50A OBJECT-IDENTITY
        STATUS      current
        DESCRIPTION "The authoritative identifier for the HPE Aruba Networking
                    10040 Front to Back Fan"
       ::= { wndModules 289 }

arubaWiredSwitchModuleS4R51A OBJECT-IDENTITY
        STATUS      current
        DESCRIPTION "The authoritative identifier for the HPE Aruba Networking
                    10040 Back to Front Fan"
       ::= { wndModules 290 }

arubaWiredSwitchModuleS4R52A OBJECT-IDENTITY
        STATUS      current
        DESCRIPTION "The authoritative identifier for the HPE Aruba Networking
                    10040 3000W Front to Back Power Supply"
       ::= { wndModules 291 }

arubaWiredSwitchModuleS4R53A OBJECT-IDENTITY
        STATUS      current
        DESCRIPTION "The authoritative identifier for the HPE Aruba Networking
                    10040 3000W Back to Front Power Supply"
       ::= { wndModules 292 }

arubaWiredSwitchModuleS4R58A OBJECT-IDENTITY
        STATUS      current
        DESCRIPTION "The authoritative identifier for the HPE ANW 10040 FRU Sw"
       ::= { wndModules 293 }

arubaWiredSwitchModuleS4R59A OBJECT-IDENTITY
        STATUS      current
        DESCRIPTION "The authoritative identifier for the HPE ANW 10040 TAA FRU Sw"
       ::= { wndModules 294 }

arubaWiredSwitchFanTrayJL669B OBJECT-IDENTITY
        STATUS      current
        DESCRIPTION "The authoritative identifier for Aruba X751 Front to Back Fan Tray."
       ::= { wndModules 295 }

arubaWiredTransceiverModule OBJECT-IDENTITY
        STATUS      current
        DESCRIPTION "Identifier for transceiver modules (SFP, SFP+, QSFP, QSFP28, etc.)."
        ::= { wndModules 304 }

-- Feature Sub-tree where we allocate OID for Proprietary MIBs

arubaWiredLoopProtectMIB     OBJECT IDENTIFIER ::= { wndFeatures 1 }

arubaWiredMclagMIB           OBJECT IDENTIFIER ::= { wndFeatures 2 }

arubaWiredMgmdSnoopingMIB    OBJECT IDENTIFIER ::= { wndFeatures 3 }

arubaWiredMgmdRmonTrapMIB    OBJECT IDENTIFIER ::= { wndFeatures 4 }

arubaWiredRpvstMIB           OBJECT IDENTIFIER ::= { wndFeatures 5 }

arubaWiredMvrpMIB            OBJECT IDENTIFIER ::= { wndFeatures 6 }

arubaWiredVsxMIB             OBJECT IDENTIFIER ::= { wndFeatures 7 }

arubaWiredPoeMIB             OBJECT IDENTIFIER ::= { wndFeatures 8 }

arubaWiredLldpMIB            OBJECT IDENTIFIER ::= { wndFeatures 9 }

arubaWiredVsfMIB             OBJECT IDENTIFIER ::= { wndFeatures 10 }

arubaWiredChassisMIB         OBJECT IDENTIFIER ::= { wndFeatures 11 }

arubaWiredCiptMIB            OBJECT IDENTIFIER ::= { wndFeatures 12 }

arubaWiredMstpMIB            OBJECT IDENTIFIER ::= { wndFeatures 13 }

arubaWiredMdnsMIB            OBJECT IDENTIFIER ::= { wndFeatures 14 }

arubaWiredVsfv2MIB           OBJECT IDENTIFIER ::= { wndFeatures 15 }

arubaWiredAAAMIB             OBJECT IDENTIFIER ::= { wndFeatures 16 }

arubaWiredPortAccessMIB      OBJECT IDENTIFIER ::= { wndFeatures 17 }

arubaWiredPortVlanMIB        OBJECT IDENTIFIER ::= { wndFeatures 18 }

arubaWiredMacNotifyMIB       OBJECT IDENTIFIER ::= { wndFeatures 19 }

arubaWiredConfigMIB          OBJECT IDENTIFIER ::= { wndFeatures 20 }

arubaWiredPortSecurityMIB    OBJECT IDENTIFIER ::= { wndFeatures 21 }

arubaWiredSystemInfoMIB      OBJECT IDENTIFIER ::= { wndFeatures 22 }

arubawiredProviderBridgeMIB  OBJECT IDENTIFIER ::= { wndFeatures 23 }

arubaWiredInterfaceMIB       OBJECT IDENTIFIER ::= { wndFeatures 24 }

arubaWiredDistServicesMIB    OBJECT IDENTIFIER ::= { wndFeatures 25 }

arubaWiredSwitchImage        OBJECT IDENTIFIER ::= { wndFeatures 26 }

arubaWiredPmMIB              OBJECT IDENTIFIER ::= { wndFeatures 27 }

hpeAnwFlowTelemetryProfileMIB OBJECT IDENTIFIER ::= { wndFeatures 28 }

END
