--**MOD+************************************************************************
--* Module:    ARUBAWIRED-MSTP-MIB : MSTP MIB file
--*
--* (c) Copyright 2020 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains MIB definition of ARUBAWIRED-MSTP-MIB
--*
--**MOD-************************************************************************

ARUBAWIRED-MSTP-MIB DEFINITIONS ::= BEGIN
IMPORTS
            MODULE-IDENTITY, OBJECT-TYPE, Counter32, NOTIFICATION-TYPE,
            Integer32
                 FROM SNMPv2-SMI
            DateAndTime, DisplayString , MacAddress
                 FROM  SNMPv2-TC
            MODULE-COMPLIANCE , OBJECT-GROUP, NOTIFICATION-GROUP
                 FROM SNMPv2-CONF
            wndFeatures
              FROM ARUBAWIRED-NETWORKING-OID;

arubaWiredMstpMIB MODULE-IDENTITY
        LAST-UPDATED "201805290000Z" -- February 18, 2020
        ORGANIZATION "HPE/Aruba Networking Division"
        CONTACT-INFO "Hewlett Packard Enterprise
                          3000 Hanover St.
                          Palo Alto, CA 94304-1112"
        DESCRIPTION
                     "This MIB module for Multiple Spanning
                      Tree Protocol(MSTP)."

        REVISION     "201801180000Z" -- February 18, 2020
        DESCRIPTION
                     "Initial version of this MIB module"
        ::= { wndFeatures 13 }

  -- Top-level structure of MIB
     arubaWiredMstpNotifications  OBJECT IDENTIFIER ::= { arubaWiredMstpMIB 0}
     arubaWiredMstpObjects        OBJECT IDENTIFIER ::= { arubaWiredMstpMIB 1}

     -- NOTIFICATIONS

     arubaWiredMstpNotificationTable OBJECT-TYPE
          SYNTAX          SEQUENCE OF ArubaWiredMstpNotificationEntry
          MAX-ACCESS      not-accessible
          STATUS          current
          DESCRIPTION
               "Information describing the Mstp configuration
               and statistics of the Instances and CIST."
          ::= { arubaWiredMstpObjects 1 }

     arubaWiredMstpNotificationEntry OBJECT-TYPE
          SYNTAX          ArubaWiredMstpNotificationEntry
          MAX-ACCESS      not-accessible
          STATUS          current
          DESCRIPTION
               "Information describing the Mstp
               events for trap generation."
          INDEX           { arubaWiredMstpId }
          ::= { arubaWiredMstpNotificationTable 1 }

     ArubaWiredMstpNotificationEntry ::= SEQUENCE {

          arubaWiredMstpPortName
               DisplayString,
          arubaWiredMstpInstanceID
               Integer32,
          arubaWiredMstpPortErrantBpduRxCount
               Integer32,
          arubaWiredMstpErrantBpduSrcMac
               MacAddress,
          arubaWiredMstpSuperiorBpduSrcPort
               DisplayString,
          arubaWiredMstpSuperiorBpduSrcMac
               MacAddress,
          arubaWiredMstpPortInstanceState
               DisplayString,
          arubaWiredMstpErrantBpduDetector
               INTEGER,
          arubaWiredMstpPortDesignatedBridge
               DisplayString,
          arubaWiredMstpOldPortRole
               DisplayString,
          arubaWiredMstpNewPortRole
              DisplayString,
          arubaWiredMstpTopoChangeTime
               DateAndTime,
          arubaWiredMstpPreviousRootBridgeID
               DisplayString,
          arubaWiredMstpNewRootBridgeID
               DisplayString,
          arubaWiredMstpRootBridgeChangeTimeStamp
               DateAndTime,
          arubaWiredMstpId
               Integer32
     }

     arubaWiredMstpPortName OBJECT-TYPE
          SYNTAX         DisplayString (SIZE (0..20))
          MAX-ACCESS     accessible-for-notify
          STATUS         current
          DESCRIPTION    "The port Name"
          ::= { arubaWiredMstpNotificationEntry 1 }

     arubaWiredMstpInstanceID OBJECT-TYPE
          SYNTAX         Integer32 (0..65)
          MAX-ACCESS     accessible-for-notify
          STATUS          current
          DESCRIPTION    "Unique identifier of the STP Instance."
          ::= { arubaWiredMstpNotificationEntry 2 }

     arubaWiredMstpPortErrantBpduRxCount OBJECT-TYPE
          SYNTAX          Integer32 (0..2147483647)
          MAX-ACCESS      accessible-for-notify
          STATUS          current
          DESCRIPTION     "The number of errant bpdu rx on the port 
                    for the particular instance "
          ::= { arubaWiredMstpNotificationEntry 3 }

     arubaWiredMstpErrantBpduSrcMac OBJECT-TYPE
          SYNTAX      MacAddress
          MAX-ACCESS   accessible-for-notify
          STATUS       current
          DESCRIPTION  "Source MAC address of the port sending this
                    Errant trap."
          ::= { arubaWiredMstpNotificationEntry 4 }

     arubaWiredMstpSuperiorBpduSrcPort OBJECT-TYPE
          SYNTAX         DisplayString (SIZE (0..20))
          MAX-ACCESS     accessible-for-notify
          STATUS          current
          DESCRIPTION    "Port belonging to the Bridge, which 
                    transmitted the superior BPDU."
          ::= { arubaWiredMstpNotificationEntry 5 }

     arubaWiredMstpSuperiorBpduSrcMac OBJECT-TYPE
          SYNTAX       MacAddress
          MAX-ACCESS   accessible-for-notify
          STATUS       current
          DESCRIPTION  "The source MAC address of the port
                    sending superior BPDU."
          ::= { arubaWiredMstpNotificationEntry 6 }

     arubaWiredMstpPortInstanceState OBJECT-TYPE
          SYNTAX          DisplayString (SIZE (0..20))
          MAX-ACCESS      accessible-for-notify
          STATUS          current
          DESCRIPTION     "State of the port for the particular Instance"
          ::= { arubaWiredMstpNotificationEntry 7 }

     arubaWiredMstpErrantBpduDetector OBJECT-TYPE
          SYNTAX       INTEGER{
                         bpduFilter (1),
                         bpduProtection (2)
                        }
          MAX-ACCESS   accessible-for-notify
          STATUS       current
          DESCRIPTION  "The identifier of the feature generating
                         Errant BPDU trap."
          ::= { arubaWiredMstpNotificationEntry 8 }

     arubaWiredMstpPortDesignatedBridge OBJECT-TYPE
          SYNTAX      DisplayString (SIZE (0..20))
          MAX-ACCESS   accessible-for-notify
          STATUS       current
          DESCRIPTION  "The designated bridge name for this STP instance."
          ::= { arubaWiredMstpNotificationEntry 9 }

     arubaWiredMstpOldPortRole OBJECT-TYPE
          SYNTAX      DisplayString (SIZE (0..20))
          MAX-ACCESS   accessible-for-notify
          STATUS       current
          DESCRIPTION  "The previous role of the port before
                    the Topology change.
                    Forwarding/Blocking/Err-DisabledState"
          ::= { arubaWiredMstpNotificationEntry 10 }

     arubaWiredMstpNewPortRole OBJECT-TYPE
          SYNTAX      DisplayString (SIZE (0..20))
          MAX-ACCESS   accessible-for-notify
          STATUS       current
          DESCRIPTION  "The new role of the port after the Topology change.
                    Forwarding/Blocking/Err-DisabledState"
          ::= { arubaWiredMstpNotificationEntry 11 }

     arubaWiredMstpTopoChangeTime OBJECT-TYPE
          SYNTAX      DateAndTime
          MAX-ACCESS   accessible-for-notify
          STATUS       current
          DESCRIPTION  "Time at which the Topology Change happened."
          ::= { arubaWiredMstpNotificationEntry 12 }

     arubaWiredMstpPreviousRootBridgeID OBJECT-TYPE
          SYNTAX       DisplayString (SIZE (0..20))
          MAX-ACCESS   accessible-for-notify
          STATUS       current
          DESCRIPTION  "Bridge ID of the Previous root,
                    before the Topology change."
          ::= { arubaWiredMstpNotificationEntry 13 }

     arubaWiredMstpNewRootBridgeID OBJECT-TYPE
          SYNTAX       DisplayString (SIZE (0..20))
          MAX-ACCESS   accessible-for-notify
          STATUS       current
          DESCRIPTION  "Bridge ID of the New root,
                    after the Topology change."
          ::= { arubaWiredMstpNotificationEntry 14 }

     arubaWiredMstpRootBridgeChangeTimeStamp OBJECT-TYPE
          SYNTAX       DateAndTime
          MAX-ACCESS   accessible-for-notify
          STATUS       current
          DESCRIPTION  "Time when the new root is elected."
          ::= { arubaWiredMstpNotificationEntry 15 }

     arubaWiredMstpId OBJECT-TYPE
          SYNTAX       Integer32 (0..65)
          MAX-ACCESS   not-accessible
          STATUS       current
          DESCRIPTION  "Instance ID"
          ::= { arubaWiredMstpNotificationEntry 16 }

     arubaWiredMstpErrantBpduReceived NOTIFICATION-TYPE
            OBJECTS     {arubaWiredMstpPortName,
                         arubaWiredMstpPortErrantBpduRxCount,
                         arubaWiredMstpErrantBpduSrcMac,
                         arubaWiredMstpPortInstanceState,
                         arubaWiredMstpErrantBpduDetector
                        }
            STATUS      current
            DESCRIPTION
                  "This Trap is generated when an unexpected (errant) BPDU
                  has been received on a port."
            ::= { arubaWiredMstpNotifications 1 }

     arubaWiredMstpInstanceTopologyChange NOTIFICATION-TYPE
            OBJECTS     {arubaWiredMstpPortName,
                         arubaWiredMstpInstanceID,
                         arubaWiredMstpOldPortRole,
                         arubaWiredMstpNewPortRole,
                         arubaWiredMstpTopoChangeTime
                        }
            STATUS      current
            DESCRIPTION
                  "Trap is generated when a Topology Change is detected in
                   the specified INSTANCE."
            ::= { arubaWiredMstpNotifications 2 }

     arubaWiredMstpCISTTopologyChange NOTIFICATION-TYPE
            OBJECTS     {arubaWiredMstpPortName,
                         arubaWiredMstpOldPortRole,
                         arubaWiredMstpNewPortRole,
                         arubaWiredMstpTopoChangeTime
                        }
            STATUS      current
            DESCRIPTION
                  "Trap is generated when a Topology
                         Change is detected in CIST."
            ::= { arubaWiredMstpNotifications 3 }

     arubaWiredMstpInstanceNewRoot NOTIFICATION-TYPE
            OBJECTS     {arubaWiredMstpInstanceID,
                         arubaWiredMstpPreviousRootBridgeID,
                         arubaWiredMstpNewRootBridgeID,
                         arubaWiredMstpRootBridgeChangeTimeStamp
                        }
            STATUS      current
            DESCRIPTION
                  "Trap generated when sending agent has become
                   the new root of spanning Tree for the specified INSTANCE;
                   the notification is sent by a bridge soon after its election
                   as the new root."
            ::= { arubaWiredMstpNotifications 4 }

     arubaWiredMstpCISTNewRoot NOTIFICATION-TYPE
            OBJECTS     {arubaWiredMstpPreviousRootBridgeID,
                         arubaWiredMstpNewRootBridgeID,
                         arubaWiredMstpRootBridgeChangeTimeStamp
                        }
            STATUS      current
            DESCRIPTION
                  "Trap generated when sending agent has become
                   the new root of spanning Tree for the specified CIST;
                   the notification is sent by a bridge soon after its election
                   as the new root."
            ::= { arubaWiredMstpNotifications 5 }

     arubaWiredMstpInstanceLoopGuardInconsistency NOTIFICATION-TYPE
            OBJECTS     {arubaWiredMstpPortName,
                         arubaWiredMstpInstanceID,
                         arubaWiredMstpPortDesignatedBridge
                        }
            STATUS      current
            DESCRIPTION
                  "Trap generated when a Loop Guard feature enabled port
                   receives superior BPDUs on its interface for a
                   given instance."
            ::= { arubaWiredMstpNotifications 6 }

     arubaWiredMstpCISTLoopGuardInconsistency NOTIFICATION-TYPE
            OBJECTS     {arubaWiredMstpPortName,
                         arubaWiredMstpPortDesignatedBridge
                        }
            STATUS      current
            DESCRIPTION
                  "Trap generated when a Loop Guard feature enabled port
                   receives superior BPDUs on its interface for CIST."
            ::= { arubaWiredMstpNotifications 7 }

     arubaWiredMstpInstanceRootGuardInconsistency NOTIFICATION-TYPE
            OBJECTS     {arubaWiredMstpPortName,
                         arubaWiredMstpInstanceID,
                         arubaWiredMstpSuperiorBpduSrcMac,
                         arubaWiredMstpSuperiorBpduSrcPort
                        }
            STATUS      current
            DESCRIPTION
                  "Trap generated when a Root Guard feature enabled port
                   receives superior BPDUs on its interface for a
                   given instance."
            ::= { arubaWiredMstpNotifications 8 }

     arubaWiredMstpCISTRootGuardInconsistency NOTIFICATION-TYPE
            OBJECTS     {arubaWiredMstpPortName,
                         arubaWiredMstpSuperiorBpduSrcMac,
                         arubaWiredMstpSuperiorBpduSrcPort
                        }
            STATUS      current
            DESCRIPTION
                  "Trap generated when a Root Guard feature enabled port
                   receives superior BPDUs on its interface for CIST."
            ::= { arubaWiredMstpNotifications 9 }

 -- Conformance Information

     arubaWiredMstpConformance OBJECT IDENTIFIER ::= { arubaWiredMstpMIB 2}
     arubaWiredMstpGroups OBJECT IDENTIFIER ::= { arubaWiredMstpConformance 1 }

     arubaWiredMstpNotificationObjectGroup   OBJECT-GROUP
         OBJECTS {  arubaWiredMstpPortName,
                    arubaWiredMstpInstanceID,
                    arubaWiredMstpPortErrantBpduRxCount,
                    arubaWiredMstpErrantBpduSrcMac,
                    arubaWiredMstpSuperiorBpduSrcPort,
                    arubaWiredMstpSuperiorBpduSrcMac,
                    arubaWiredMstpPortInstanceState,
                    arubaWiredMstpErrantBpduDetector,
                    arubaWiredMstpPortDesignatedBridge,
                    arubaWiredMstpOldPortRole,
                    arubaWiredMstpNewPortRole,
                    arubaWiredMstpTopoChangeTime,
                    arubaWiredMstpPreviousRootBridgeID,
                    arubaWiredMstpNewRootBridgeID,
                    arubaWiredMstpRootBridgeChangeTimeStamp
                   }
        STATUS          current
        DESCRIPTION   "Group of objects required for
                       notifications."
        ::= { arubaWiredMstpGroups 1 }

    arubaWiredMstpNotificationGroup   NOTIFICATION-GROUP
       NOTIFICATIONS { arubaWiredMstpErrantBpduReceived,
                       arubaWiredMstpInstanceNewRoot,
                       arubaWiredMstpCISTNewRoot,
                       arubaWiredMstpInstanceRootGuardInconsistency,
                       arubaWiredMstpCISTRootGuardInconsistency,
                       arubaWiredMstpInstanceLoopGuardInconsistency,
                       arubaWiredMstpCISTLoopGuardInconsistency,
                       arubaWiredMstpInstanceTopologyChange,
                       arubaWiredMstpCISTTopologyChange
                       }
       STATUS          current
       DESCRIPTION   "Group of notifications."
       ::= { arubaWiredMstpGroups 2 }

-- Compliance Statements

     arubaWiredMstpCompliances OBJECT IDENTIFIER ::=
                    {arubaWiredMstpConformance 2}

     arubaWiredMstpNotificationCompliance MODULE-COMPLIANCE
          STATUS      current
          DESCRIPTION "The compliance statement
                    for Mstp extension notifications."
          MODULE  -- this module
          MANDATORY-GROUPS { arubaWiredMstpNotificationObjectGroup,
                             arubaWiredMstpNotificationGroup
                           }
          ::= { arubaWiredMstpCompliances 1 }
END
