CISCOSB-SENSORENTMIB DEFINITIONS ::= BEGIN

IMPORTS
        rlEnv
                FROM CISCOSB-HWENVIROMENT
        MODULE-IDENTITY, OBJECT-TYPE,
        Integer32, Unsigned32, mib-2
                FROM SNMPv2-SMI
        entPhySensorEntry
                FROM ENTITY-SENSOR-MIB
        MODULE-COMPLIANCE, OBJECT-GROUP
                FROM SNMPv2-CONF
        TEXTUAL-CONVENTION, TimeStamp
                FROM SNMPv2-TC
        entPhysicalIndex, entityPhysicalGroup
                FROM ENTITY-MIB
        SnmpAdminString
                FROM SNMP-FRAMEWORK-MIB
        EntitySensorValue
                FROM ENTITY-SENSOR-MIB;

rlSensor MODULE-IDENTITY
    LAST-UPDATED "200309210000Z"
    ORGANIZATION "Cisco Systems, Inc."

    CONTACT-INFO
    "Postal: 170 West Tasman Drive
    San Jose , CA 95134-1706
    USA

    
    Website:  Cisco Small Business Support Community <http://www.cisco.com/go/smallbizsupport>"

    DESCRIPTION
            "The private MIB module definition for sensors in CISCOSB devices."
    REVISION "200309210000Z"
    DESCRIPTION
            "ADDED this MODULE-IDENTITY clause."
    ::= { rlEnv 4 }



RlEntitySensorLocation ::= TEXTUAL-CONVENTION
    STATUS       current
    DESCRIPTION
            "An object using this data type represents the location
            of a physical sensor.
            
            The value 'pcb(1)' indicates that sensor is external or located in
            thermal controller (on PCB).
            
            The value 'pp(2)' indicates that sensor is located in packet processor 
            chip.
            
            The value 'poe(3)' indicates that sensor is located in PoE chip.

            The value 'phy(4)' indicates that sensor is located in PHY chip.
            
            The value 'cpu(5)' indicates that sensor is located in CPU chip.
            
            The value 'notassembled(6)' indicates that sensor is not assembled."
    SYNTAX INTEGER {
        pcb(1),
        pp(2),
        poe(3),
        phy(4),
        cpu(5),
        notassembled(6)
    }

rlEntPhySensorTable OBJECT-TYPE
        SYNTAX     SEQUENCE OF RlEntPhySensorEntry
        MAX-ACCESS not-accessible
        STATUS     current
        DESCRIPTION
                "The addition to the table of sensors maintained by the environmental
                monitor."
        ::= { rlEnv 3 }

rlEntPhySensorEntry OBJECT-TYPE
        SYNTAX     RlEntPhySensorEntry
        MAX-ACCESS not-accessible
        STATUS     current
        DESCRIPTION
                "An additon to the entry in the sensor table, representing the
                maximum/minimum values for the sensor associated."
        AUGMENTS     {entPhySensorEntry}
        ::= { rlEntPhySensorTable 1 }

RlEntPhySensorEntry ::=
        SEQUENCE {
                rlEnvPhySensorMinValue       EntitySensorValue,
                rlEnvPhySensorMaxValue       EntitySensorValue,
                rlEnvPhySensorTestValue      EntitySensorValue,
                rlEnvPhySensorLocation       RlEntitySensorLocation
        }

rlEnvPhySensorMinValue OBJECT-TYPE
        SYNTAX     EntitySensorValue
        MAX-ACCESS read-only
        STATUS     current
        DESCRIPTION
                "Minimum value for the Sensor being instrumented."
        ::= { rlEntPhySensorEntry 1 }

rlEnvPhySensorMaxValue OBJECT-TYPE
        SYNTAX     EntitySensorValue
        MAX-ACCESS read-only
        STATUS     current
        DESCRIPTION
                "Maximum value for the Sensor being instrumented."
        ::= { rlEntPhySensorEntry 2 }

rlEnvPhySensorTestValue OBJECT-TYPE
        SYNTAX     EntitySensorValue
        MAX-ACCESS read-write
        STATUS     current
        DESCRIPTION
                "Test/reference value for the Sensor being instrumented."
        ::= { rlEntPhySensorEntry 3 }

rlEnvPhySensorLocation OBJECT-TYPE
        SYNTAX     RlEntitySensorLocation
        MAX-ACCESS read-only
        STATUS     current
        DESCRIPTION
                "Location value for the Sensor being instrumented."
        ::= { rlEntPhySensorEntry 4 }
END
