-- *****************************************************************
-- E7-TC.my: Calix Networks E7 Textual Conventions
--
-- Calix confidential and proprietary.
--
-- Copyright (c) 2007-2009 Calix Networks, Inc.
-- All rights reserved.
-- *****************************************************************

E7-TC DEFINITIONS ::= BEGIN

    IMPORTS
	TEXTUAL-CONVENTION
	    FROM SNMPv2-TC
	;

E7AlarmType ::= TEXTUAL-CONVENTION
    STATUS current
    DESCRIPTION "E7 supported alarms"
    SYNTAX INTEGER {
        none(0),
		logInit(1),
        moreToShow(2),
        unequipped(3),
        notOperational(4),
        mismatchEquipmentAttributes(5),
        backupFilesExist(6),
        restoreFileExists(7),
        multipleDatabases(8),
        improperRemoval(9),
        badInventory(10),
        unsupportedEquipment(11),
        lowSoftwareResources(12),
        ntpFreeRunning(13),
        ntpServer1Down(14),
        ntpServer2Down(15),
        ntpServer3Down(16),
        databaseFailure(17),
        cardTooCold(18),
        equipOverheat(19),
        lossOfSignal(20),
        aggLinkDown(21),
        eapsIsolatedNode(22),
        erpsRingPortDown(23),
        erpsRingDown(24),
        erpsSecondRingMaster(25),
        erpsActingRingMaster(26),
        fanFailure(27),
        rstpNoPrimary(28),
        rstpNoSecondary(29),
        rstpMultiplePrimaries(30),
        rstpMultipleSecondaries(31),
        airCompressorFail(32),
        airConditioningFail(33),
        airDryerFail(34),
        batteryDischarging(35),
        batteryFail(36),
        centralizedPwrFail(37),
        commericalPwrFail(38),
        coolingFanFail(39),
        engineFail(40),
        engineOperating(41),
        explosiveGas(42),
        fireDetectorFail(43),
        fire(44),
        flood(45),
        fuseFail(46),
        generatorFail(47),
        highAirflow(48),
        highHumidity(49),
        highTemp(50),
        highWater(51),
        intrusion(52),
        lowBatterVoltage(53),
        lowCablePressure(54),
        lowFuel(55),
        lowHumidity(56),
        lowTemp(57),
        lowWater(58),
        miscellaneous(59),
        openDoor(60),
        pumpFail(61),
        rectifierFail(62),
        rectifierHighVoltage(63),
        rectifierLowVoltate(64),
        smoke(65),
        toxicGas(66),
        ventilationFail(67),
        releaseNotCommitted(68),
        upgradeInProgress(69),
        newReleaseIsReady(70),
        moduleFault(71),
        contactOffNormal(72),
        powerAFail(73),
        powerBFail(74),
        bootDataCorrupt(75),
        power(76),
        thermal(77),
        security(78),
        lacpFault(79),
        rstpFault(80),
        unrecognizedSfp(81),
        shelfError(82),
        differentVersion(83),
        ponLaserEol(84),
        lossOfPon(85),
        ontMissing(86),
        ontMismatch(87),
        ontProvError(88),
        ontEquipFailed(89),
        ontOnBattery(90),
        ontBatteryMissing(91),
        ontBatteryFailed(92),
        ontBatteryLow(93),
        ontRfSignalLow(94),
        ontRfReturnLaserEol(95),
        ontEthDown(96),
        ontDs1LosLof(97),
        ontDs1Rai(98),
        ontDs1Ais(99),
        noStandbyController(100),
        noBpDataPath(101),
        svcWithNoFac(102),
        timingFreerun(103),
        timingHoldover(104),
        timingLockedA(105),
        timingLockedB(106),
        timingFailSrcA(107),
        timingFailSrcB(108),
        timingFailDevice(109),
        equipmentFailure(110),
        ontSoftwareMismatch(111),
        unused112(112),
        switchingPowerSupplyAFailed(113),
        switchingPowerSupplyBFailed(114),
        ontDs1LosMatrix(115),
        ontDs1LofMatrix(116),
        ponBwOverSubscribed(117),
        reserved118(118),
        reserved119(119),
        reserved120(120),
        duplicateOntRegId(121),
        gponReplicationResourceExhausted(122),
        cpldOutOfRev(123),
        bpduGuard(124),
        moduleNotForStacking(125),
        ethOamMepNearEndMaxLoss(126),
        ethOamMepNearEndAvgLoss(127),
        ethOamMepNearFarMaxLoss(128),
        ethOamMepNearFarAvgLoss(129),
        ethOamMepMaxDelayMeasurement(130),
        ethOamMepAvgDelayMeasurement(131),
        ethOamMepMaxDelayVariation(132),
        ethOamMepCcmLossOfContinuity(133),
        ethOamMepCcmRxInterfaceNotUp(134),
        ethOamMepCcmRxUnexpectedMeg(135),
        ethOamMepCcmRxUnexpectedMep(136),
        ethOamMepCcmRxUnexpectedPeriod(137),
        stackingRingPortDown(138),
        stackingRingSecondMaster(139),
        stackingRingActingMaster(140),
        ontPwe3FarEndLossOfPackets(141),
        ontPwe3FarEndLossOfSignal(142),
        ontPwe3MalformedPackets(143),
        ethOamMepCcmRxWithRdi(144),
        ethOamMepAvgDelayThresholdExceeded(145),
        rfc2544Loopback(146),
        e5TooOld(147),
        bpduUnknown(148),
        equipIdFail(149),
        noTimingCard(150),
        efmDown(151),
        rfiSignalLoss(152),
        rfiDyingGasp(153),
        rfiCriticalAlarm(154),
        noPower(155),
        ftaOutOfDate(156),
        cardNotFullyInserted(157),
        voipLowSoftwareResources(158),
        switchControlFault(159),
        voipDown(160),
        initialFlashWriteInProgress(161),
        voipRegFail(162),
        stackingRingHealthCompromised(163),
        erpsDomainHealthCompromised(164),
        controlVlanAuditFailure(165),
        ontRfSignalBad(166),
        interfaceQualityAuditFailure(167),
        xdslPortProvFailure(168),
        xdslGroupProvFailure(169),
        xdslGroupLowRateDownstream(170),
        xdslGroupLowRateUpstream(171),
        xdslGroupLossOfSignal(172),
        cardTypeDiffers(173),
        cardHwFailure(174),
        softwareInitializationInProgress(175),
        stackingRingVlanProvError(176),
        fastIgmpRingVlanProvError(177),
        dosAttack(178),
        ontUpgradeInProgress(179),
        differentOntPackage(180),
        deltInProgress(181),
        seltInProgress(182),
        ontConfigInProgress(183),
        differentOntConfig(184),
        ontUsSdber(185),
        ontDsSdber(186),
        ontRgConfigUnavailable(187),
        h248MgToMgcAssocDown(188),
        fileUpdateInProgress(189),
        ont3pFileUpgradeInProgress(190),
        differentOnt3pFile(191),
        voiceHwInitFailure(192),
        switchCriticalEvent(193),
        voipDhcpFail(194),
        improperConnectionOnStackingPort(195),
        potsCalibrationFailure(196),
        dcVbattFailure(197),
        ontDyingGasp(200),
        lowRxOptPowerNe(201),
        highRxOptPowerNe(202),
        lowRxOptPowerFe(203),
        highRxOptPowerFe(204),
        lowTxOptPower(205),
        highTxOptPower(206),
        lowLaserBias(207),
        highLaserBias(208),
        lowOptLaunchPower(209),
        highOptLaunchPower(210),
        lowOntTemperature(211),
        highOntTemperature(212),
        xdslVectoringProvFailure(213),
        ontSelfTestFailed(214),
        aggInterfaceDegraded(215),
        ontSipConfigUnavailable(216),
        ponRogueDetected(217),
        ontRogueDetected(218),
        erpsIsolatedNode(219),
        erpsLocalSf(220),
        erpsRemoteSf(221),
        erpsLocalMs(222),
        erpsRemoteMs(223),
        erpsLocalFs(224),
        erpsRemoteFs(225),
        erpsFopTo(226),
        erpsFopPm(227),
        msgQueueOverflow(228),
        voipMsgQueueOverflow(229),
        ontYellowTemp(230),
        ontRedTemp(231),
        missingOntImages(232),
        unexpectedMessageSize(233),
        tooManyLinkedOnts(234),
        coefFileInProgress(235),
        differentCoefFile(236),
        igmpVersionMismatch(237),
        dslConfigFileUpgrade(238),
        differentDslConfigFile(239),

        noDslConfigFile(240),
        sipuaRegName(241),
        sipuaRegReach(242),
        sipuaRegConnect(243),
        sipuaRegValidate(244),
        sipuaRegAuth(245),
        sipuaRegTimeout(246),
        sipuaRegFail(247),
        ffpDown(248),
        ffpNoProtect(249),

        fileserverUnavailable(250),
        dcVbatt80VFailure(251),
        dcVbattNegtive54VFailure(252),
        dcVbattNegtive36VFailure(253),
        vectoringFailure(254),
        vccLinkFailure(255),
        vectoringHardwareFailure(256),
        vectoringServiceDegrade(257),
        slvTargetDown(258),
        vectoringSoftwareVersionMismatch(259),

        ontPreloadInProgress(260),
        cpePortProvFail(261),
        cpeUplinkGroupProvFail(262),
        cpeUplinkGroupLowRateDs(263),
        cpeUplinkGroupLowRateUs(264),
        cpeUplinkGroupLos(265),
        cpePortLos(266),
        mgmtgePortsDown(267),
        mgmtgeGatewayNotReachable(268),
        dyingGasp(269),

        hg0Failure(270),
        timingFirmwareMismatch(271),
        timingFirmwareDownload(272),
        timingFirmwareCorrupt(273),
        ontFileServerNotProvisioned(274),
        fantrayCapabilityInSufficient(275),
        failureOnRemoteOntFile(276),
        ontFileServerUnavailable(277),
        ponBwOverSubscribedDs(278),
        pseoverloadred(279),
        remotePowerFailure(280),

		ulpDown(282),
        ulpNoProtect(283),

        fallBackToLocalAuthen(285),
		tacacsAuthUnreachable(286),
		tacacsAccUnreachable(287),
		poweredDown(288)
    }

E7EventType ::= TEXTUAL-CONVENTION
    STATUS current
    DESCRIPTION "E7 supported general events"
    SYNTAX INTEGER {
        none(0),
        logInit(1),
        upgradeHadErrors(2),
        upgradeFailedToXferFiles(3),
        upgradeFailedToRun(4),
        resetInProgress(5),
        resetSuccess(6),
        resetHadErrors(7),
        resetFailedToRun(8),
        commitInProgress(9),
        commitSuccess(10),
        commitHadErrors(11),
        commitFailedToCommit(12),
        revertInProgress(13),
        revertSuccess(14),
        revertHadErrors(15),
        revertFailedToRun(16),
        revertFailedToCommit(17),
        autoUpgrInProgress(18),
        autoUpgrSuccess(19),
        autoUpgrFailedToXferFiles(20),
        autoUpgrFailedToRun(21),
        autoUpgrFailedToCommit(22),
        deleteUpgrInProgress(23),
        deleteUpgrSuccess(24),
        deleteUpgrHadErrors(25),
        deleteUpgrFailed(26),
        databaseRestoreInProgress(27),
        databaseRestoreComplete(28),
        databaseRestoreCompleteWithFailures(29),
        vlanMacThresholdExceeded(30),
        stpMemoryAllocationFailure(31),
        stpBufferAllocationFailure(32),
        stpNewRoot(33),
        stpTopologyChange(34),
        stpProtocolMigration(35),
        stpInvalidBpdu(36),
        stpNewPortRole(37),
        erpsProtocolViolation(38),
        erpsInvalidProvisioning(39),
        timeSet(40),
        databaseReset(41),
        cancelUpgrInProgress(42),
        cancelUpgrSuccess(43),
        cancelUpgrHadErrors(44),
        cancelUpgrFailed(45),
        switchoverInProgress(46),
        switchoverSuccess(47),
        switchoverAborted(48),
        unused49(49),
        ontArrival(50),
        ontDeparture(51),
        ontDebugUpgrInProgress(52),
        ontDebugUpgrSuccess(53),
        ontDebugUpgrHadErrors(54),
        ontDebugUpgrFailed(55),
        ontPreArrival(56),
        autoUpgrTooManyFailures(57),
        cardArrival(58),
        cardDeparture(59),
        unused60(60),
        ontLink(61),
        ontUnlink(62),
        rebootInProgress(63),
        rebootSuccess(64),
        rebootHadErrors(65),
        rebootFailed(66),
        cancelResetInProgress(67),
        cancelResetSuccess(68),
        stackingRingProtocolViolation(69),
        stackingRingInvalidProvisioning(70),
        unused71(71),
        systemTimeSet(72),
        cardMigrationUpgrade(73),
        igmpGroupLimitReached(74),
        aeOntDiscovered(75),
        remoteLinkOamLoopbackStart(76),
        remoteLinkOamLoopbackEnd(77),
        localLinkOamLoopbackStart(78),
        localLinkOamLoopbackEnd(79),
        ontFileXferInProgress(80),
        ontFileXferSuccess(81),
        ontFileXferHadErrors(82),
        ontFileXferFailed(83),
        ontDownloadInProgress(84),
        ontDownloadSuccess(85),
        ontDownloadHadErrors(86),
        ontDownloadFailed(87),
        ontActivateInProgress(88),
        ontActivateSuccess(89),
        ontActivateHadErrors(90),
        ontActivateFailed(91),
        configFileXferInProgress(92),
        configFileXferSuccess(93),
        configFileXferHadErrors(94),
        configFileXferFailed(95),
        configFileApplyInProgress(96),
        configFileApplySuccess(97),
        configFileApplyHadErrors(98),
        configFileApplyFailed(99),
        ontFileCancelInProgress(100),
        ontFileCancelSuccess(101),
        ontFileCancelHadErrors(102),
        ontFileCancelFailed(103),
        ontFileRemoveInProgress(104),
        ontFileRemoveSuccess(105),
        ontFileRemoveHadErrors(106),
        ontFileRemoveFailed(107),
        ontUserReset(108),
        lldpDelete(109),
        lldpUpdate(110),
        ontAutoQuarantine(111),
        ontT1InbandLpbkStart(112),
        ontT1InbandLpbkEnd(113),
        license3rdPartyOntDelink(114),
        coefFileTransInProgress(115),
        coefFileTransSuccess(116),
        coefFileTransHadErrors(117),
        coefFileTransFailed(118),
        coefFileApplyInProgress(119),
        coefFileApplySuccess(120),
        coefFileApplyHadErrors(121),
        coefFileApplyFailed(122),
        coefFileCancelInProgress(123),
        coefFileCancelSuccess(124),
        coefFileCancelHadErrors(125),
        coefFileCancelFailed(126),
        coefFileRemoveInProgress(127),
        coefFileRemoveSuccess(128),
        coefFileRemoveHadErrors(129),

        coefFileRemoveFailed(130),
        dslConfigRetrieveInProgress(131),
        dslConfigRetrieveComplete(132),
        dslConfigRetrieveCompleteWithErrors(133),
        dslConfigRetrieveFailed(134),
        dslConfigApplyInProgress(135),
        dslConfigApplyComplete(136),
        dslConfigApplyCompleteWithErrors(137),
        dslConfigApplyFailed(138),
        dslConfigCancelInProgress(139),

        dslConfigCancelComplete(140),
        dslConfigCancelCompleteWithErrors(141),
        dslConfigCancelFailed(142),
        dslConfigRemoveInProgress(143),
        dslConfigRemoveComplete(144),
        dslConfigRemoveCompleteWithErrors(145),
        dslConfigRemoveFailed(146),
        resettingVoipCard(147),
        ffpSwitchover(148),
        vectoringModeSwitched(149),

        fallbackToNonVectoring(150),
        ontFileInstallInProgress(151),
        ontFileInstallComplete(152),
        ontFileInstallCompleteWithErrors(153),
        ontFileInstallFailed(154),
        recoveredFromFallback(159),
        failToMoveEthSvc(160),
        dnxGponLifFailed(161),
        nonvectoringcpearrived(162),
        ulpSwitchover(163),
        ontPortColorEnabled(164),
        ontPortColorDisabled(165),
        ontPortColorDisplay(166),
        ontPortColorUndisplay(167)
    }

E7SecurityType ::= TEXTUAL-CONVENTION
    STATUS current
    DESCRIPTION "E7 supported security events"
    SYNTAX INTEGER {
        none(0),
        unused1(1),
        userLogin(2),
        userLogout(3),
        inactiveLogout(4),
        adminForcedLogout(5),
        loginFailed(6),
        alarmLogCleared(7),
        dbChangeLogCleared(8),
        eventLogCleared(9),
        securityLogCleared(10),
        tcaLogCleared(11),
        unused12(12),
        radiusLoginFailBadSecret(13),
        databaseReset(14)
    }

E7TcaType ::= TEXTUAL-CONVENTION
    STATUS current
    DESCRIPTION "E7 supported tcas"
    SYNTAX INTEGER {
        cvC(2),
        cvCFe(3),
        fecC(4),
        fecCFe(5),
        fecL(6),
        fecLFe(7),
        esL(8),
        esLFe(9),
        sesL(10),
        sesLFe(11),
        lossL(12),
        lossLFe(13),
        uasL(14),
        uasLFe(15),
        initL(16),
        lInitL(17),
        crcP(18),
        cvP(19),
        inErrors(43),
        inDiscards(44),
        fcsErr(61),
        exColl(62),
        lateColl(63),
        longFrame(64),
        rxBufOvfl(65),
        txBufOvfl(66),
        snglColl(67),
        multColl(68),
        sqe(69),
        deferredTx(70),
        macTxErr(71),
        carSenseErr(72),
        alignErr(73),
        macRxErr(74),
        errSec(75),
        sevErrSec(76),
        burstySec(77),
        unavailSec(78),
        rxCtrlSlipSec(79),
        missingPkts(88),
        misorderUsable(89),
        misorderDropped(90),
        bufferUnderOverrun(91),
        malformedPkts(92),
        strayPkts(93),
        mmtPktLoss(94),
        tdmLbitPktsSent(95)
    }

E7ObjectClass ::= TEXTUAL-CONVENTION
    STATUS current
    DESCRIPTION
        "Object class reported in the traps and AlarmTable"
    SYNTAX INTEGER {
        invalid(0),
        system(1),
        card(2),
        dhcpGlobal(3),
        ethPortAny(4),
        opt82Prof(5),
        vlan(6),
        sshKeyOld(7),
        chassis(8),
        shelf(9),
        db(10),
        snmpTrapDest(11),
        envPin(12),
        snmpCommunity(13),
        rstpConfig(14),
        craftUser(15),
        igmpGroup(16),
        craftSerial(17),
        craftFe(18),
        ponPort(19),
        ontEthMcastProf(20),
        ontEthStaticIp(21),
        fanTray(22),
        igmpMember(23),
        portMonitor(24),
        monitorSource(25),
        dscpMap(26),
        mgmtConfig(27),
        igmpConfig(28),
        ntp(29),
        macTableEntry(30),
        ontEthSvc(31),
        ontEthTagAction(32),
        ontEthBwProf(33),
        ontEthSecuProf(34),
        cos(35),
        ethStudy(36),
        erps(37),
        snmpUser(38),
        notfLogIndex(39),
        snmpConfig(40),
        potPortCos(41),
        l2CtrlProfile(42),
        l2Acl(43),
        l2AclRule(44),
        ethGePort(45),
        eth10GePort(46),
        vlanMember(47),
        tagAction(48),
        ponCosConfig(49),
        policyMap(50),
        policy(51),
        classMap(52),
        classRule(53),
        acl(54),
        aclRule(55),
        l3Acl(56),
        l3AclRule(57),
        ethPortGos(58),
        ontFEth(59),
        ethIntf(60),
        lagIntf(61),
        intfAny(62),
        ont(63),
        ontSlot(64),
        ontGigEth(65),
        ontHpnaEth(66),
        ontEthAny(67),
        ontRfVideo(68),
        ontHotRfVideo(69),
        ontVideoAny(70),
        ontPots(71),
        ontDs1(72),
        ontPortAny(73),
        ontProfile(74),   
        macTableCount(75),
        ontSipSvc(76),
        sipProfile(77),
        mcastAddrRange(78),
        mvrProfile(79),
        ontIpHost(80),
        discOnt(81),
        quarnatineOnt(82),
        ontEthSvcName(83),
        ontEthGos(84),
        ontDs1Gos(85),
        ontCsipSvc(86),
        csipProfile(87),
        ontPwe3Svc(88),
        ontPwe3Profile(89),
        ds1Pwe3Profile(90),
        bpVlanMap(91),
        ontMatchList(92),
        ontMatchRuleTagged(93),
        ontMatchRuleUntagged(94),
        timing(95),
        timingSrc(96),
        ontPwe3Gos(97),
        igmpIntfAny(98),
        sshKey(99),
        ontMgmt(100),
        ontRfAvo(101),
        radiusCfg(102),
        radiusAuthServer(103),
        radiusAcctServer(104),
        mcastFilter(105),
        syslog(106),
        mvrVlan(107),
        dhcpLease(108),
        systemVlanMap(109),
        ethOamCfg(110),
        ethOamPmProfile(111),
        ethOamMeg(112),
        ethOamMep(113),
        ethOamMip(114),
        ethOamRemoteMep(115),
        igmpRouterPort(116),
        vlanIgmpProfile(117),
        h248MediaGwProfile(118),
        ontH248Svc(119),
        ethOamDiscRmtMep(120),
        ethOamLbResults(121),
        ethOamLtHistory(122),
        ethOamLtResults(123),
        ethOamMepStats(124),
        ethOamMipStats(125),
        ethOamFrameDelay(126),
        ethOamFrameLoss(127),
        ifVlanIgmpRtd(128),
        backplane10GePort(129),
        bkplLink(130),
        sslPrivKey(131),
        sslCert(132),
        l2cpRange(133),
        l2cpFilter(134),
        powerInput(135),
        lcPots(136),
        lcIpHost(137),
        vdslPort(138),
        vdslBondedIntf(139),
        lcH248Svc(140),
        lcSipSvc(141),
        lcTdmGwSvc(142),
        bkplGePort(143),
        vdslPortTemplate(144),
        vdslPortTemplateData(145),
        vdslPortTemplateMask(146),
        vdslPortGos(147),
        ethIntfEthSvc(148),
        ethIntfEthSvcStaticIp(149),
        bondedIntfEthSvc(150),
        bondedIntfEthSvcStaticIp(151),
        pppoeProf(152),
        dialPlan(153),
        dialPlanRule(154),
        vdslBpsc(155),
        pppoeSession(156),
        pppoeDiscStats(157),
        sipGwProf(158),
        ontMgcpSvc(159),
        mgcpMediaGwProf(160),
        ipPrecMap(161),
        avoCfg(162),
        vdslPortEthPm(163),
        vdslBondRtd(164),
        ontRg(165),
        ontFb(166),
        ontPonUsCos(167),
        macFilter(168),
        macFilterRule(169),
        ontPhyPort(170),
        ontMgmtSvc(171),
        ponUsCosProf(172),
        lcH248Gw(173),
        lcMgcpGw(174),
        ontRgMgmtProf(175),
        ethPortLocalLldp(176),
        vdslDelt(177),
        vdslDeltHlinReal(178),
        vdslDeltHlinImag(179),

        vdslDeltHlog(180),
        vdslDeltQln(181),
        vdslDeltSnr(182),
        eapsTopoEntry(183),
        ethPortRemoteLldp(184),
        vdslVectorGrp(185),
        ethPortLldpUnrecTlvs(186),
        ontEthStatsRtd(187),
        g8032Ring(188),
        g8032RingPortCfg(189),

        vdslSelt(190),
        vdslSeltTFunc(191),
        license(192),
        mcastWhiteList(193),
        mcastWhiteListRange(194),
        singleLinkEthWhiteList(195),
        ontEthWhiteList(196),
        bondedLinkEthWhiteList(197),
        eth40GePort(198),
        ffpGroup(199),

        ffpGroupActPort(200),
        dot1xCfg(201),
        dot1xAuthServer(202),
        dot1xProf(203),
        vlanIpHost(204),
        dhcpSvcProf(205),
        dot1xAcctServer(206),
        dot1xStatsRtd(207),
        vccPort(208),
        mgmtGe(209),

        cpePort(211),
        cpeBondedUplink(212),
        vdslBondUplinkRtd(213),
        cpeBondedUplinkRtd(214),
        cpePortEthPm(215),
        dyingGasp(216),
        vtuBpsc(217),
        externOnt(218),
        voicePolicyProf(219),

        activation(220),
        VcpMgmt(221),
        vdslVector(222),
        vdslVectorFallbackTmpltData(223),
        vdslVectorFallbackTmpltMask(224),
        powerDomain(225),
        powerNode(226),

        ulpGroup(233),

        tacacsCfg(236),
        tacacsAuthServer(237),
        tacacsAcctServer(238)
        
    }

-- the following items are for the future E7-Calix MIB
E7AdminStatus ::= TEXTUAL-CONVENTION
    STATUS current
    DESCRIPTION "administrative status values"
    SYNTAX INTEGER {
        unknown(0),
        enabled(1),
        alarmsuppress(2),
        disabled(3)
    }

E7CardType ::= TEXTUAL-CONVENTION
    STATUS current
    DESCRIPTION "E7 card types"
    SYNTAX INTEGER {
        none(0),
        unknown(1),
        agg(1012),              -- E5400 card
        backplaneE5400(1013),
        backplaneE7x2SlotChassis1RU(1014),
        fantrayE5400(1015),
        fantrayE7x2SlotChassis1RU(1016),
        gpon4(1017),
        activeEthernet(1018),   -- E5312 card
        backplaneE5312(1019),
        tenge4(1020),           -- 10ge-4, leading digits not always accepted
        backplaneE7x2S0lotChassis(1021),
        fantrayE7x20SlotChassis(1022),
        ge12(1023),
        scp(1026),
        ge24(1027),
        ge32(1028),
        gpon4x(1029),
        ge24x(1030),
        vdsl48c(1031), -- VDSL combo card 
        vdsl48(1032),
        e5Voip(1033),
        gpon4r2(1036),
        gpon8(1037),
        gpon8x(1038),
        vdsl48Db(1039),
        e348c(1040),
        backplaneE348C(1041),
        ex10gTestLc(1042),
        e3Voip(1043),
        scpPlus(1044),
        fantrayE7x2SlotChassis1RU2(1045),
        vdsl48d(1046), -- VDSL data only
        e38g(1047),-- E3-8G
        e38gIntf(1048), -- E3-8G Intferface
        backplaneE38G(1049), -- E3-8G backplane
        scp240g(1500), -- SCP2-40ge
        ge4x(1501), -- 10GE4x
        gpon16x(1502),
        scp210g(1503),  -- SCP2-10ge
        ngpon4(1504),
        fantrayExLFta2(1510),
        vdsl48cr2(1515), -- VDSL combo card r2
        vdsl48r2(1516), -- VDSL overlay card r2
        vdsl48dr2(1517), -- VDSL data only card r2
        vcp192(1518), -- VCP 192 card
        vcp384(1519), -- VCP 384 card
        fantrayE5Fta2(2000),
        e548c(2001),
        e548(2003),
        e548Db(2004),
        backplaneE5(2005),
        e348cr2Fiber(2006), --E3 VDSL-48C R2 Fiber
        e348cr2Hybrid(2007), -- E3 VDSL-48C R2 Hybrid
        e348or2Fiber(2008), --E3 VDSL-48O R2 Fiber
        e348or2Hybrid(2009), -- E3 VDSL-48O R2 Hybrid
        e3vcp192(2010),  -- E3 VCP192
        e3vdsl48r2Voip(2011),
        e3vdsl48r2Db(2012)
    }

E7PowerLevel ::= TEXTUAL-CONVENTION
    STATUS current
    DESCRIPTION "Power level for card"
    SYNTAX INTEGER {
        notSet(0),
        powerLevelLow(1),
        powerLevel2(2),
        powerLevel3(3),
        powerLevel4(4),
        powerLevelFull(5)
    }

E7SnmpVers ::= TEXTUAL-CONVENTION
    STATUS current
    DESCRIPTION "E7 snmp versions (for trap destinations)"
    SYNTAX INTEGER {
        unknown(0),
        v2c(2),
        v3(3)
    }

E7SnmpMsgFilter ::= TEXTUAL-CONVENTION
    STATUS current
    DESCRIPTION "E7 snmp message filter(for trap destinations)"
    SYNTAX INTEGER {
        all(0),
        event(1),
        tca(2),
        db(3),
        alarm(4)
    }

E7OntType ::= TEXTUAL-CONVENTION
    STATUS current
    DESCRIPTION "E7 ONT types"
    SYNTAX INTEGER {
               none(0),
               unknown(1)
           }   
           
E7EtherType ::= TEXTUAL-CONVENTION
    STATUS current
    DESCRIPTION "E7 Ethernet types"
    SYNTAX INTEGER {
               invalid(0),
               e8100(1),
               e88a8(2),
               e9100(3),
               any(4),
               ppoe(5),
               arp(6),
               ipv4(7),
               ipv6(8)
           }   
           
E7Pbit ::= TEXTUAL-CONVENTION
    STATUS current
    DESCRIPTION "E7 Pbit "
    SYNTAX INTEGER {
                invalid(0),
                pbit(1),
                promote(2),
                useCosId(3),
                useIfMap(4),
                preserve(5),
                useOuter(6)
    }

E7BondedInterfaceIndex ::= TEXTUAL-CONVENTION
    STATUS current
    DESCRIPTION "E7 DSL bonded interface index"
    SYNTAX INTEGER (0..2237183)

E7OperStatus ::= TEXTUAL-CONVENTION
    STATUS current
    DESCRIPTION "Operational status values"
    SYNTAX INTEGER {
        invalid(0),
        enabled(1),
        degraded(2),
        systemdisabled(3)
        userdisabled(4)
    }

E7XdslGrpOperStatus ::= TEXTUAL-CONVENTION
    STATUS current
    DESCRIPTION "Xdsl group Operational status values"
    SYNTAX INTEGER {
        invalid(0),
        up(1),
        down(2),
        test(3)
        unknown(4)
        dormant(5)
        notpresent(6)
        lowlayerdown(7)
    }



END
