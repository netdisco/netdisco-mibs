--       Suresh gandhi 
--       Bluesocket, Inc.
--       Jan  2003
--       Copyright Bluesocket, Inc. 2001-2002
--       WARNING:
--       This MIB is DRAFT-ONLY and is subject to change.
--       Management Information Base for  Blueserver

BLUE-NOTIFICATION-MIB DEFINITIONS ::= BEGIN

      IMPORTS
         OBJECT-TYPE, enterprises
                                          FROM SNMPv2-SMI
         blueSocket 
                                          FROM BLUESERVER-MIB
         DisplayString,DateAndTime, PhysAddress 
				                          FROM SNMPv2-TC;

    	blueNotification   OBJECT IDENTIFIER ::= { blueSocket 2 }

        notifyObjects      OBJECT IDENTIFIER ::=  { blueNotification 1 }
        blueTraps          OBJECT IDENTIFIER ::=  { blueNotification 2 }
        configChangeTraps  OBJECT IDENTIFIER ::=  { blueTraps 1 }
        FailureTraps       OBJECT IDENTIFIER ::=  { blueTraps 2 }

-- Notification group
-- notifyObjects group
        ntyobjLevel OBJECT-TYPE
        SYNTAX  OCTET STRING(SIZE(1..20))
        ACCESS  accessible-for-notify
        STATUS  current
        DESCRIPTION
               "Event priority or log level."
        DEFVAL { Info }       
        ::= { notifyObjects 1}

        ntyobjObjName OBJECT-TYPE
        SYNTAX  OCTET STRING(SIZE(1..255))
        ACCESS  accessible-for-notify
        STATUS  current
        DESCRIPTION
             "The name of the object that triggered the event.
              In case of no objects assosicated with
              failures, the value will be NULL.  "
        DEFVAL { Unknown }       
        ::= { notifyObjects 2 }

        ntyobjDesc OBJECT-TYPE
        SYNTAX  OCTET STRING(SIZE(0..255))
        ACCESS  accessible-for-notify
        STATUS  current
        DESCRIPTION
             "Description about event/trap."
        DEFVAL { NULL }       
        ::= { notifyObjects 3 }

        ntyobjObjOID OBJECT-TYPE
        SYNTAX  OBJECT IDENTIFIER
        ACCESS  accessible-for-notify
        STATUS  current
        DESCRIPTION
             "The OID of the object that triggered the event"
        DEFVAL { 0.0 }       
        ::= { notifyObjects 4 }

        ntyobjObjvalue OBJECT-TYPE
        SYNTAX  OCTET STRING(SIZE(0..255))
        ACCESS  accessible-for-notify
        STATUS  current
        DESCRIPTION
             "The value of the object that triggered
              the event at the time of event occurrence."
        DEFVAL { NULL }       
        ::= { notifyObjects 5 }


-- blueTraps group
-- configChangeTraps group

    cctSystemConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 1 }

    cctUserConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 2 }


    cctExternalServConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 3 }


    cctRoleConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 4 }

    cctDestinationConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 5 }


    cctServiceConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 6 }


    cctInterfaceConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 7 }


    cctIpsecConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 8 }

    cctMobilityConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 9 }

    cctProcessConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 10 }


    cctDhcpConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjObjName - The name of the object that triggered the event
             ntyobjDesc    - Description about the event/trap 
             "
    ::= { configChangeTraps 11 }

    cctIKEConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjtrObjName - The name of the object that triggered the event
             ntyobjtrDesc    - Description about the event/trap 
             "
    ::= { configChangeTraps 12 }

    cctImageConfChange NOTIFICATION-TYPE
    OBJECTS { ntyobjLevel,ntyobjObjName,ntyobjDesc}
    STATUS  current
    DESCRIPTION
            "This trap will be sent for any Configuration changes. 
             Example: 
                User    added/modified/deleted
                Service added/modified/delete. 
             ntyobjLevel   - Indicate the priority or log level
             ntyobjtrObjName - The name of the object that triggered the event
             ntyobjtrDesc    - Description about the event/trap 
             "
    ::= { configChangeTraps 13 }




--FailureTraps group

    btSysConfFailure  NOTIFICATION-TYPE
    OBJECTS { ntyobjLevel,ntyobjObjName,ntyobjDesc}
    STATUS  current
    DESCRIPTION
            "This trap will be sent on any failures. 
             Example: 
                User Login failure
                Authentication failure
                Failover 
             ntyobjLevel   - Indicate the priority or log level
             ntyobjObjName - The name of the object that triggered the event.
                         In case of no objects assosicated with
                         failures, the value will be NULL.
             
             ntyobjDesc    - Description about the event/trap 
             "
    ::= { FailureTraps 1 }

    btIKEFailure  NOTIFICATION-TYPE
    OBJECTS { ntyobjLevel,ntyobjObjName,ntyobjDesc}
    STATUS  current
    DESCRIPTION
            "This trap will be sent on any failures. 
             Example: 
                User Login failure
                Authentication failure
                Failover 
             ntyobjLevel   - Indicate the priority or log level
             ntyobjObjName - The name of the object that triggered the event.
                         In case of no objects assosicated with
                         failures, the value will be NULL.
             
             ntyobjDesc    - Description about the event/trap 
             "
    ::= { FailureTraps 2 }

    btProcessFailure  NOTIFICATION-TYPE
    OBJECTS { ntyobjLevel,ntyobjObjName,ntyobjDesc}
    STATUS  current
    DESCRIPTION
            "This trap will be sent on any failures. 
             Example: 
                User Login failure
                Authentication failure
                Failover 
             ntyobjLevel   - Indicate the priority or log level
             ntyobjObjName - The name of the object that triggered the event.
                         In case of no objects assosicated with
                         failures, the value will be NULL.
             
             ntyobjDesc    - Description about the event/trap 
             "
    ::= { FailureTraps 3 }



    btConditionalEvent NOTIFICATION-TYPE
    OBJECTS { ntyobjLevel,ntyobjObjOID,ntyobjObjValue,ntyobjDesc}
    STATUS  current
    DESCRIPTION
            "This trap will be sent if the threshold have been met for
            the underlaying Object. 
             Example: 
                User    added/modified/deleted
                Service added/modified/delete. 
             ntyobjLevel    - Indicate the trap priority or log level
             ntyobjObjOID  - The OID of the object that triggered the event
             ntyobjObjValue - The value of the object that triggered
                          the event at the time of event occurrence.
             trDesc     - Description about the event/trap 
             "
    ::= { blueTraps 3 }
  END
