BLUESERVER-MIB DEFINITIONS ::= BEGIN

      IMPORTS
         OBJECT-TYPE, NOTIFICATION-TYPE,TimeTicks, 
         Integer32, MODULE-IDENTITY, enterprises
                          FROM SNMPv2-SMI
         TEXTUAL-CONVENTION,DisplayString, RowStatus, DateAndTime
		              FROM SNMPv2-TC;
        
blueSocket MODULE-IDENTITY
    LAST-UPDATED "200303100000Z"
    ORGANIZATION "Bluesocket Inc."
    CONTACT-INFO
            "   Suresh Gandhi
                Bluesocket, Inc.
                Burlington, MA 01803
                sgandhi@bluesocket.com
            "
    DESCRIPTION
       "This MIB is DRAFT-ONLY and is subject to change.
        Management Information Base for Blueserver."

    ::= { enterprises 9967 }

          blueSocket
                            FROM BLUESOCKET-ROOT;

    	   blueServer         OBJECT IDENTIFIER ::= { blueSocket 1 }
    	   blueNotification   OBJECT IDENTIFIER ::= { blueSocket 2 }

        users              OBJECT IDENTIFIER ::= { blueServer 1 }
--                         OBJECT IDENTIFIER ::= { blueServer 2 }
        destination        OBJECT IDENTIFIER ::= { blueServer 3 }
        service            OBJECT IDENTIFIER ::= { blueServer 4 }
        policy             OBJECT IDENTIFIER ::= { blueServer 5 }
        vpn                OBJECT IDENTIFIER ::= { blueServer 6 }
        configuration      OBJECT IDENTIFIER ::= { blueServer 7 }
        interface          OBJECT IDENTIFIER ::= { blueServer 8 }
        replication        OBJECT IDENTIFIER ::= { blueServer 9 }
        connection         OBJECT IDENTIFIER ::= { blueServer 10 }
        roles              OBJECT IDENTIFIER ::= { blueServer 11 }
        serviceMgmt        OBJECT IDENTIFIER ::= { blueServer 12 }
        statistics         OBJECT IDENTIFIER ::= { blueServer 13 } 
        vlan               OBJECT IDENTIFIER ::= { blueServer 14 } 
        schedule           OBJECT IDENTIFIER ::= { blueServer 15 } 
        

--user group
        nativeUsers        OBJECT IDENTIFIER ::= { users 1 }
        adminUsers         OBJECT IDENTIFIER ::= { users 2 }
        
-- vpn group
        ipsec              OBJECT IDENTIFIER ::=  { vpn  1 }
        pptp               OBJECT IDENTIFIER ::=  { vpn  2 }
        subnetVpn          OBJECT IDENTIFIER ::=  { vpn  3 }
        certificate        OBJECT IDENTIFIER ::=  { vpn  4 }
        l2tp               OBJECT IDENTIFIER ::=  { vpn  5 }
       
-- configuration group
        http               OBJECT IDENTIFIER ::=  { configuration  1 }
        misc               OBJECT IDENTIFIER ::=  { configuration  2 }
        autoBackup         OBJECT IDENTIFIER ::=  { configuration  3 }
        time               OBJECT IDENTIFIER ::=  { configuration  4 }       
        mobility           OBJECT IDENTIFIER ::=  { configuration  5 }       
        publicAccess       OBJECT IDENTIFIER ::=  { configuration  6 }       
        confLog            OBJECT IDENTIFIER ::=  { configuration  7 }       
        snmpConf           OBJECT IDENTIFIER ::=  { configuration  8 }       
        systemTracker      OBJECT IDENTIFIER ::=  { configuration  9 }       
        authentication     OBJECT IDENTIFIER ::=  { configuration  10 }       

-- interface Group
--                         OBJECT IDENTIFIER ::=  { interface 1 }
--                         OBJECT IDENTIFIER ::=  { interface 2 }
        failover           OBJECT IDENTIFIER ::=  { interface 3 }
        managed            OBJECT IDENTIFIER ::=  { interface 4 }
        protected          OBJECT IDENTIFIER ::=  { interface 5 }
        
        userSummary        OBJECT IDENTIFIER ::=  { statistics 1 }
        systemStats        OBJECT IDENTIFIER ::=  { statistics 2 }
    
        confLogGroup       OBJECT IDENTIFIER ::=  { confLog    1 }       

	
-- snmp configuration group
        snmpTrapConf       OBJECT IDENTIFIER ::= { snmpConf  1 }       
       
--   Authentication groups
     exAuthServer          OBJECT IDENTIFIER ::= { authentication 1 }

-- notification groups
        notifyObjects      OBJECT IDENTIFIER ::=  { blueNotification 1 }
        blueTraps          OBJECT IDENTIFIER ::=  { blueNotification 2 }

        blueConfigTraps    OBJECT IDENTIFIER ::=  { blueTraps 1 }
        blueFailureTraps   OBJECT IDENTIFIER ::=  { blueTraps 2 }
        blueThresholdTraps OBJECT IDENTIFIER ::=  { blueTraps 3 }
        blueGeneralTraps   OBJECT IDENTIFIER ::=  { blueTraps 4 }

-- textual convention
--        BlueIpAddress ::= OCTET STRING (SIZE (7..15)) 

--        BlueMacAddress ::= OCTET STRING (SIZE (6..17)) 

--        LocalDateAndTime ::= OCTET STRING (SIZE (4)) 


BlueIpAddress ::= TEXTUAL-CONVENTION
    DISPLAY-HINT "1d.1d.1d.1d"
    STATUS       current
    DESCRIPTION
            ""
    SYNTAX       OCTET STRING (SIZE (7..15))


BlueMacAddress ::= TEXTUAL-CONVENTION
    DISPLAY-HINT "1x:1x:1x:1x:1x:1x"
    STATUS       current
    DESCRIPTION
            ""
    SYNTAX       OCTET STRING (SIZE (17))

LocalDateAndTime ::= TEXTUAL-CONVENTION
    DISPLAY-HINT ""
    STATUS       current
    DESCRIPTION
            ""
    SYNTAX       OCTET STRING (SIZE (6))

-- the user Group

        nativeUserTable     OBJECT-TYPE
        SYNTAX   SEQUENCE OF NativeUserEntry
        MAX-ACCESS            not-accessible
        STATUS             current
        DESCRIPTION    "A list of nativeUser entries."
              ::= { nativeUsers 1 }

        nativeUserEntry OBJECT-TYPE
        SYNTAX  NativeUserEntry
        MAX-ACCESS  not-accessible
        STATUS  current
        DESCRIPTION
             "A nativeUser entry containing information 
              about a particular nativeUser."
        INDEX   { nativeUserId }
        ::= { nativeUserTable 1 }

        NativeUserEntry ::=
              SEQUENCE {
                  nativeUserId
                      Integer32,
                  nativeUserAccess
                      INTEGER,
                  nativeUserName
                      DisplayString,
                  nativeUserRoleId
                      Integer32,
                  nativeUserEmailId
                      DisplayString,
                  nativeUserFixedIpAddr
                      BlueIpAddress,
                  nativeUserPassword
                      DisplayString,
                  nativeUserNotes
                      DisplayString,
                  nativeUserRowStatus
                      RowStatus, 
                  nativeUserRadAcctServId
                      Integer32
          }
        nativeUserId OBJECT-TYPE
        SYNTAX  Integer32 (1..2147483647)
        MAX-ACCESS  not-accessible
        STATUS  current
        DESCRIPTION

               "A unique id  for each nativeUser."
        ::= { nativeUserEntry 1 }

        nativeUserAccess OBJECT-TYPE
        SYNTAX  INTEGER {
                   disable(0),
                   enable(1)

                } 
        MAX-ACCESS  read-create
        STATUS  current
        DESCRIPTION
              "To Enable/disable an nativeUser."
        ::= { nativeUserEntry 2 }

        nativeUserName OBJECT-TYPE
        SYNTAX  DisplayString
        MAX-ACCESS  read-create
        STATUS  current
        DESCRIPTION
               "A unique Name for each nativeUser"
        ::= { nativeUserEntry 3 }

        nativeUserRoleId OBJECT-TYPE
        SYNTAX  Integer32 
        MAX-ACCESS  read-create
        STATUS  current
        DESCRIPTION
              "The role Id associated with this nativeUser"
        ::= { nativeUserEntry 4 }

        nativeUserEmailId OBJECT-TYPE
        SYNTAX  DisplayString
        MAX-ACCESS  read-create

        STATUS  current
              DESCRIPTION
                      "The Email address of the nativeUser"
        ::= { nativeUserEntry 5 }

        nativeUserFixedIpAddr OBJECT-TYPE
        SYNTAX  BlueIpAddress
        MAX-ACCESS  read-create
        STATUS  current
        DESCRIPTION

               "Required for users connecting using the Windows 2000 IPSec client"
        ::= { nativeUserEntry 6 }

        nativeUserPassword OBJECT-TYPE
        SYNTAX  DisplayString
        MAX-ACCESS  read-create
        STATUS  current
        DESCRIPTION
                "The nativeUser password"
        ::= { nativeUserEntry 7 }


        nativeUserNotes OBJECT-TYPE
        SYNTAX  DisplayString
        MAX-ACCESS  read-create
        STATUS  current
        DESCRIPTION
               "Notes"
        ::= { nativeUserEntry 8 }

        nativeUserRowStatus OBJECT-TYPE
        SYNTAX  RowStatus
        MAX-ACCESS  read-create
        STATUS  current
        DESCRIPTION
               "The Row status attribute for row handling"

        ::= { nativeUserEntry 9 }

        nativeUserRadAcctServId OBJECT-TYPE
        SYNTAX  Integer32
        MAX-ACCESS  read-create
        STATUS  current
        DESCRIPTION
               "The row id from exRadAcctServTable for the 
               selected radius accounting server."
        ::= { nativeUserEntry 10 }

        adminUserTable     OBJECT-TYPE
        SYNTAX   SEQUENCE OF AdminUserEntry
        MAX-ACCESS            not-accessible
        STATUS             current
        DESCRIPTION    "A list of adminUser entries."
              ::= { adminUsers 1 }

        adminUserEntry OBJECT-TYPE
        SYNTAX  AdminUserEntry
        MAX-ACCESS  not-accessible
        STATUS  current
        DESCRIPTION
             "An adminUser entry containing information about a particular 
             adminUser."
        INDEX   { adminUserId }
        ::= { adminUserTable 1 }

        AdminUserEntry ::=
              SEQUENCE {
                  adminUserId
                      Integer32,
                  adminUserStatus
                      INTEGER,
                  adminUserName
                      DisplayString,
                  adminUserAccess
                      INTEGER,
                  adminUserEmailId
                      DisplayString,
                  adminUserPassword
                      DisplayString,
                  adminUserNotes
                      DisplayString,
                  adminUserRowStatus
                      RowStatus 
          }

        adminUserId OBJECT-TYPE
        SYNTAX  Integer32(1..2147483647)
        MAX-ACCESS  not-accessible
        STATUS  current
        DESCRIPTION
               "A unique value for each adminUser."
        ::= { adminUserEntry 1 }


        adminUserStatus OBJECT-TYPE
        SYNTAX  INTEGER {
                   disable(0),
                   enable(1)
                } 
        MAX-ACCESS  read-create
        STATUS  current
        DESCRIPTION
              "To Enable/disable an adminUser."
        ::= { adminUserEntry 2 }

        adminUserName OBJECT-TYPE
        SYNTAX  DisplayString
        MAX-ACCESS  read-create
        STATUS  current
        DESCRIPTION
               "A unique name for each admin user"
        ::= { adminUserEntry 3 }

        adminUserAccess OBJECT-TYPE
        SYNTAX  INTEGER {
                   full(1),
                   intermediate(2),
                   readOnly(3)
                } 

        MAX-ACCESS  read-create
        STATUS  current
        DESCRIPTION
              "Admin user access level
              full - have all complete access
              intermediate - the adUsrAccessTable decides the access
                             level of this admin user.
              readonly - Readonly access"
        ::= { adminUserEntry 4 }

        adminUserEmailId OBJECT-TYPE
        SYNTAX  DisplayString
        MAX-ACCESS  read-create
        STATUS  current
              DESCRIPTION
                      "The email address of the admin user"
        ::= { adminUserEntry 5 }

        adminUserPassword OBJECT-TYPE
        SYNTAX  DisplayString
        MAX-ACCESS  read-create
        STATUS  current
        DESCRIPTION
                "The adminUser password. Get and getnext request on this 
                object returns encrypted password value"
        ::= { adminUserEntry 6 }

        adminUserNotes OBJECT-TYPE
        SYNTAX  DisplayString
        MAX-ACCESS  read-create
        STATUS  current
        DESCRIPTION
               "Admin user notes"
        ::= { adminUserEntry 7 }

        adminUserRowStatus OBJECT-TYPE
        SYNTAX  RowStatus 
        MAX-ACCESS  read-create
        STATUS  current
        DESCRIPTION
               "The Row status attribute for row handling"
        ::= { adminUserEntry 9 }

        adUsrAccessTable     OBJECT-TYPE
        SYNTAX   SEQUENCE OF AdUsrAccessEntry
        MAX-ACCESS            not-accessible
        STATUS             current
        DESCRIPTION    "A list of adUsrAccess entries."
              ::= { users 3 }

        adUsrAccessEntry OBJECT-TYPE
        SYNTAX  AdUsrAccessEntry
        MAX-ACCESS  not-accessible
        STATUS  current
        DESCRIPTION
             " Extended table from adminUserTable. The values from
             adminUserAccess column take higher precedence and this
             table entry will be considered only when the adminUserAccess 
             column from adminUserTable has a value of 'intermediate'. 
                 This table is to configure the various level of 
             administrator privilages. This is mainly for admin who 
             try to manage BSCs using Web interfaces. 
                 Every column in this table correspond to a tab name in 
             web interface. So choosing enable/disable will
             grant/deny access to the administrator user for the
             corresponding tabs.

             Note: The administrator with the username as 'admin have 
             all access and considered as the the super user for BSCs"

        INDEX   { adminUserId }
        ::= { adUsrAccessTable 1 }

        AdUsrAccessEntry ::=
              SEQUENCE {
                  adUsrAccessAdminUser
                      INTEGER,
                  adUsrAccessNativeUser
                      INTEGER,
                  adUsrAccessExServer
                      INTEGER,
                  adUsrAccessAccounting
                      INTEGER,
                  adUsrAccessRoles
                      INTEGER,
                  adUsrAccessDestination
                      INTEGER,
                  adUsrAccessServices
                      INTEGER,
                  adUsrAccessVpn
                      INTEGER,
                  adUsrAccessConfiguration
                      INTEGER,
                  adUsrAccessNetwork
                      INTEGER,
                  adUsrAccessReplication
                      INTEGER,
                  adUsrAccessMaintance
                      INTEGER,
                  adUsrAccessStatus
                      INTEGER,
                  adUsrAccessVlans
                      INTEGER,
                  adUsrAccessSchedules
                      INTEGER,
                  adUsrAccessMacDev
                      INTEGER
          }

        adUsrAccessAdminUser OBJECT-TYPE
        SYNTAX  INTEGER {
                   disable(0),
                   enable(1)
                } 
        MAX-ACCESS  read-create
        STATUS  current
        DESCRIPTION
              "To grant/deny access to manage administrator users."
        ::= { adUsrAccessEntry 1 }

        adUsrAccessNativeUser OBJECT-TYPE
        SYNTAX  INTEGER {
                   disable(0),
                   enable(1)
                } 
        MAX-ACCESS  read-create
        STATUS  current
        DESCRIPTION
              "To grant/deny access to manage native/local users."
        ::= { adUsrAccessEntry 2 }


        adUsrAccessExServer OBJECT-TYPE
        SYNTAX  INTEGER {
                   disable(0),
                   enable(1)
                } 
        MAX-ACCESS  read-create
        STATUS  current
        DESCRIPTION
              "To grant/deny access to manage external servers."
        ::= { adUsrAccessEntry 3 }



        adUsrAccessAccounting OBJECT-TYPE
        SYNTAX  INTEGER {
                   disable(0),
                   enable(1)
                } 
        MAX-ACCESS  read-create
        STATUS  current

        DESCRIPTION
              "To grant/deny access to manage accounting server"
        ::= { adUsrAccessEntry 4 }


        adUsrAccessRoles OBJECT-TYPE
        SYNTAX  INTEGER {
                   disable(0),
                   enable(1)
                } 
        MAX-ACCESS  read-create
        STATUS  current
        DESCRIPTION
              "To grant/deny access to manage roles."
        ::= { adUsrAccessEntry 5 }


        adUsrAccessDestination OBJECT-TYPE
        SYNTAX  INTEGER {
                   disable(0),
                   enable(1)
                } 
        MAX-ACCESS  read-create
        STATUS  current
        DESCRIPTION
              "To grant/deny access to manage Destinations."
        ::= { adUsrAccessEntry 6 }

        adUsrAccessServices OBJECT-TYPE
        SYNTAX  INTEGER {
                   disable(0),
                   enable(1)
                } 
        MAX-ACCESS  read-create
        STATUS  current
        DESCRIPTION
              "To grant/deny access to manage Services."
        ::= { adUsrAccessEntry 7 }

        adUsrAccessVpn OBJECT-TYPE
        SYNTAX  INTEGER {
                   disable(0),
                   enable(1)
                } 
        MAX-ACCESS  read-create
        STATUS  current
        DESCRIPTION
              "To grant/deny access to manage Vpn."
        ::= { adUsrAccessEntry 8 }

        adUsrAccessConfiguration OBJECT-TYPE
        SYNTAX  INTEGER {
                   disable(0),
                   enable(1)
                } 
        MAX-ACCESS  read-create
        STATUS  current
        DESCRIPTION
              "To grant/deny access to manage Configuration."
        ::= { adUsrAccessEntry 9 }

        adUsrAccessNetwork OBJECT-TYPE
        SYNTAX  INTEGER {
                   disable(0),
                   enable(1)
                } 
        MAX-ACCESS  read-create
        STATUS  current
        DESCRIPTION
              "To grant/deny access to manage Network."

        ::= { adUsrAccessEntry 10 }

        adUsrAccessReplication OBJECT-TYPE
        SYNTAX  INTEGER {
                   disable(0),
                   enable(1)
                } 
        MAX-ACCESS  read-create
        STATUS  current
        DESCRIPTION
              "To grant/deny access to manage replication."
        ::= { adUsrAccessEntry 11 }


        adUsrAccessMaintance OBJECT-TYPE
        SYNTAX  INTEGER {
                   disable(0),
                   enable(1)
                } 
        MAX-ACCESS  read-create
        STATUS  current
        DESCRIPTION
              "To grant/deny access to manage administrator users
               "
        ::= { adUsrAccessEntry 12 }

        adUsrAccessStatus OBJECT-TYPE
        SYNTAX  INTEGER {
                   disable(0),
                   enable(1)
                } 
        MAX-ACCESS  read-create
        STATUS  current
        DESCRIPTION
              "To grant/deny access to manage status information "
        ::= { adUsrAccessEntry 13 }

        adUsrAccessVlans OBJECT-TYPE
        SYNTAX  INTEGER {
                   disable(0),
                   enable(1)
                } 
        MAX-ACCESS  read-create
        STATUS  current
        DESCRIPTION
              "To grant/deny access to manage vlans "
        ::= { adUsrAccessEntry 14 }

        adUsrAccessSchedules OBJECT-TYPE
        SYNTAX  INTEGER {
                   disable(0),
                   enable(1)
                } 
        MAX-ACCESS  read-create
        STATUS  current
        DESCRIPTION
               "The Row status attribute for row handling"
        ::= { adUsrAccessEntry 15 }


        adUsrAccessMacDev OBJECT-TYPE
        SYNTAX  INTEGER {
                   disable(0),
                   enable(1)
                } 
        MAX-ACCESS  read-create
        STATUS  current
        DESCRIPTION
              "To grant/deny access to manage mac device external authentication
              servers"
        ::= { adUsrAccessEntry 16 }

        -- exAuthServer group
        -- radius authentication server group
        
        exRdAuthServTable     OBJECT-TYPE
        SYNTAX   SEQUENCE OF ExRdAuthServEntry

        MAX-ACCESS            not-accessible
        STATUS             current
        DESCRIPTION    
           "A table to hold information about external Raduis server."
              ::= { exAuthServer 2 }

        exRdAuthServEntry OBJECT-TYPE
        SYNTAX  ExRdAuthServEntry
        MAX-ACCESS  not-accessible
        STATUS  current
        DESCRIPTION
                "" 
        INDEX   { exRdAuthServId }
            ::= { exRdAuthServTable 1 }

        ExRdAuthServEntry ::=
              SEQUENCE {
                  exRdAuthServId
                       Integer32,
                  exRdAuthServState
                      INTEGER,
                  exRdAuthServName
                      DisplayString,
                  exRdAuthServDefRoleId 
                      Integer32,
                  exRdAuthServRdAccId
                      Integer32,
                  exRdAuthServAddr
                       DisplayString,
                  exRdAuthServPort
                      Integer32,
                  exRdAuthServSecret
                       DisplayString,
                  exRdAuthServPrecedence
                       Integer32,
                  exRdAuthServNotes
                      DisplayString,
                  exRdAuthServRowStatus
                      RowStatus 
        }
        exRdAuthServId OBJECT-TYPE
        SYNTAX  Integer32 (1..2147483647)
        MAX-ACCESS  not-accessible 
        STATUS  current
        DESCRIPTION
                "Unique Id for each entry in this table"
        ::= { exRdAuthServEntry 1 }

        exRdAuthServState OBJECT-TYPE
        SYNTAX  INTEGER {
                   disable(0),
                   enable(1)
                }
        MAX-ACCESS  read-create
        STATUS  current
        DESCRIPTION

               "To Enable/Disable  an external radius server"
        ::= { exRdAuthServEntry 2 }

        exRdAuthServName OBJECT-TYPE
        SYNTAX  DisplayString
        MAX-ACCESS  read-create
        STATUS  current
        DESCRIPTION
                "A unique external radius server name."
        ::= { exRdAuthServEntry 3 }

        exRdAuthServDefRoleId OBJECT-TYPE
        SYNTAX  Integer32
        MAX-ACCESS  read-create
        STATUS  current
        DESCRIPTION
                "Default role  Id for external server users. Should be
                an existing roleId from roleTable"
        ::= { exRdAuthServEntry 4 }

--      := { exRdAuthServEntry 5 }

        exRdAuthServRdAccId OBJECT-TYPE
        SYNTAX  Integer32
        MAX-ACCESS  read-create
        STATUS  current
        DESCRIPTION
                "For accounting logging with authentication.
                 Should be an existing exRdAccServId from
                 exRdAccServTable"

        ::= { exRdAuthServEntry 6 }

        exRdAuthServAddr OBJECT-TYPE
        SYNTAX  DisplayString
        MAX-ACCESS  read-create
        STATUS  current
        DESCRIPTION
                "Radius server Ip address or DNS name"
        ::= { exRdAuthServEntry 7 }

        exRdAuthServPort OBJECT-TYPE
        SYNTAX  Integer32
        MAX-ACCESS  read-create
        STATUS  current
        DESCRIPTION
                "Radius server port number"
        ::= { exRdAuthServEntry 8 }

        exRdAuthServSecret OBJECT-TYPE
        SYNTAX  DisplayString
        MAX-ACCESS  read-create
        STATUS  current
        DESCRIPTION
                "Shared secret"
        ::= { exRdAuthServEntry 9 }

        exRdAuthServPrecedence OBJECT-TYPE
        SYNTAX  Integer32
        MAX-ACCESS  read-create
        STATUS  current
        DESCRIPTION
                "The server's precedence for verifying username/passwords"
        ::= { exRdAuthServEntry 10 }

        exRdAuthServNotes OBJECT-TYPE
        SYNTAX  DisplayString
        MAX-ACCESS  read-create
        STATUS  current
        DESCRIPTION
                "Notes"
        ::= { exRdAuthServEntry 11 }

        exRdAuthServRowStatus OBJECT-TYPE
        SYNTAX  RowStatus 
        MAX-ACCESS  read-create
        STATUS  current
        DESCRIPTION
               "The Row status attribute for row handling"
        ::= { exRdAuthServEntry 12 }

        exLdapServTable     OBJECT-TYPE
        SYNTAX   SEQUENCE OF ExLdapServEntry
        MAX-ACCESS            not-accessible
        STATUS             current
        DESCRIPTION    "list of LDAP external servers."
              ::= { exAuthServer 3 }

        exLdapServEntry OBJECT-TYPE
        SYNTAX  ExLdapServEntry

        MAX-ACCESS  not-accessible
        STATUS  current
        DESCRIPTION
                "" 
        INDEX   { exLdapServId }
            ::= { exLdapServTable 1 }

        ExLdapServEntry ::=
              SEQUENCE {

                  exLdapServId
                      Integer32,
                  exLdapServState
                      INTEGER,
                  exLdapServName
                      DisplayString,
                  exLdapServDefRoleId 
                      Integer32,
                  exLdapServRdAccState
                      INTEGER,
                  exLdapServRdAccId
                      Integer32,
                  exLdapServAddr
                       DisplayString,
                  exLdapServPort
                      Integer32,
                  exLdapServBase
                       DisplayString,
                  exLdapServUniqueId
                       DisplayString,
                  exLdapServAccount
                       DisplayString,
                  exLdapServFilters
                       DisplayString,
                  exLdapServSecret
                       DisplayString,
                  exLdapServPrecedence
                       Integer32,
                  exLdapServNotes
                      DisplayString,
                  exLdapServSsl
                      OCTET STRING,
                  exLdapServSslServer
                      Integer32,
                  exLdapServSslClient
                      Integer32,
                  exLdapServRowStatus
                      RowStatus
        }
        exLdapServId OBJECT-TYPE
        SYNTAX  Integer32 (1..2147483647)
        MAX-ACCESS  not-accessible 
        STATUS  current
        DESCRIPTION
                "Unique Id for each entry in this table"
        ::= { exLdapServEntry 1 }

        exLdapServState OBJECT-TYPE
        SYNTAX  INTEGER {
                   disable(0),
                   enable(1)
                }
        MAX-ACCESS  read-create
        STATUS  current
        DESCRIPTION
               "To Enable/Disable  an external Ldap authentication server"
        ::= { exLdapServEntry 2 }

        exLdapServName OBJECT-TYPE
        SYNTAX  DisplayString
        MAX-ACCESS  read-create
        STATUS  current
        DESCRIPTION
                "A unique external server name"
        ::= { exLdapServEntry 3 }

        exLdapServDefRoleId OBJECT-TYPE
        SYNTAX  Integer32
        MAX-ACCESS  read-create
        STATUS  current
        DESCRIPTION
                "Default role for external server users"
        ::= { exLdapServEntry 4 }

        exLdapServRdAccState OBJECT-TYPE
        SYNTAX  INTEGER {
                   disable(0),
                   enable(1)
                }
        MAX-ACCESS  read-create
        STATUS  current
        DESCRIPTION
               ""
        ::= { exLdapServEntry 5 }


        exLdapServRdAccId OBJECT-TYPE
        SYNTAX  Integer32
        MAX-ACCESS  read-create
        STATUS  current
        DESCRIPTION
                "For accounting logging with authentication"
        ::= { exLdapServEntry 6 }

        exLdapServAddr OBJECT-TYPE
        SYNTAX  DisplayString
        MAX-ACCESS  read-create
        STATUS  current
        DESCRIPTION
                "LDAP server Ip address or DNS name"
        ::= { exLdapServEntry 7 }

        exLdapServPort OBJECT-TYPE
        SYNTAX  Integer32
        MAX-ACCESS  read-create
        STATUS  current
        DESCRIPTION
                "LDAP server port number"
        ::= { exLdapServEntry 8 }

        exLdapServBase OBJECT-TYPE
        SYNTAX  DisplayString
        MAX-ACCESS  read-create
        STATUS  current
        DESCRIPTION
                "LDAP server Base entry.
                An example base entry is dc=example, dc=com"
        ::= { exLdapServEntry 9 }

        exLdapServUniqueId OBJECT-TYPE
        SYNTAX  DisplayString
        MAX-ACCESS  read-create
        STATUS  current
        DESCRIPTION
                "LDAP server Unique Id.
                An example Unique ID attribute is uid."
        ::= { exLdapServEntry 10 }

        exLdapServAccount OBJECT-TYPE
        SYNTAX  DisplayString
        MAX-ACCESS  read-create
        STATUS  current
        DESCRIPTION
                ""
        ::= { exLdapServEntry 11 }

        exLdapServFilters OBJECT-TYPE
        SYNTAX  DisplayString
        MAX-ACCESS  read-create
        STATUS  current
        DESCRIPTION
                "Additional LDAP filters used when looking up 
                 Unique ID attribute. An example is objectClass=Person"
        ::= { exLdapServEntry 12 }

        exLdapServSecret OBJECT-TYPE
        SYNTAX  DisplayString
        MAX-ACCESS  read-create
        STATUS  current
        DESCRIPTION
                "LDAP external server secret base entry"
        ::= { exLdapServEntry 13 }
        
        exLdapServPrecedence OBJECT-TYPE
        SYNTAX  Integer32
        MAX-ACCESS  read-create
        STATUS  current
        DESCRIPTION
                "The precedence this server has for verifying 
                 username/passwords"
        ::= { exLdapServEntry 14 }

        exLdapServNotes OBJECT-TYPE
        SYNTAX  DisplayString
        MAX-ACCESS  read-create
        STATUS  current
        DESCRIPTION
                "Notes"
        ::= { exLdapServEntry 15 }

-- ::= { exLdapServEntry 16 }

        exLdapServSsl OBJECT-TYPE
        SYNTAX  OCTET STRING(SIZE(1))
        MAX-ACCESS  read-create
        STATUS  current
        DESCRIPTION
                ""
        ::= { exLdapServEntry 17 }

        exLdapServSslServer OBJECT-TYPE
        SYNTAX  Integer32
        MAX-ACCESS  read-create
        STATUS  current
        DESCRIPTION
                ""
        ::= { exLdapServEntry 18 }

        exLdapServSslClient OBJECT-TYPE
        SYNTAX  Integer32
        MAX-ACCESS  read-create

        STATUS  current
        DESCRIPTION
                ""
        ::= { exLdapServEntry 19 }

        exLdapServRowStatus OBJECT-TYPE
        SYNTAX  RowStatus 
        MAX-ACCESS  read-create
        STATUS  current
        DESCRIPTION
               "The Row status attribute for row handling"
        ::= { exLdapServEntry 20 }

        exNtlmServTable     OBJECT-TYPE
        SYNTAX   SEQUENCE OF ExNtlmServEntry
        MAX-ACCESS            not-accessible
        STATUS             current
        DESCRIPTION    "A list of NTLM external authentication server  entries."
              ::= { exAuthServer 4 }

        exNtlmServEntry OBJECT-TYPE
        SYNTAX  ExNtlmServEntry
        MAX-ACCESS  not-accessible
        STATUS  current
        DESCRIPTION
                "" 
        INDEX   { exNtlmServId }
            ::= { exNtlmServTable 1 }

        ExNtlmServEntry ::=
              SEQUENCE {
                  exNtlmServId
                      Integer32,
                  exNtlmServState
                      INTEGER,
                  exNtlmServName
                      DisplayString,
                  exNtlmServDefRoleId 
                      Integer32,
                  exNtlmServRdAccState
                      INTEGER,
                  exNtlmServRdAccId
                      Integer32,
                  exNtlmServDomainName
                       DisplayString,
                  exNtlmServMsdc
                       DisplayString,
                  exNtlmServMsrpc
                       DisplayString,
                  exNtlmServMsad
                       Integer32,
                  exNtlmServNotes
                      DisplayString,
                  exNtlmServRowStatus
                      RowStatus

        }
        exNtlmServId OBJECT-TYPE
        SYNTAX  Integer32 (1..2147483647)
        MAX-ACCESS  not-accessible 
        STATUS  current
        DESCRIPTION
                "Unique Id for each entry in this table"
        ::= { exNtlmServEntry 1 }

        exNtlmServState OBJECT-TYPE
        SYNTAX  INTEGER {
                   disable(0),
                   enable(1)
                }
        MAX-ACCESS  read-create
        STATUS  current
        DESCRIPTION
               "To Enable/Disable  an external NTLM server"
        ::= { exNtlmServEntry 2 }

        exNtlmServName OBJECT-TYPE
        SYNTAX  DisplayString
        MAX-ACCESS  read-create
        STATUS  current
        DESCRIPTION
                "A unique external server name"
        ::= { exNtlmServEntry 3 }

        exNtlmServRdAccState OBJECT-TYPE
        SYNTAX  INTEGER {
                   disable(0),
                   enable(1)
                }
        MAX-ACCESS  read-create
        STATUS  current

        DESCRIPTION
               ""
        ::= { exNtlmServEntry 4 }

        exNtlmServRdAccId OBJECT-TYPE
        SYNTAX  Integer32
        MAX-ACCESS  read-create
        STATUS  current
        DESCRIPTION
                "For accounting logging with authentication"
        ::= { exNtlmServEntry 5 }

        exNtlmServDefRoleId OBJECT-TYPE
        SYNTAX  Integer32
        MAX-ACCESS  read-create
        STATUS  current
        DESCRIPTION
                "Default role Id for external server users.
                 Should be an existing exRdAccServId from
                 exRdAccServTable"
        ::= { exNtlmServEntry 6 }

        exNtlmServDomainName OBJECT-TYPE
        SYNTAX  DisplayString
        MAX-ACCESS  read-create
        STATUS  current
        DESCRIPTION
                "Optional NT Domain Name to match"
        ::= { exNtlmServEntry 7 }

        exNtlmServMsdc OBJECT-TYPE
        SYNTAX  DisplayString
        MAX-ACCESS  read-create
        STATUS  current
        DESCRIPTION
                "List of IP addresses of domain controllers "
        ::= { exNtlmServEntry 8 }

        exNtlmServMsrpc OBJECT-TYPE
        SYNTAX  DisplayString
        MAX-ACCESS  read-create
        STATUS  current
        DESCRIPTION
                "List of port range for MSRPC separated by comma"
        ::= { exNtlmServEntry 9 }

        exNtlmServMsad OBJECT-TYPE
        SYNTAX  Integer32
        MAX-ACCESS  read-create
        STATUS  current
        DESCRIPTION
                " "
        ::= { exNtlmServEntry 10 }
        exNtlmServNotes OBJECT-TYPE
        SYNTAX  DisplayString
        MAX-ACCESS  read-create
        STATUS  current
        DESCRIPTION
                "Notes"
        ::= { exNtlmServEntry 11 }

        exNtlmServRowStatus OBJECT-TYPE
        SYNTAX  RowStatus 
        MAX-ACCESS  read-create

        STATUS  current
        DESCRIPTION
               "The Row status attribute for row handling"
        ::= { exNtlmServEntry 12 }

        -- the exUserRule table
        exUserRuleTable     OBJECT-TYPE
        SYNTAX   SEQUENCE OF ExUserRuleEntry
        MAX-ACCESS            not-accessible
        STATUS             current
        DESCRIPTION    "When a user successfully authenticates against 
                        the external server the following rules are checked in 
                        numerical order. If a rule matches then the user 
                        is assigned the role, and no further rule is checked. 
                        If no rules match, the user is assigned the 
                        default role"
              ::= { exAuthServer 5}

        exUserRuleEntry OBJECT-TYPE
        SYNTAX  ExUserRuleEntry
        MAX-ACCESS  not-accessible
        STATUS  current
        DESCRIPTION
             ""
        INDEX   { exServId,exUserRuleId }
        ::= { exUserRuleTable 1 }

        ExUserRuleEntry ::=
              SEQUENCE {
                  exServId
                      Integer32,
                  exUserRuleId
                      Integer32,
                  exUserRuleAttribute
                      OCTET STRING,
                  exUserRuleOperator
                      OCTET STRING,
                  exUserRuleValue
                      OCTET STRING,
                  exUserRuleRoleId
                      Integer32,
                  exUserRuleSeqId
                      Integer32 ,
                  exUserRuleRowStatus
                      RowStatus 
        }

        exServId OBJECT-TYPE
        SYNTAX  Integer32 (1..2147483647)
        MAX-ACCESS  not-accessible
        STATUS  current
        DESCRIPTION
               "First index of this table. This index value should match
               any of external authentication servers table index. 
               Eg: Radius or ldap or ntlm or 802_1x authentication servers"
        ::= { exUserRuleEntry 1 }


        exUserRuleId OBJECT-TYPE
        SYNTAX  Integer32 (1..2147483647)
        MAX-ACCESS  not-accessible
        STATUS  current
        DESCRIPTION
               "index"
        ::= { exUserRuleEntry 2 }


        exUserRuleAttribute OBJECT-TYPE
        SYNTAX  OCTET STRING (SIZE(1..50))
        MAX-ACCESS  read-create
        STATUS  current
        DESCRIPTION
               "The name of attributes that are be used for authentication"
        ::= { exUserRuleEntry 3 }

        exUserRuleOperator OBJECT-TYPE
        SYNTAX  OCTET STRING (SIZE(1..15))
        MAX-ACCESS  read-create
        STATUS  current
        DESCRIPTION
               "The logical operator that works along with the 
                exUserRuleAttribute columnar attribute"
        ::= { exUserRuleEntry 4 }

        exUserRuleValue OBJECT-TYPE
        SYNTAX  OCTET STRING (SIZE(1..50)) 
        MAX-ACCESS  read-create
        STATUS  current
        DESCRIPTION
               "The attribute  value"
        ::= { exUserRuleEntry 5}

        exUserRuleRoleId OBJECT-TYPE
        SYNTAX  Integer32 
        MAX-ACCESS  read-create
        STATUS  current
        DESCRIPTION
               "The role id to be assigned for the given user 
                if the rule matches"
        ::= { exUserRuleEntry 6}

        exUserRuleSeqId OBJECT-TYPE
        SYNTAX  Integer32 
        MAX-ACCESS  read-create
        STATUS  current
        DESCRIPTION
               "The sequence to be followed when the rules are checked for 
                user authentication"
        ::= { exUserRuleEntry 7}

        exUserRuleRowStatus OBJECT-TYPE
        SYNTAX  RowStatus 
        MAX-ACCESS  read-create
        STATUS  current
        DESCRIPTION
               "The Row status attribute for row handling"
        ::= { exUserRuleEntry 8}

        -- radius accounting server group
        
        exRdAccServTable     OBJECT-TYPE
        SYNTAX   SEQUENCE OF ExRdAccServEntry
        MAX-ACCESS            not-accessible
        STATUS             current
        DESCRIPTION    "A table to hold information about external 
                        Raduis Accounting server."
              ::= { exAuthServer 6 }

        exRdAccServEntry OBJECT-TYPE
        SYNTAX  ExRdAccServEntry
        MAX-ACCESS  not-accessible
        STATUS  current
        DESCRIPTION
                "" 
        INDEX   { exRdAccServId }
            ::= { exRdAccServTable 1 }

        ExRdAccServEntry ::=
              SEQUENCE {
                  exRdAccServId
                      Integer32,
                  exRdAccServState
                      INTEGER,
                  exRdAccServName
                      DisplayString,
                  exRdAccServAddr
                       DisplayString,
                  exRdAccServPort
                      Integer32,
                  exRdAccServSecret
                       DisplayString,
                  exRdAccServNotes
                       DisplayString,
                  exRdAccServRowStatus
                       RowStatus 
        }
        exRdAccServId OBJECT-TYPE
        SYNTAX  Integer32 (1..2147483647)
        MAX-ACCESS  not-accessible 
        STATUS  current
        DESCRIPTION
                "Unique Id for each entry in this table"
        ::= { exRdAccServEntry 1 }

        exRdAccServState OBJECT-TYPE
        SYNTAX  INTEGER {
                   disable(0),
                   enable(1)
                }
        MAX-ACCESS  read-create
        STATUS  current
        DESCRIPTION
               "To Enable/Disable  this external radius accounting server"
        ::= { exRdAccServEntry 2 }

        exRdAccServName OBJECT-TYPE
        SYNTAX  DisplayString
        MAX-ACCESS  read-create
        STATUS  current
        DESCRIPTION
                "A unique external radius accounting server name"
        ::= { exRdAccServEntry 3 }


        exRdAccServAddr OBJECT-TYPE
        SYNTAX  DisplayString
        MAX-ACCESS  read-create
        STATUS  current
        DESCRIPTION
                "RADIUS accounting server Ip address or DNS name"
        ::= { exRdAccServEntry 4 }

        exRdAccServPort OBJECT-TYPE
        SYNTAX  Integer32
        MAX-ACCESS  read-create
        STATUS  current
        DESCRIPTION
                "RADIUS server port number"
        ::= { exRdAccServEntry 5 }

        exRdAccServSecret OBJECT-TYPE
        SYNTAX  DisplayString
        MAX-ACCESS  read-create
        STATUS  current
        DESCRIPTION
                "Shared secret"
        ::= { exRdAccServEntry 6 }

        exRdAccServNotes OBJECT-TYPE
        SYNTAX  DisplayString
        MAX-ACCESS  read-create
        STATUS  current
        DESCRIPTION
                "Notes"
        ::= { exRdAccServEntry 7 }

        exRdAccServRowStatus OBJECT-TYPE
        SYNTAX  RowStatus 
        MAX-ACCESS  read-create
        STATUS  current
        DESCRIPTION
             "The Row status attribute for row handling"
      ::= { exRdAccServEntry 8 }

        -- 8021x authentication server accounting server group
        
        ex802AuthServTable     OBJECT-TYPE
        SYNTAX   SEQUENCE OF Ex802AuthServEntry
        MAX-ACCESS            not-accessible
        STATUS             current
        DESCRIPTION    "A table to hold information about external 
                        802_1x auth  server."
              ::= { exAuthServer 7 }

        ex802AuthServEntry OBJECT-TYPE
        SYNTAX  Ex802AuthServEntry
        MAX-ACCESS  not-accessible
        STATUS  current
        DESCRIPTION
                "" 
        INDEX   { ex802AuthServId }
            ::= { ex802AuthServTable 1 }

        Ex802AuthServEntry ::=
              SEQUENCE {
                  ex802AuthServId
                      Integer32,
                  ex802AuthServState
                      INTEGER,
                  ex802AuthServName
                      DisplayString,
                  ex802AuthServAddr
                       DisplayString,
                  ex802AuthServPort
                      Integer32,
                  ex802AuthServDefaultRole
                       Integer32,
                  ex802AuthServNotes
                       DisplayString,
                  ex802AuthServRowStatus
                       RowStatus 
        }
        ex802AuthServId OBJECT-TYPE
        SYNTAX  Integer32 (1..2147483647)
        MAX-ACCESS  not-accessible 
        STATUS  current
        DESCRIPTION
                "Unique Id for each entry in this table"
        ::= { ex802AuthServEntry 1 }

        ex802AuthServState OBJECT-TYPE
        SYNTAX  INTEGER {
                   disable(0),
                   enable(1)
                }
        MAX-ACCESS  read-create
        STATUS  current
        DESCRIPTION
               "To Enable/Disable an external server"
        ::= { ex802AuthServEntry 2 }

        ex802AuthServName OBJECT-TYPE
        SYNTAX  DisplayString
        MAX-ACCESS  read-create
        STATUS  current
        DESCRIPTION
                "A unique external server name"
        ::= { ex802AuthServEntry 3 }


        ex802AuthServAddr OBJECT-TYPE
        SYNTAX  DisplayString
        MAX-ACCESS  read-create
        STATUS  current
        DESCRIPTION
                "802_1x server Ip address or DNS name"
        ::= { ex802AuthServEntry 4 }

        ex802AuthServPort OBJECT-TYPE
        SYNTAX  Integer32
        MAX-ACCESS  read-create
        STATUS  current

        DESCRIPTION
                "802_1x server port number"
        ::= { ex802AuthServEntry 5 }

        ex802AuthServDefaultRole OBJECT-TYPE
        SYNTAX  Integer32
        MAX-ACCESS  read-create
        STATUS  current
        DESCRIPTION

                "Default role Id"
        ::= { ex802AuthServEntry 6 }

        ex802AuthServNotes OBJECT-TYPE
        SYNTAX  DisplayString
        MAX-ACCESS  read-create
        STATUS  current
        DESCRIPTION
                "Notes"
        ::= { ex802AuthServEntry 7 }

        ex802AuthServRowStatus OBJECT-TYPE
        SYNTAX  RowStatus 
        MAX-ACCESS  read-create
        STATUS  current
        DESCRIPTION
               "The Row status attribute for row handling"
        ::= { ex802AuthServEntry 8 }

        -- 802_1x authentication server accounting server group
        
        macDevAuthTable     OBJECT-TYPE
        SYNTAX   SEQUENCE OF MacDevAuthEntry
        MAX-ACCESS            not-accessible
        STATUS             current
        DESCRIPTION    "A table to hold information about external 
                        mac device auth server."
              ::= { authentication 2 }

        macDevAuthEntry OBJECT-TYPE
        SYNTAX  MacDevAuthEntry
        MAX-ACCESS  not-accessible
        STATUS  current
        DESCRIPTION
                "" 
        INDEX   { macDevAuthId }
            ::= { macDevAuthTable 1 }

        MacDevAuthEntry ::=
              SEQUENCE {
                  macDevAuthId
                      Integer32,
                  macDevAuthState
                      INTEGER,
                  macDevAuthName
                      DisplayString,
                  macDevAuthMac
                       DisplayString,
                  macDevAuthDefaultRole
                       Integer32,
                  macDevAuthNotes
                       DisplayString,
                  macDevAuthRowStatus
                       RowStatus 
        }
        macDevAuthId OBJECT-TYPE
        SYNTAX  Integer32 (1..2147483647)
        MAX-ACCESS  not-accessible 
        STATUS  current
        DESCRIPTION
                "Unique Id for each entry in this table"
        ::= { macDevAuthEntry 1 }

        macDevAuthState OBJECT-TYPE
        SYNTAX  INTEGER {
                   disable(0),
                   enable(1)
                }
        MAX-ACCESS  read-create
        STATUS  current
        DESCRIPTION
               "To Enable/Disable  an external mac device auth server"
        ::= { macDevAuthEntry 2 }

        macDevAuthName OBJECT-TYPE
        SYNTAX  DisplayString
        MAX-ACCESS  read-create
        STATUS  current
        DESCRIPTION
                "A unique name"
        ::= { macDevAuthEntry 3 }


        macDevAuthMac OBJECT-TYPE
        SYNTAX  DisplayString
        MAX-ACCESS  read-create
        STATUS  current
        DESCRIPTION
                "Mac address of the host machine to be authenticated"
        ::= { macDevAuthEntry 4 }

        macDevAuthDefaultRole OBJECT-TYPE
        SYNTAX  Integer32
        MAX-ACCESS  read-create
        STATUS  current
        DESCRIPTION
                "Default role Id"
        ::= { macDevAuthEntry 5 }

        macDevAuthNotes OBJECT-TYPE
        SYNTAX  DisplayString
        MAX-ACCESS  read-create
        STATUS  current
        DESCRIPTION
                "Notes"
        ::= { macDevAuthEntry 6 }

        macDevAuthRowStatus OBJECT-TYPE
        SYNTAX  RowStatus 
        MAX-ACCESS  read-create
        STATUS  current
        DESCRIPTION
               "The Row status attribute for row handling"
        ::= { macDevAuthEntry 7 }

        -- the destination  Group
        -- Contains the information about the host

        -- the host table
        hostTable     OBJECT-TYPE
        SYNTAX   SEQUENCE OF HostEntry
        MAX-ACCESS            not-accessible
        STATUS             current
        DESCRIPTION    
              "To define the destinations that wireless users can 
               potentially access. Adestination can be a single 
               device within a netwokr and/or all the devices reachable 
               within address space"

              ::= { destination 1 }

        hostEntry OBJECT-TYPE
        SYNTAX  HostEntry
        MAX-ACCESS  not-accessible
        STATUS  current
        DESCRIPTION
             ""
        INDEX   { hostId }
        ::= { hostTable 1 }

        HostEntry ::=
              SEQUENCE {
                  hostId
                      Integer32,
                  hostName
                      OCTET STRING,
                  hostAddress
                      BlueIpAddress,
                  hostNetmask
                      BlueIpAddress,
                  hostInvertDest
                      OCTET STRING,
                  hostType
                      OCTET STRING,
                  hostNotes
                       DisplayString,
                  hostRowStatus
                       RowStatus 
        }

        hostId OBJECT-TYPE
        SYNTAX  Integer32(1..2147483647)
        MAX-ACCESS  not-accessible
        STATUS  current
        DESCRIPTION
               "Table index"
        ::= { hostEntry 1 }


        hostName OBJECT-TYPE
        SYNTAX  OCTET STRING(SIZE(1..50))
        MAX-ACCESS  read-create
        STATUS  current
        DESCRIPTION
               "Unique name for every host or network"
        ::= { hostEntry 2 }

        hostAddress OBJECT-TYPE
        SYNTAX  BlueIpAddress
        MAX-ACCESS  read-create
        STATUS  current
        DESCRIPTION
               "IP or FQDN (Fully Qualified Domain Name)"
        ::= { hostEntry 3 }

        hostNetmask OBJECT-TYPE
        SYNTAX  BlueIpAddress
        MAX-ACCESS  read-create
        STATUS  current
        DESCRIPTION
               "Netmask for network entries. 
               To be set to 255.255.255.255 if hostType is set to 'H'"
        ::= { hostEntry 4 }


        hostInvertDest OBJECT-TYPE
        SYNTAX  OCTET STRING (SIZE(1))
        MAX-ACCESS  read-create
        STATUS  current
        DESCRIPTION
               "
                'N' Invert option is not selected (No)
                'Y' Invert option is selected (Yes)"
        ::= { hostEntry 5 }

        hostType OBJECT-TYPE
        SYNTAX  OCTET STRING (SIZE(1))
        MAX-ACCESS  read-create
        STATUS  current
        DESCRIPTION
               "The entry can be either a end host or a sub network.
                In case of host, the hostNetmask column is set to 
                a default value of 255.255.255.255
                'H' - Host  
                'N' - Network
                "
        ::= { hostEntry 6 }

        hostNotes OBJECT-TYPE
        SYNTAX  DisplayString
        MAX-ACCESS  read-create
        STATUS  current
        DESCRIPTION
               "Notes"
        ::= { hostEntry 7 }

        hostRowStatus OBJECT-TYPE
        SYNTAX  RowStatus 
        MAX-ACCESS  read-create
        STATUS  current
        DESCRIPTION
               "The Row status attribute for row handling"
        ::= { hostEntry 8 }

        -- the host Group table
        hostGrpTable     OBJECT-TYPE
        SYNTAX   SEQUENCE OF HostGrpEntry
        MAX-ACCESS            not-accessible
        STATUS             current
        DESCRIPTION    
              "To define the destination Group."
              ::= { destination 2 }

        hostGrpEntry OBJECT-TYPE
        SYNTAX  HostGrpEntry
        MAX-ACCESS  not-accessible
        STATUS  current
        DESCRIPTION
             ""
        INDEX   { hostGrpId }
        ::= { hostGrpTable 1 }

        HostGrpEntry ::=
              SEQUENCE {
                  hostGrpId
                      Integer32,
                  hostGrpName
                      OCTET STRING,
                  hostGrpRowStatus
                       RowStatus 
        }

        hostGrpId OBJECT-TYPE
        SYNTAX  Integer32(1..2147483647)
        MAX-ACCESS  not-accessible
        STATUS  current
        DESCRIPTION
               "Table index."
        ::= { hostGrpEntry 1 }


        hostGrpName OBJECT-TYPE
        SYNTAX  OCTET STRING(SIZE(1..50))
        MAX-ACCESS  read-create
        STATUS  current
        DESCRIPTION
               "Unique name for every host Grp"
        ::= { hostGrpEntry 2 }

        hostGrpRowStatus OBJECT-TYPE
        SYNTAX  RowStatus 
        MAX-ACCESS  read-create
        STATUS  current
        DESCRIPTION
               "The Row status attribute for row handling"
        ::= { hostGrpEntry 3 }

        -- the host group member table

        hostGrpMemTable OBJECT-TYPE
        SYNTAX          SEQUENCE OF HostGrpMemEntry
        MAX-ACCESS          not-accessible
        STATUS          current
        DESCRIPTION    
              "To define the destinations group members."
              ::= { destination 3 }

        hostGrpMemEntry OBJECT-TYPE
        SYNTAX          HostGrpMemEntry
        MAX-ACCESS          not-accessible
        STATUS          current
        DESCRIPTION
             ""
        INDEX   { hostGrpId,hostGrpMemId}
        ::= { hostGrpMemTable 1 }

        HostGrpMemEntry ::=
              SEQUENCE {
                  hostGrpMemId
                      Integer32,
                  hostGrpMemRowStatus
                       RowStatus 
        }

        hostGrpMemId OBJECT-TYPE
        SYNTAX  Integer32(1..2147483647)
        MAX-ACCESS  not-accessible
        STATUS  current
        DESCRIPTION
               "Second index of the Table"
        ::= { hostGrpMemEntry 1 }

        hostGrpMemRowStatus OBJECT-TYPE
        SYNTAX  RowStatus 
        MAX-ACCESS  read-create
        STATUS  current
        DESCRIPTION
               "The Row status attribute for row handling"
        ::= { hostGrpMemEntry 2 }

        -- the service  Group
        -- Contains the information about the service

        -- the service table
        serviceTable     OBJECT-TYPE
        SYNTAX   SEQUENCE OF ServiceEntry
        MAX-ACCESS            not-accessible
        STATUS             current
        DESCRIPTION    "A list of service entries."
              ::= { service 1 }

        serviceEntry OBJECT-TYPE
        SYNTAX  ServiceEntry
        MAX-ACCESS  not-accessible
        STATUS  current
        DESCRIPTION
             "List of services"
        INDEX   { serviceId }
        ::= { serviceTable 1 }

        ServiceEntry ::=
              SEQUENCE {
                  serviceId
                      Integer32,
                  serviceName
                      OCTET STRING,
                  servicePort
                      Integer32,
                  serviceProtocol
                      OCTET STRING,
                  serviceCosPriorityIn
                      Integer32,
                  serviceCosPriorityOut
                      Integer32,
                  serviceCosDscpIn
                      Integer32,
                  serviceCosDscpOut
                      Integer32,
                  serviceNotes
                      DisplayString,
                  serviceRowStatus
                      RowStatus 
        }

        serviceId OBJECT-TYPE
        SYNTAX  Integer32 (1..2147483647)
        MAX-ACCESS  not-accessible
        STATUS  current
        DESCRIPTION
               "Index"
        ::= { serviceEntry 1 }

        serviceName OBJECT-TYPE
        SYNTAX  OCTET STRING (SIZE(1..50)) 
        MAX-ACCESS  read-create
        STATUS  current
        DESCRIPTION
               "Unique name for this service"
        ::= { serviceEntry 2 }

        servicePort OBJECT-TYPE
        SYNTAX  Integer32 
        MAX-ACCESS  read-create
        STATUS  current
        DESCRIPTION
               ""
        ::= { serviceEntry 3 }

        serviceProtocol OBJECT-TYPE

        SYNTAX  OCTET STRING (SIZE(1..10 )) 
        MAX-ACCESS  read-create
        STATUS  current
        DESCRIPTION
               "The port associated with this service"
        ::= { serviceEntry 4 }

--        ::= { serviceEntry 5 }
--        ::= { serviceEntry 6 }

        serviceCosPriorityIn OBJECT-TYPE
        SYNTAX  Integer32
        MAX-ACCESS  read-create
        STATUS  current
        DESCRIPTION
                "Incoming priority"
        ::= { serviceEntry 7 }

        serviceCosPriorityOut OBJECT-TYPE
        SYNTAX  Integer32
        MAX-ACCESS  read-create
        STATUS  current
        DESCRIPTION
                "Out going priority"
        ::= { serviceEntry 8 }

        serviceCosDscpIn OBJECT-TYPE
        SYNTAX  Integer32
        MAX-ACCESS  read-create
        STATUS  current
        DESCRIPTION
                "Incoming DSCP value"
        ::= { serviceEntry 9 }

        serviceCosDscpOut OBJECT-TYPE
        SYNTAX  Integer32
        MAX-ACCESS  read-create
        STATUS  current
        DESCRIPTION
                "Out going DSCP value"
        ::= { serviceEntry 10 }

        serviceNotes OBJECT-TYPE
        SYNTAX  DisplayString 
        MAX-ACCESS  read-create
        STATUS  current
        DESCRIPTION
               "User notes"
        ::= { serviceEntry 11 }

        serviceRowStatus OBJECT-TYPE
        SYNTAX  RowStatus 
        MAX-ACCESS  read-create
        STATUS  current
        DESCRIPTION
               "The Row status attribute for row handling"
        ::= { serviceEntry 12 }
      
        -- the service group table

        serviceGrpTable OBJECT-TYPE
        SYNTAX          SEQUENCE OF ServiceGrpEntry
        MAX-ACCESS          not-accessible
        STATUS          current
        DESCRIPTION    
              "To define the sevice groups."
              ::= { service 2 }

        serviceGrpEntry OBJECT-TYPE
        SYNTAX          ServiceGrpEntry
        MAX-ACCESS          not-accessible
        STATUS          current
        DESCRIPTION
             ""
        INDEX   { serviceGrpId }
        ::= { serviceGrpTable 1 }

        ServiceGrpEntry ::=
              SEQUENCE {
                  serviceGrpId
                      Integer32,
                  serviceGrpName
                      OCTET STRING,
                  serviceGrpRowStatus
                       RowStatus 
        }

        serviceGrpId OBJECT-TYPE
        SYNTAX  Integer32(1..2147483647)
        MAX-ACCESS  not-accessible
        STATUS  current
        DESCRIPTION
               "Table index"
        ::= { serviceGrpEntry 1 }


        serviceGrpName OBJECT-TYPE
        SYNTAX  OCTET STRING(SIZE(1..50))
        MAX-ACCESS  read-create
        STATUS  current
        DESCRIPTION
               "Unique name for every service group"
        ::= { serviceGrpEntry 2 }

        serviceGrpRowStatus OBJECT-TYPE
        SYNTAX  RowStatus 
        MAX-ACCESS  read-create
        STATUS  current
        DESCRIPTION
               "The Row status attribute for row handling"
        ::= { serviceGrpEntry 3 }

        -- the service group member table

        serviceGrpMemTable OBJECT-TYPE
        SYNTAX          SEQUENCE OF ServiceGrpMemEntry
        MAX-ACCESS          not-accessible
        STATUS          current
        DESCRIPTION    
              "To define the service group members."
              ::= { service 3 }


        serviceGrpMemEntry OBJECT-TYPE
        SYNTAX          ServiceGrpMemEntry
        MAX-ACCESS          not-accessible
        STATUS          current
        DESCRIPTION
             ""
        INDEX   { serviceGrpId,serviceGrpMemId}
        ::= { serviceGrpMemTable 1 }

        ServiceGrpMemEntry ::=
              SEQUENCE {
                  serviceGrpMemId
                      Integer32,
                  serviceGrpMemRowStatus
                       RowStatus 
        }

        serviceGrpMemId OBJECT-TYPE
        SYNTAX  Integer32(1..2147483647)
        MAX-ACCESS  not-accessible
        STATUS  current
        DESCRIPTION
               "Table index"
        ::= { serviceGrpMemEntry 1 }

        serviceGrpMemRowStatus OBJECT-TYPE
        SYNTAX  RowStatus 
        MAX-ACCESS  read-create
        STATUS  current
        DESCRIPTION
               "The Row status attribute for row handling"
        ::= { serviceGrpMemEntry 2 }

        -- the policy Group
        -- Contains the information about the policy

        -- the policy table
        policyTable     OBJECT-TYPE
        SYNTAX   SEQUENCE OF PolicyEntry
        MAX-ACCESS            not-accessible
        STATUS             current
        DESCRIPTION    
              "Network traffic is checked against the following 
               policies. If the service, direction, and destination 
               match, the action is taken and checking ends. If no 
               policy matches the policies in any inherited role(s) 
               are checked, finally the traffic is denied if nothing 
               matches"
              ::= { policy 1 }

        policyEntry OBJECT-TYPE
        SYNTAX  PolicyEntry
        MAX-ACCESS  not-accessible
        STATUS  current
        DESCRIPTION
             ""
        INDEX   {roleId,policyId}
        ::= { policyTable 1 }

        PolicyEntry ::=
              SEQUENCE {
                  policyId
                      Integer32,
                  policyServiceId
                      Integer32,
                  policyHostId
                      Integer32,
                  policyAction
                      OCTET STRING,
                  policyDirection
                      OCTET STRING,
                  policySeqId
                      Integer32,
                  policyVlanId
                      Integer32,
                  policyScheduleId
                      Integer32,
                  policyRowStatus
                      RowStatus 
        }

        policyId  OBJECT-TYPE
        SYNTAX  Integer32(1..2147483647)
        MAX-ACCESS  not-accessible
        STATUS  current
        DESCRIPTION
               "Index of this table"
        ::= { policyEntry 1 }

        policyServiceId OBJECT-TYPE
        SYNTAX  Integer32
        MAX-ACCESS  read-create
        STATUS  current
        DESCRIPTION
               "ServiceTable Index associated with this policy. 
                Row creation or set on this object fails on invalid service id"
        ::= { policyEntry 2 }

        policyHostId OBJECT-TYPE
        SYNTAX  Integer32
        MAX-ACCESS  read-create
        STATUS  current
        DESCRIPTION
               "Host table Index associated with this policy.
                Row creation or set on this object fails on invalid host id"
        ::= { policyEntry 3 }

        policyAction OBJECT-TYPE
        SYNTAX  OCTET STRING (SIZE(1))
        MAX-ACCESS  read-create
        STATUS  current
        DESCRIPTION
               "To allow or to deny the traffic. 
                'P' - allow
                'D' - deny."
        ::= { policyEntry 4 }

        policyDirection OBJECT-TYPE
        SYNTAX  OCTET STRING (SIZE(1))

        MAX-ACCESS  read-create
        STATUS  current
        DESCRIPTION
               "To decide the direction of the traffic. 
               'I' - incoming
               'O' - Out going 
               'B' - Both ways"
        ::= { policyEntry 5 }

        policySeqId OBJECT-TYPE
        SYNTAX  Integer32
        MAX-ACCESS  read-create
        STATUS  current
        DESCRIPTION
               "squence id"
        ::= { policyEntry 6 }

--      ::= { policyEntry 7 }

        policyVlanId OBJECT-TYPE
        SYNTAX  Integer32

        MAX-ACCESS  read-create
        STATUS  current
        DESCRIPTION
               "vlan  id"
        ::= { policyEntry 8 }

        policyScheduleId OBJECT-TYPE
        SYNTAX  Integer32
        MAX-ACCESS  read-create
        STATUS  current
        DESCRIPTION
               "schedule id"
        ::= { policyEntry 9 }

        policyRowStatus OBJECT-TYPE
        SYNTAX  RowStatus 
        MAX-ACCESS  read-create
        STATUS  current
        DESCRIPTION
               "The Row status attribute for row handling"
        ::= { policyEntry 10 }


        -- the vpn  Group
        -- Contains the information about the setting

        -- the ipsecMethod  Group
        -- Contains the information about the ipsecMethod

        -- the ipsec Group
        exchangeMode   OBJECT-TYPE
        SYNTAX   INTEGER {
                    aggressive(1),
                    main      (2)
                 }
        MAX-ACCESS   read-write 
        STATUS   current
        DESCRIPTION    "IKE Settings Exchange mode."
              ::= { ipsec 1 }

        authenticationMethod   OBJECT-TYPE
        SYNTAX   INTEGER {
                    certificates(1),
                    sharedKeys(2)
                 }
        MAX-ACCESS   read-write 
        STATUS   current
        DESCRIPTION    "IKE Settings Authentication Method."
              ::= { ipsec 2 }

        idleTimeout   OBJECT-TYPE
        SYNTAX   Integer32 
        MAX-ACCESS   read-write 
        STATUS   current
        DESCRIPTION    "IKE Settings idle timeout in seconds"
              ::= { ipsec 3 }

        maxLifeTimeInSecs  OBJECT-TYPE
        SYNTAX   Integer32 
        MAX-ACCESS   read-write 
        STATUS   current
        DESCRIPTION    "IKE Settings maximun time out in seconds"
              ::= { ipsec 4 }

        maxLifeTimeInKbs  OBJECT-TYPE
        SYNTAX   Integer32 
        MAX-ACCESS   read-write 
        STATUS   current
        DESCRIPTION    "IKE Settings maximun time out in Kilogytes"
              ::= { ipsec 5 }


        refreshThresholdInSecs  OBJECT-TYPE
        SYNTAX   Integer32 
        MAX-ACCESS   read-write 
        STATUS   current
        DESCRIPTION    "IKE Settings refresh threshold in seconds"
              ::= { ipsec 6 }

        refreshThresholdInKbs  OBJECT-TYPE
        SYNTAX   Integer32 
        MAX-ACCESS   read-write 
        STATUS   current
        DESCRIPTION    "IKE Settings refresh threshold in kilobytes"
              ::= { ipsec 7 }

        minLifeTimeInSecs  OBJECT-TYPE
        SYNTAX   Integer32 
        MAX-ACCESS   read-write 
        STATUS   current
        DESCRIPTION    "IKE Settings maximun time out in seconds"
              ::= { ipsec 8 }

        minLifeTimeInKbs  OBJECT-TYPE
        SYNTAX   Integer32 
        MAX-ACCESS   read-write 
        STATUS   current
        DESCRIPTION    "IKE Settings maximun time out in seconds"
              ::= { ipsec 9 }

        exModeAggressive OBJECT-TYPE
        SYNTAX  INTEGER {
                   disable(0),
                   enable(1)
                }
        MAX-ACCESS  read-write
        STATUS  current
        DESCRIPTION
               "IKE Settings : Exchange mode - main"
        ::= { ipsec 10 }


        exModeMain OBJECT-TYPE
        SYNTAX  INTEGER {
                   disable(0),
                   enable(1)
                }
        MAX-ACCESS  read-write
        STATUS  current
        DESCRIPTION
               "IKE Settings : Exchange mode - Aggressive"
        ::= { ipsec 11 }

        authMethodCertificates OBJECT-TYPE
        SYNTAX  INTEGER {
                   disable(0),
                   enable(1)
                }
        MAX-ACCESS  read-write
        STATUS  current
        DESCRIPTION
               "authentication method - certificates"
        ::= { ipsec 12 }

        authMethodPreSharedKeys OBJECT-TYPE
        SYNTAX  INTEGER {
                   disable(0),
                   enable(1)
                }
        MAX-ACCESS  read-write
        STATUS  current
        DESCRIPTION
               "authentication method - pre-shared keys"
        ::= { ipsec 13 }

        ipsecConfTable     OBJECT-TYPE
        SYNTAX   SEQUENCE OF IpsecConfEntry
        MAX-ACCESS            not-accessible
        STATUS             current
        DESCRIPTION    "A list of ipsec configuration entries."
              ::= { ipsec 14 }

        ipsecConfEntry OBJECT-TYPE
        SYNTAX  IpsecConfEntry
        MAX-ACCESS  not-accessible
        STATUS  current
        DESCRIPTION
             "ipsec configuration"
        INDEX   { ipsecConfId }
        ::= { ipsecConfTable 1 }

        IpsecConfEntry ::=
              SEQUENCE {
                  ipsecConfId
                      Integer32,
                 ipsecConfEnableConfiguration
                      INTEGER,
                 ipsecConfName
                      DisplayString,
                 ipsecConfLocalAuth
                      INTEGER,
                  ipsecConfEspTripleDESWithMD5 
                      INTEGER,
                  ipsecConfEspTripleDESWithSHA1 
                      INTEGER,
                  ipsecConfEsp56BitDESWithMD5 
                      INTEGER,
                  ipsecConfEsp56BitDESWithSHA1 
                      INTEGER,
                  ipsecConfEsp128BitAESWithMD5 
                      INTEGER,
                  ipsecConfEsp128BitAESWithSHA1 
                      INTEGER,
                  ipsecConfEsp192BitAESWithMD5 
                      INTEGER,
                  ipsecConfEsp192BitAESWithSHA1 
                      INTEGER,
                  ipsecConfEsp256BitAESWithMD5 
                      INTEGER,
                  ipsecConfEsp256BitAESWithSHA1 
                      INTEGER,
                  ipsecConfDiffieHellmanGrp1 
                      INTEGER,
                  ipsecConfDiffieHellmanGrp2 
                      INTEGER,
                  ipsecConfDiffieHellmanGrp5 
                      INTEGER,
                  ipsecConfPsfMode 
                      INTEGER,
                  ipsecConfCompressionDeflate 
                      INTEGER,
                  ipsecConfCompressionLZS 
                      INTEGER,
                  ipsecConfRowStatus 
                      RowStatus 
                  
        }

        ipsecConfId OBJECT-TYPE
        SYNTAX  Integer32(1..2147483647)
        MAX-ACCESS  not-accessible
        STATUS  current
        DESCRIPTION
               ""
        ::= { ipsecConfEntry 1 }

        ipsecConfEnableConfiguration OBJECT-TYPE
        SYNTAX  INTEGER { 
                   no(0),
                   yes(1)
                }
        MAX-ACCESS  read-create
        STATUS  current
        DESCRIPTION
               "Local authentication: User Name and password/Pre-shared Key"
        ::= { ipsecConfEntry 2 }

        ipsecConfName OBJECT-TYPE
        SYNTAX  DisplayString
        MAX-ACCESS  read-create
        STATUS  current
        DESCRIPTION
               ""
        ::= { ipsecConfEntry 3 }


        ipsecConfLocalAuth OBJECT-TYPE
        SYNTAX  INTEGER { 
                   disable(0),
                   enable(1)
                }
        MAX-ACCESS  read-create
        STATUS  current
        DESCRIPTION
               "Local authentication: User Name and password/Pre-shared Key"
        ::= { ipsecConfEntry 4 }

        ipsecConfEspTripleDESWithSHA1 OBJECT-TYPE
        SYNTAX  INTEGER { 
                   disable(0),
                   enable(1)
                }
        MAX-ACCESS  read-create 
        STATUS  current
        DESCRIPTION
               "Encryption: ESP - Triple DES with SHA1 Integrity"
        ::= { ipsecConfEntry 5 }


        ipsecConfEspTripleDESWithMD5 OBJECT-TYPE
        SYNTAX  INTEGER { 
                   disable(0),
                   enable(1)
                }
        MAX-ACCESS  read-create
        STATUS  current
        DESCRIPTION
               "Encryption: ESP - Triple DES with MD5 Integrity"
        ::= { ipsecConfEntry 6 }


        ipsecConfEsp56BitDESWithMD5 OBJECT-TYPE
        SYNTAX  INTEGER { 
                   disable(0),
                   enable(1)
                }
        MAX-ACCESS  read-create 
        STATUS  current
        DESCRIPTION
               "Encryption: ESP - 56 Bit DES with MD5 Integrity"
        ::= { ipsecConfEntry 7 }

        ipsecConfEsp56BitDESWithSHA1 OBJECT-TYPE
        SYNTAX  INTEGER { 
                   disable(0),
                   enable(1)
                }
        MAX-ACCESS  read-create 
        STATUS  current
        DESCRIPTION
               "Encryption: ESP - 56-bit DES with SHA1 Integrity"
        ::= { ipsecConfEntry 8 }


        ipsecConfEsp128BitAESWithMD5 OBJECT-TYPE
        SYNTAX  INTEGER { 
                   disable(0),
                   enable(1)
                }
        MAX-ACCESS  read-create
        STATUS  current
        DESCRIPTION
               "Encryption: ESP - 128-bit AES with MD5 Integrity"
        ::= { ipsecConfEntry 9 }


        ipsecConfEsp128BitAESWithSHA1 OBJECT-TYPE
        SYNTAX  INTEGER { 
                   disable(0),
                   enable(1)
                }
        MAX-ACCESS  read-create
        STATUS  current
        DESCRIPTION
               "Encryption: ESP - 128-bit AES with SHA1 Integrity"
        ::= { ipsecConfEntry 10 }


        ipsecConfEsp192BitAESWithMD5 OBJECT-TYPE
        SYNTAX  INTEGER { 
                   disable(0),
                   enable(1)

                }
        MAX-ACCESS  read-create
        STATUS  current
        DESCRIPTION
               "Encryption: ESP - 192-bit AES with MD5 Integrity"
        ::= { ipsecConfEntry 11 }


        ipsecConfEsp192BitAESWithSHA1 OBJECT-TYPE
        SYNTAX  INTEGER { 
                   disable(0),
                   enable(1)

                }
        MAX-ACCESS  read-create
        STATUS  current
        DESCRIPTION
               "Encryption: ESP - 192-bit AES with SHA1 Integrity"
        ::= { ipsecConfEntry 12 }

        ipsecConfEsp256BitAESWithMD5 OBJECT-TYPE
        SYNTAX  INTEGER { 
                   disable(0),
                   enable(1)
                }
        MAX-ACCESS  read-create
        STATUS  current
        DESCRIPTION
               "Encryption: ESP - 256-bit AES with MD5 Integrity"
        ::= { ipsecConfEntry 13 }

        ipsecConfEsp256BitAESWithSHA1 OBJECT-TYPE
        SYNTAX  INTEGER { 
                   disable(0),
                   enable(1)
                }
        MAX-ACCESS  read-create
        STATUS  current
        DESCRIPTION
               "Encryption: ESP - 256-bit AES with MD5 Integrity"
        ::= { ipsecConfEntry 14 }

        ipsecConfDiffieHellmanGrp1 OBJECT-TYPE
        SYNTAX  INTEGER { 
                   disable(0),
                   enable(1)
                }
        MAX-ACCESS  read-create
        STATUS  current
        DESCRIPTION
               "IKE Encryption: Diffie-Hellman Group 1"
        ::= { ipsecConfEntry 15 }


        ipsecConfDiffieHellmanGrp2 OBJECT-TYPE
        SYNTAX  INTEGER { 
                   disable(0),
                   enable(1)
                }
        MAX-ACCESS  read-create 
        STATUS  current
        DESCRIPTION
               "IKE Encryption: Diffie-Hellman Group 2"
        ::= { ipsecConfEntry 16 }


        ipsecConfDiffieHellmanGrp5 OBJECT-TYPE
        SYNTAX  INTEGER { 
                   disable(0),
                   enable(1)
                }

        MAX-ACCESS  read-create 
        STATUS  current
        DESCRIPTION
               "IKE Encryption: Diffie-Hellman Group 5"
        ::= { ipsecConfEntry 17 }

        ipsecConfPsfMode OBJECT-TYPE
        SYNTAX  INTEGER { 
                   disable(0),
                   enable(1)
                }
        MAX-ACCESS  read-create 
        STATUS  current
        DESCRIPTION
               "Perfect Forward Secrecy Mode"

        ::= { ipsecConfEntry 18 }

        ipsecConfCompressionDeflate OBJECT-TYPE
        SYNTAX  INTEGER { 
                   disable(0),
                   enable(1)
                }
        MAX-ACCESS  read-create
        STATUS  current
        DESCRIPTION
               "compression: Delfate"
        ::= { ipsecConfEntry 19 }

        ipsecConfCompressionLZS OBJECT-TYPE
        SYNTAX  INTEGER { 
                   disable(0),
                   enable(1)
                }
        MAX-ACCESS  read-create 
        STATUS  current
        DESCRIPTION
               "Compression: LZS"
        ::= { ipsecConfEntry 20 }
  
        ipsecConfRowStatus OBJECT-TYPE
        SYNTAX  RowStatus 
        MAX-ACCESS  read-create
        STATUS  current
        DESCRIPTION
               "The Row status attribute for row handling"
        ::= { ipsecConfEntry 21 }

        -- pptp group 

        pptpEnable OBJECT-TYPE
        SYNTAX  INTEGER {
                   no(0),
                   yes(1)
                } 
        MAX-ACCESS  read-write 
        STATUS  current
        DESCRIPTION
               ""
        ::= { pptp 1 }

        pptpRemoteIpStartAddr OBJECT-TYPE
        SYNTAX  BlueIpAddress
        MAX-ACCESS  read-write
        STATUS  current
        DESCRIPTION
               ""
        ::= { pptp 2 }

        pptpRemoteIpEndAddr OBJECT-TYPE
        SYNTAX  BlueIpAddress
        MAX-ACCESS  read-write
        STATUS  current
        DESCRIPTION
               ""
        ::= { pptp 3 }


        pptpLocalIpAddr OBJECT-TYPE
        SYNTAX  BlueIpAddress
        MAX-ACCESS  read-write
        STATUS  current
        DESCRIPTION
               ""
        ::= { pptp 4 }

        pptpEncryption40Bit OBJECT-TYPE
        SYNTAX  INTEGER{
                   disable(0),
                   enable(1)
                }
        MAX-ACCESS  read-write
        STATUS  current
        DESCRIPTION
               "Enable 40-bit encryption"
        ::= { pptp 5 }

        pptpEncryption128Bit OBJECT-TYPE
        SYNTAX  INTEGER{
                   disable(0),
                   enable(1)
                }
        MAX-ACCESS  read-write
        STATUS  current
        DESCRIPTION
               "Enable 128-bit encryption"
        ::= { pptp 6 }

        pptpIdleTimeout OBJECT-TYPE
        SYNTAX  Integer32
        MAX-ACCESS  read-write
        STATUS  current
        DESCRIPTION
               "idle timeout"
        ::= { pptp 7 }

        pptpLdapPwdAttrName OBJECT-TYPE
        SYNTAX  DisplayString
        MAX-ACCESS  read-write
        STATUS  current
        DESCRIPTION
               "The LDAP attribute name for the encrypted ntPassword."
        ::= { pptp 8 }

        pptpRoleId OBJECT-TYPE
        SYNTAX  Integer32
        MAX-ACCESS  read-write
        STATUS  current
        DESCRIPTION
               "For automatic role assignment of PPTP clients. 
                The role Id represent row id from Role table"
        ::= { pptp 9 }


        -- l2tp group 

        l2tpEnable OBJECT-TYPE
        SYNTAX  INTEGER {
                   no(0),
                   yes(1)
                } 
        MAX-ACCESS  read-write
        STATUS  current
        DESCRIPTION
               ""
        ::= { l2tp 1 }

        l2tpRemoteIpStartAddr OBJECT-TYPE
        SYNTAX  BlueIpAddress
        MAX-ACCESS  read-write
        STATUS  current
        DESCRIPTION
               "First remote ip address of the tunnel"
        ::= { l2tp 2 }

        l2tpRemoteIpEndAddr OBJECT-TYPE
        SYNTAX  BlueIpAddress
        MAX-ACCESS  read-write
        STATUS  current
        DESCRIPTION
               "Last remote ip address of the tunnel"
        ::= { l2tp 3 }

        l2tpLocalIpAddr OBJECT-TYPE
        SYNTAX  BlueIpAddress
        MAX-ACCESS  read-write
        STATUS  current
        DESCRIPTION
               ""
        ::= { l2tp 4 }

        l2tpIdleTimeout OBJECT-TYPE
        SYNTAX  Integer32
        MAX-ACCESS  read-write
        STATUS  current
        DESCRIPTION
               "idle timeout"
        ::= { l2tp 5 }

        l2tpLdapPwdAttrName OBJECT-TYPE
        SYNTAX  DisplayString
        MAX-ACCESS  read-write
        STATUS  current
        DESCRIPTION
               "For LDAP Authentication, the attribute name for the encrypted ntPassword."
        ::= { l2tp 6 }

        l2tpRoleId OBJECT-TYPE
        SYNTAX  Integer32
        MAX-ACCESS  read-write
        STATUS  current
        DESCRIPTION
               "For automatic role assignment of l2tp clients. 
                The role Id represent row id from Role table"
        ::= { l2tp 7 }

        -- subnet VPN group

        subnetVpnMode OBJECT-TYPE
        SYNTAX  INTEGER{
                   disable(0),
                   enable(1)
                }
        MAX-ACCESS  read-write
        STATUS  current
        DESCRIPTION
               "To enable or diable the subnet VPN option"
        ::= { subnetVpn 1 }

        subnetVpnRtFirstIp OBJECT-TYPE
        SYNTAX  BlueIpAddress
        MAX-ACCESS  read-write
        STATUS  current
        DESCRIPTION
               "Client address range: First remote Ip address."
        ::= { subnetVpn 2 }


        subnetVpnRtLastIp OBJECT-TYPE
        SYNTAX  BlueIpAddress
        MAX-ACCESS  read-write
        STATUS  current
        DESCRIPTION
               "Client address range: Last remote Ip address."
        ::= { subnetVpn 3 }


        subnetVpnSharedSec OBJECT-TYPE
        SYNTAX  DisplayString
        MAX-ACCESS  read-write
        STATUS  current
        DESCRIPTION
               "Group shared secret."
        ::= { subnetVpn 4 }


        subnetIpConfIdInUse OBJECT-TYPE
        SYNTAX  Integer32
        MAX-ACCESS  read-write
        STATUS  current
        DESCRIPTION
               "The ipsec configuration to use: represent the row id from 
                ipConfTable."
        ::= { subnetVpn 5 }

        -- http group

        httpPort OBJECT-TYPE
        SYNTAX  DisplayString
        MAX-ACCESS  read-write
        STATUS  current
        DESCRIPTION
               "Comma seperated list of Http/Proxy Ports to Monitor.
                Web requests on these ports will be redirected to the login"
        ::= { http 1 }

        httpRedirect OBJECT-TYPE
        SYNTAX  Integer32
        MAX-ACCESS  read-write
        STATUS  current
        DESCRIPTION
               "Port of http redirection for user login
                Adjust if 8080 is in use on your network."
        ::= { http 2 }


        httpAutoRedirectStatus OBJECT-TYPE
        SYNTAX  INTEGER{
                   disable(0),
                   enable(1)
                }
        MAX-ACCESS  read-write
        STATUS  current
        DESCRIPTION
               "If enabled, users will be redirected to the default URL,
               not their original destination."
        ::= { http 3 }


        httpAutoPause OBJECT-TYPE
        SYNTAX  Integer32
        MAX-ACCESS  read-write
        STATUS  current
        DESCRIPTION
               "Pause in seconds before redirecting user login"
        ::= { http 4 }

        httpDefaultUrl OBJECT-TYPE
        SYNTAX  OCTET STRING(SIZE(1..255))
        MAX-ACCESS  read-write
        STATUS  current
        DESCRIPTION
               "Default Url"
        ::= { http 5 }

        httpLogoutPopup OBJECT-TYPE
        SYNTAX  INTEGER{
                   disable(0),
                   enable(1)
                 }
        MAX-ACCESS  read-write
        STATUS  current
        DESCRIPTION
               "Logout popup enable/disable"
        ::= { http 6 }

        httpRootCaUrl OBJECT-TYPE
        SYNTAX  DisplayString
        MAX-ACCESS  read-write
        STATUS  current
        DESCRIPTION
               "Adjust if you custom SSL is a chain certificate."
        ::= { http 7 }

        httpExServerChoice OBJECT-TYPE
        SYNTAX  INTEGER {
                   disable(0),
                   enable(1)
                } 
        MAX-ACCESS  read-write
        STATUS  current
        DESCRIPTION
               "External server choice"
        ::= { http 8 }


        httpPasswdChangeChoice OBJECT-TYPE
        SYNTAX  INTEGER {
                   enable(1),
                   disable(0)
                } 
        MAX-ACCESS  read-write
        STATUS  current
        DESCRIPTION
               "
               Password change choice enable/disable.
               Password change choice are only available for local users."
        ::= { http 9 }

        httpLangChangeChoice OBJECT-TYPE
        SYNTAX  INTEGER {
                   disable(0),
                   enable(1)
                } 
        MAX-ACCESS  read-write
        STATUS  current
        DESCRIPTION
               " Language change choice enabled/disable.
               Language change choice are only available for local users."
        ::= { http 10 }

        httpLoginHelpButton OBJECT-TYPE
        SYNTAX  INTEGER {
                   disable(0),
                   enable(1)
                } 
        MAX-ACCESS  read-write
        STATUS  current
        DESCRIPTION
               "Custom HTML popups can be created in the customized 
               login section."
        ::= { http 11 }


        httpAttemptWait OBJECT-TYPE
        SYNTAX  Integer32 
        MAX-ACCESS  read-write
        STATUS  current
        DESCRIPTION
               "Number of minutes to wait after the maximum number of
                login attempts is made."
        ::= { http 12 }

        httpMaxNumOfActiveSess OBJECT-TYPE
        SYNTAX  Integer32 
        MAX-ACCESS  read-write
        STATUS  current
        DESCRIPTION
               "Number of active sessions per username/authentication
               type. '0' is unlimited."
        ::= { http 13 }

        httpAdminACL OBJECT-TYPE
        SYNTAX DisplayString
        MAX-ACCESS  read-write
        STATUS  current
        DESCRIPTION
               "Admin access control list. Comma seperated list of IP 
               addresses to allow adminstrative access"
        ::= { http 14 }

        httpRedirectToHostName OBJECT-TYPE
        SYNTAX INTEGER {
               disable(0),
               enable(1)
               }
        MAX-ACCESS  read-write
        STATUS  current
        DESCRIPTION
               " Redirect to hostname. 
                 Will cause unregistered users to be redirected to hostname, 
                 not the Ip address"
        ::= { http 15 }

        httpLoginAttempts OBJECT-TYPE
        SYNTAX Integer32
        MAX-ACCESS  read-write
        STATUS  current
        DESCRIPTION
               "Number of login attempts"
        ::= { http 16 }

        httpChainCertChangeChoice OBJECT-TYPE
        SYNTAX INTEGER {
                   disable(0),
                   enable(1)
               }    
        MAX-ACCESS  read-write
        STATUS  current
        DESCRIPTION
                 "Adjust if your custom SSL is a chain certificate
                  Hint: 
                  disable if you do not require a chain certificate"
        ::= { http 17 }


        -- Misc Group 
        statusUpTime OBJECT-TYPE
        SYNTAX  Integer32
        MAX-ACCESS  read-write
        STATUS  current
        DESCRIPTION
               "Time in seconds between updating internal status data"
        ::= { misc 1 }

        connectionCheckTime OBJECT-TYPE
        SYNTAX  Integer32
        MAX-ACCESS  read-write
        STATUS  current
        DESCRIPTION
               "Time in seconds between checking connection status"
        ::= { misc 2 }

        apCheckTime OBJECT-TYPE
        SYNTAX  Integer32
        MAX-ACCESS  read-write
        STATUS  current
        DESCRIPTION
               "Time in seconds between checking access point status"
        ::= { misc 3 }

        statusRefreshTime OBJECT-TYPE
        SYNTAX  Integer32
        MAX-ACCESS  read-write
        STATUS  current
        DESCRIPTION
               "Time in seconds between refreshing status display"
        ::= { misc 4 }

        apSnmpCommunity OBJECT-TYPE
        SYNTAX  DisplayString
        MAX-ACCESS  read-write
        STATUS  current
        DESCRIPTION
               "Read only snmp community string for all Access point"
        ::= { misc 5 }

--      ::= { misc 6 }

--       ::= { misc 7 }

--       ::= { misc 8 }

--       ::= { misc 9 }
        
        autoBkupRate OBJECT-TYPE
        SYNTAX  OCTET STRING (SIZE(5..7))
        MAX-ACCESS  read-write
        STATUS  current
        DESCRIPTION
               "Auto backup mode"
        ::= { autoBackup 1 }

        autoBkupFtpServName OBJECT-TYPE
        SYNTAX  DisplayString 
        MAX-ACCESS  read-write
        STATUS  current
        DESCRIPTION
               "FTP Server hostname"
        ::= { autoBackup 2 }

        autoBkupFtpDestDir OBJECT-TYPE
        SYNTAX  DisplayString 
        MAX-ACCESS  read-write
        STATUS  current
        DESCRIPTION
               "FTP Server hostname"
        ::= { autoBackup 3 }

        autoBkupFtpServUser OBJECT-TYPE
        SYNTAX  DisplayString 
        MAX-ACCESS  read-write
        STATUS  current
        DESCRIPTION
               "FTP Server user name"
        ::= { autoBackup 4 }

        autoBkupFtpServPasswd OBJECT-TYPE
        SYNTAX  DisplayString 
        MAX-ACCESS  read-write
        STATUS  current
        DESCRIPTION
               "FTP Server password"
        ::= { autoBackup 5 }

        tZone OBJECT-TYPE
        SYNTAX  DisplayString 

        MAX-ACCESS  read-write
        STATUS  current
        DESCRIPTION
               "Time zone"
        ::= { time 1  }

        tMonth OBJECT-TYPE
        SYNTAX  INTEGER (1..12) 
        MAX-ACCESS  read-write
        STATUS  current
        DESCRIPTION
               "System time setting:Month "
        ::= { time 2  }


        tDay OBJECT-TYPE
        SYNTAX  INTEGER (1..31)
        MAX-ACCESS  read-write
        STATUS  current
        DESCRIPTION
               "System time setting:Day "
        ::= { time 3  }


        tYear OBJECT-TYPE
        SYNTAX  Integer32 (1..9999)
        MAX-ACCESS  read-write
        STATUS  current
        DESCRIPTION
               "System time setting:Year "
        ::= { time 4  }


        tHours OBJECT-TYPE
        SYNTAX  INTEGER (0..24)
        MAX-ACCESS  read-write
        STATUS  current
        DESCRIPTION
               "System time setting:Hours "
        ::= { time 5  }

        tMinutes OBJECT-TYPE
        SYNTAX  INTEGER (0..59)
        MAX-ACCESS  read-write
        STATUS  current
        DESCRIPTION
               "System time setting:Minutes "
        ::= { time 6  }

        tSeconds OBJECT-TYPE
        SYNTAX  INTEGER (0..59)
        MAX-ACCESS  read-write
        STATUS  current
        DESCRIPTION
               "System time setting:Seconds."
        ::= { time 7  }

        tNtpSync OBJECT-TYPE
        SYNTAX  DisplayString 
        MAX-ACCESS  read-write
        STATUS  current
        DESCRIPTION
               "NTP settings synchronize"
        ::= { time 8  }

        tNtpServers OBJECT-TYPE
        SYNTAX  DisplayString 
        MAX-ACCESS  read-write
        STATUS  current
        DESCRIPTION
               "List of NTP servers"
        ::= { time 9  }

-- Public acecss group
-- Public access configuration settings.

        paFixedIpClientAccess OBJECT-TYPE
        SYNTAX  INTEGER {
                   disable(0),
                   enable(1)
        }    
        MAX-ACCESS  read-write
        STATUS  current
        DESCRIPTION
               "Allow any client fixed ip settings"
        ::= { publicAccess 1 }

        paSMTPServerIp OBJECT-TYPE
        SYNTAX  DisplayString 
        MAX-ACCESS  read-write
        STATUS  current
        DESCRIPTION
               "Ip or name of mail server for SMTP port redirection."
               
        ::= { publicAccess 2 }

-- Logging information
-- Logging configuration settings.

        logMaxLogEntries OBJECT-TYPE
        SYNTAX  Integer32
        MAX-ACCESS  read-write
        STATUS  current
        DESCRIPTION
               "Maximum number of log entries to keep"
        ::= { confLogGroup 1 }

        logNoOfDelLogEntries OBJECT-TYPE
        SYNTAX  Integer32 
        MAX-ACCESS  read-write
        STATUS  current
        DESCRIPTION
               "Number of log entries to delete when reaching maximum"
        ::= { confLogGroup 2 }


        logStorage OBJECT-TYPE
        SYNTAX  INTEGER {
                local  (0),
                remote (1),
                both   (2)
                }    

        MAX-ACCESS  read-write
        STATUS  current
        DESCRIPTION
               "Log storage"
        ::= { confLogGroup 3 }

        remoteLog OBJECT-TYPE
        SYNTAX  DisplayString
        MAX-ACCESS  read-write
        STATUS  current
        DESCRIPTION
               "ip or the name of the remote server log"
        ::= { confLogGroup 4 }

        sysLogFacility OBJECT-TYPE
        SYNTAX  DisplayString
        MAX-ACCESS  read-write
        STATUS  current
        DESCRIPTION
               "Facility of remote syslog server"
        ::= { confLogGroup 5 }

        logMaxRemSysLogLevel OBJECT-TYPE
        SYNTAX  INTEGER(0..7) 
        MAX-ACCESS  read-write
        STATUS  current
        DESCRIPTION
               "Maximum log level to send to remote syslog server"
        ::= { confLogGroup 6 }

-- appLogLevelTable 
--       the appLogLev table
        appLogLevTable     OBJECT-TYPE
        SYNTAX   SEQUENCE OF AppLogLevEntry
        MAX-ACCESS            not-accessible
        STATUS             current
        DESCRIPTION    "List of active appLogLevs"
              ::= { confLog 3 }

        appLogLevEntry OBJECT-TYPE
        SYNTAX  AppLogLevEntry
        MAX-ACCESS  not-accessible
        STATUS  current
        DESCRIPTION
             "An application log level  entry containing information about 
              a particular active appLogLevel."
        INDEX   { appLogLevId }
        ::= { appLogLevTable 1 }

        AppLogLevEntry ::=
              SEQUENCE {
                  appLogLevId
                      Integer32,
                  appLogLevName
                      DisplayString,
                  appLogLevLevel
                      INTEGER
        }
        appLogLevId  OBJECT-TYPE
        SYNTAX  Integer32(1..2147483647)
        MAX-ACCESS  not-accessible
        STATUS  current
        DESCRIPTION
               "Index for this table"
        ::= { appLogLevEntry 1 }

        appLogLevName  OBJECT-TYPE

        SYNTAX  DisplayString
        MAX-ACCESS  read-only
        STATUS  current
        DESCRIPTION
               "Name"
        ::= { appLogLevEntry 2 }

        appLogLevLevel  OBJECT-TYPE
        SYNTAX  INTEGER {
                emergency (0),
                alert(1),
                critical(2),
                error(3),
                warning(4),
                notice(5),
                info(6),
                debug(7)
                }    
        MAX-ACCESS  read-write
        STATUS  current
        DESCRIPTION
               ""
        ::= { appLogLevEntry 3 }
 

        -- the interface Group
        -- Contains the information about the policy
        -- managed protected 
        -- contains information about the protected side interface

        pIntTable     OBJECT-TYPE
        SYNTAX   SEQUENCE OF PIntEntry
        MAX-ACCESS            not-accessible
        STATUS             current
        DESCRIPTION    "A list of pInt entries."
              ::= { protected 1 }

        pIntEntry OBJECT-TYPE
        SYNTAX  PIntEntry
        MAX-ACCESS  not-accessible
        STATUS  current
        DESCRIPTION
             "A pInt entry containing information 
              about a particular protected interface"
        INDEX   { pIntId }
        ::= { pIntTable 1 }

        PIntEntry ::=
              SEQUENCE {
                  pIntId
                      Integer32,
                  pIntName
                      DisplayString,
                  pIntGetIpFromDhcp
                      INTEGER,
                  pIntDhcpTimeout
                      Integer32,
                  pIntIpAddress
                      BlueIpAddress,
                  pIntNetmask
                      BlueIpAddress,
                  pIntGateway
                      BlueIpAddress,
                  pIntPrimaryDNS
                      BlueIpAddress,
                  pIntSecondaryDNS
                      BlueIpAddress,
                  pIntDefaultDomain
                      OCTET STRING,
                  pIntHostName
                      DisplayString,
                  pIntEnableMulticast
                      INTEGER,
                  pIntVlanId
                      Integer32,
                  pIntVlanInterface
                      Integer32,
                  pIntProxyArpStatus
                      INTEGER,
                  pIntRowStatus
                      RowStatus 

          }
        pIntId OBJECT-TYPE
        SYNTAX  Integer32(1..2147483647)
        MAX-ACCESS  not-accessible
        STATUS  current
        DESCRIPTION
               "A unique id  for each protected interface"
        ::= { pIntEntry 1 }

        pIntName OBJECT-TYPE
        SYNTAX  DisplayString
        MAX-ACCESS  read-create
        STATUS  current
        DESCRIPTION
               "Interface name"
        ::= { pIntEntry 2 }



        pIntGetIpFromDhcp OBJECT-TYPE
        SYNTAX  INTEGER {
                   false(0),
                   true(1)
                } 
        MAX-ACCESS  read-create
        STATUS  current
        DESCRIPTION
               "Obtain IP settings from a DHCP server for the interface"
        ::= { pIntEntry 3 }

        pIntDhcpTimeout OBJECT-TYPE
        SYNTAX  Integer32 
        MAX-ACCESS  read-create
        STATUS  current
        DESCRIPTION
               "Timeout in seconds for DHCP request"
        ::= { pIntEntry 4 }

        pIntIpAddress OBJECT-TYPE
        SYNTAX  BlueIpAddress
        MAX-ACCESS  read-create
        STATUS  current
        DESCRIPTION
               "Ipaddress "
        ::= { pIntEntry 5 }

        pIntNetmask OBJECT-TYPE
        SYNTAX  BlueIpAddress
        MAX-ACCESS  read-create
        STATUS  current
        DESCRIPTION
               "netmask "
        ::= { pIntEntry 6 }

        pIntGateway OBJECT-TYPE
        SYNTAX  BlueIpAddress
        MAX-ACCESS  read-create
        STATUS  current
        DESCRIPTION
               "gateway ip address "
        ::= { pIntEntry 7 }

        pIntPrimaryDNS OBJECT-TYPE
        SYNTAX  BlueIpAddress
        MAX-ACCESS  read-create
        STATUS  current
        DESCRIPTION
               "Primary DNS "
        ::= { pIntEntry 8 }

        pIntSecondaryDNS OBJECT-TYPE
        SYNTAX  BlueIpAddress
        MAX-ACCESS  read-create
        STATUS  current
        DESCRIPTION
               "secondary DNS "
        ::= { pIntEntry 9 }

        pIntDefaultDomain OBJECT-TYPE
        SYNTAX  OCTET STRING (SIZE(1..50))
        MAX-ACCESS  read-create
        STATUS  current
        DESCRIPTION
               "Default Domain"
        ::= { pIntEntry 10 }


        pIntHostName OBJECT-TYPE
        SYNTAX  DisplayString
        MAX-ACCESS  read-create
        STATUS  current
        DESCRIPTION
               "Hostname"
        ::= { pIntEntry 11 }

        pIntEnableMulticast OBJECT-TYPE
        SYNTAX  INTEGER {
                   false(0),
                   true(1)
                }
        MAX-ACCESS  read-create
        STATUS  current
        DESCRIPTION
               "enable mulitcast for this interface"
        ::= { pIntEntry 12 }

        pIntVlanId OBJECT-TYPE
        SYNTAX  Integer32 
        MAX-ACCESS  read-create
        STATUS  current
        DESCRIPTION
               "VLAN Id associated with this protected interface"
        ::= { pIntEntry 13 }


        pIntVlanInterface OBJECT-TYPE
        SYNTAX  Integer32 
        MAX-ACCESS  read-create
        STATUS  current
        DESCRIPTION
               "VLAN type"
        ::= { pIntEntry 14 }

        pIntProxyArpStatus OBJECT-TYPE
        SYNTAX  INTEGER {
                   disable(0),
                   enable(1)
                } 
        MAX-ACCESS  read-create
        STATUS  current
        DESCRIPTION
               ""
        ::= { pIntEntry 15 }

        pIntRowStatus OBJECT-TYPE
        SYNTAX  RowStatus 
        MAX-ACCESS  read-create
        STATUS  current

        DESCRIPTION
               ""
        ::= { pIntEntry 16 }

        -- managed group 
        mIntTable     OBJECT-TYPE
        SYNTAX   SEQUENCE OF MIntEntry
        MAX-ACCESS            not-accessible
        STATUS             current
        DESCRIPTION    "A list of mInt entries."
              ::= { managed 1 }

        mIntEntry OBJECT-TYPE
        SYNTAX  MIntEntry
        MAX-ACCESS  not-accessible
        STATUS  current
        DESCRIPTION
             "A entry containing information 
              about a particular managed interface"
        INDEX   { mIntId }
        ::= { mIntTable 1 }

        MIntEntry ::=
              SEQUENCE {
                  mIntId
                      Integer32,
                  mIntName
                      DisplayString,
                  mIntEnableDhcpRelay
                      INTEGER,
                  mIntIpAddress
                      BlueIpAddress,
                  mIntNetmask
                      BlueIpAddress,
                  mIntDhcpServerOpt
                      INTEGER,
                  mIntNatAddresses
                      INTEGER,
                  mIntMulticastOpt
                      INTEGER,
                  mIntDhcpStartIpAddr
                      BlueIpAddress,
                  mIntDhcpEndIpAddr
                      BlueIpAddress,
                  mIntNetbiosNameServ
                      BlueIpAddress,
                  mIntDnsDomainName
                      OCTET STRING,
                  mIntDefaultLease
                      Integer32,
                  mIntMaximumLease
                      Integer32,
                  mIntDynamicDNS
                      INTEGER,
                  mIntVlanId
                      Integer32,
                  mIntVlanInterface
                      Integer32,
                  mIntProxyArpStatus
                      INTEGER,
                  mIntRowStatus
                      RowStatus 
          }
        mIntId OBJECT-TYPE
        SYNTAX  Integer32(1..2147483647)
        MAX-ACCESS  not-accessible
        STATUS  current
        DESCRIPTION
               "A unique id  for each managed interface"
        ::= { mIntEntry 1 }

        mIntName OBJECT-TYPE
        SYNTAX  DisplayString
        MAX-ACCESS  read-create
        STATUS  current
        DESCRIPTION
               "Managed interface name"
        ::= { mIntEntry 2 }

        mIntEnableDhcpRelay OBJECT-TYPE
        SYNTAX  INTEGER {
                   false(0),
                   true(1)
                }
        MAX-ACCESS  read-create
        STATUS  current
        DESCRIPTION
               "enable or disable dhcp relay. Setting it to true enables it
                and setting it to value 0 disables it"
        ::= { mIntEntry 3 }

        mIntIpAddress OBJECT-TYPE
        SYNTAX  BlueIpAddress
        MAX-ACCESS  read-create
        STATUS  current
        DESCRIPTION
               "Ipaddress of the managed interface"
        ::= { mIntEntry 4 }

        mIntNetmask OBJECT-TYPE
        SYNTAX  BlueIpAddress
        MAX-ACCESS  read-create
        STATUS  current
        DESCRIPTION
               "Netmask"
        ::= {mIntEntry 5 }


        mIntDhcpServerOpt OBJECT-TYPE
        SYNTAX  INTEGER {
                   stop(0),
                   start(1)
                }
        MAX-ACCESS  read-create
        STATUS  current
        DESCRIPTION
               "Start/stop DHCP server"
        ::= { mIntEntry 6 }

        mIntNatAddresses OBJECT-TYPE
        SYNTAX  INTEGER {
                   disable(0),
                   enable(1)
                }
        MAX-ACCESS  read-create
        STATUS  current
        DESCRIPTION
               "NAT the addresses in the protected interface address"
        ::= { mIntEntry 7 }

        mIntMulticastOpt OBJECT-TYPE
        SYNTAX  INTEGER {
                   disable(0),
                   enable(1)
                }
        MAX-ACCESS  read-create
        STATUS  current
        DESCRIPTION
               "Enable/disable multicast"
        ::= { mIntEntry 8 }

        mIntDhcpStartIpAddr OBJECT-TYPE
        SYNTAX  BlueIpAddress
        MAX-ACCESS  read-write
        STATUS  current
        DESCRIPTION
               "DHCP start ip address "
        ::= { mIntEntry 9 }


        mIntDhcpEndIpAddr OBJECT-TYPE
        SYNTAX  BlueIpAddress
        MAX-ACCESS  read-create
        STATUS  current
        DESCRIPTION
               "DHCP end IP address"
        ::= { mIntEntry 10 }

        mIntNetbiosNameServ OBJECT-TYPE
        SYNTAX  BlueIpAddress
        MAX-ACCESS  read-create
        STATUS  current
        DESCRIPTION
               "Netbios name server"
        ::= { mIntEntry 11 }

        mIntDnsDomainName OBJECT-TYPE
        SYNTAX  OCTET STRING (SIZE(1..50))
        MAX-ACCESS  read-create
        STATUS  current
        DESCRIPTION
               "DNS domain name"
        ::= { mIntEntry 12 }


        mIntDefaultLease OBJECT-TYPE
        SYNTAX  Integer32
        MAX-ACCESS  read-create
        STATUS  current
        DESCRIPTION
               "Default lease time in seconds"
        ::= { mIntEntry 13 }

        mIntMaximumLease OBJECT-TYPE
        SYNTAX  Integer32
        MAX-ACCESS  read-create
        STATUS  current
        DESCRIPTION
               "Maximum lease time in seconds"
        ::= { mIntEntry 14 }
        
        mIntDynamicDNS OBJECT-TYPE
        SYNTAX  INTEGER{
                   disabled(1),
                   adHoc(2),
                   interim(3) 
                }
        MAX-ACCESS  read-create
        STATUS  current
        DESCRIPTION
               "Dynamic DNS update scheme"
        ::= { mIntEntry 15 }

        mIntVlanId OBJECT-TYPE
        SYNTAX  Integer32 
        MAX-ACCESS  read-write
        STATUS  current
        DESCRIPTION
               ""
        ::= { mIntEntry 16 }

        mIntVlanInterface OBJECT-TYPE
        SYNTAX  Integer32 
        MAX-ACCESS  read-create
        STATUS  current
        DESCRIPTION
               "VLAN id"
        ::= { mIntEntry 17 }

        mIntProxyArpStatus OBJECT-TYPE
        SYNTAX  INTEGER {
                   disable(0),
                   enable(1)
                } 
        MAX-ACCESS  read-create
        STATUS  current
        DESCRIPTION
               ""
        ::= { mIntEntry 18 }

        mIntRowStatus OBJECT-TYPE
        SYNTAX  RowStatus 
        MAX-ACCESS  read-create
        STATUS  current
        DESCRIPTION
               "The Row status attribute for row handling"
        ::= { mIntEntry 19 }
        

        -- the fixedIpAddr  Group

        -- the fixedIpAddr table
        fixedIpAddrTable     OBJECT-TYPE
        SYNTAX   SEQUENCE OF FixedIpAddrEntry
        MAX-ACCESS            not-accessible
        STATUS             current
        DESCRIPTION    ""
              ::= { managed 2 }

        fixedIpAddrEntry OBJECT-TYPE
        SYNTAX  FixedIpAddrEntry
        MAX-ACCESS  not-accessible
        STATUS  current
        DESCRIPTION
             "An fixed ip address entry mapping between the hardware address 
              and the ip address and their default role id"
        INDEX   { mIntId, fixedIpAddrId }
        ::= { fixedIpAddrTable 1 }
        FixedIpAddrEntry ::=
              SEQUENCE {
                  fixedIpAddrId
                      Integer32,
                  fixedIpAddrMac
                      OCTET STRING,
                  fixedIpAddrAddress
                      BlueIpAddress,
                  fixedIpAddrHost
                      BlueIpAddress,
                  fixedIpAddrRoleId
                      Integer32,
                  fixedIpAddrRowStatus
                      RowStatus 
        }

        fixedIpAddrId OBJECT-TYPE
        SYNTAX  Integer32(1..2147483647)
        MAX-ACCESS  not-accessible 
        STATUS  current
        DESCRIPTION
               ""
        ::= { fixedIpAddrEntry 1 }

        fixedIpAddrMac OBJECT-TYPE
        SYNTAX OCTET STRING(SIZE(6..17))
        MAX-ACCESS  read-create
        STATUS  current
        DESCRIPTION
               ""
        ::= { fixedIpAddrEntry 2 }

        fixedIpAddrAddress OBJECT-TYPE
        SYNTAX  BlueIpAddress
        MAX-ACCESS  read-create
        STATUS  current
        DESCRIPTION
               ""
        ::= { fixedIpAddrEntry 3 }

        fixedIpAddrHost OBJECT-TYPE
        SYNTAX  BlueIpAddress
        MAX-ACCESS  read-create
        STATUS  current
        DESCRIPTION
               ""
        ::= { fixedIpAddrEntry 4 }

        fixedIpAddrRoleId OBJECT-TYPE
        SYNTAX  Integer32
        MAX-ACCESS  read-create
        STATUS  current
        DESCRIPTION
               ""
        ::= { fixedIpAddrEntry 5 }

        fixedIpAddrRowStatus OBJECT-TYPE
        SYNTAX  RowStatus 
        MAX-ACCESS  read-create
        STATUS  current
        DESCRIPTION
               "The Row status attribute for row handling"
        ::= { fixedIpAddrEntry 6 }

        -- the nat  Group
        -- Contains the information about the nat settings 

        -- the nat table
        natTable     OBJECT-TYPE
        SYNTAX   SEQUENCE OF NatEntry
        MAX-ACCESS            not-accessible
        STATUS             current
        DESCRIPTION    ""
              ::= { managed 3 }

        natEntry OBJECT-TYPE
        SYNTAX  NatEntry
        MAX-ACCESS  not-accessible
        STATUS  current
        DESCRIPTION
             ""
        INDEX   { mIntId,natId}
        ::= { natTable 1 }
        NatEntry ::=
              SEQUENCE {
                  natId
                      Integer32,
                  natProtectedIp
                      BlueIpAddress,
                  natManagedIp
                      BlueIpAddress,
                  natRowStatus
                      RowStatus 
        }

        natId OBJECT-TYPE
        SYNTAX  Integer32(1..2147483647)
        MAX-ACCESS  not-accessible 
        STATUS  current
        DESCRIPTION
               ""
        ::= { natEntry 1 }

        natProtectedIp OBJECT-TYPE
        SYNTAX  BlueIpAddress
        MAX-ACCESS  read-create
        STATUS  current
        DESCRIPTION
               "Protected side IP address"
        ::= { natEntry 2 }

        natManagedIp OBJECT-TYPE
        SYNTAX  BlueIpAddress
        MAX-ACCESS  read-create
        STATUS  current
        DESCRIPTION
               "Managed side IP address"
        ::= { natEntry 3 }

        natRowStatus OBJECT-TYPE
        SYNTAX  RowStatus 
        MAX-ACCESS  read-create
        STATUS  current
        DESCRIPTION
               "The Row status attribute for row handling"
        ::= { natEntry 4 }
        
        
        -- failover group

        heartBeatInterval OBJECT-TYPE
        SYNTAX  Integer32
        MAX-ACCESS  read-write
        STATUS  current
        DESCRIPTION
               "the time in seconds between heartbeats "
        ::= { failover 1 }
        

        noOfFailedBeats OBJECT-TYPE
        SYNTAX  Integer32
        MAX-ACCESS  read-write
        STATUS  current
        DESCRIPTION
               "Number of failed beats before fail-over"
        ::= { failover 2 }
       
        -- the replication  Group
        -- Contains the information about the replication

        machineRole OBJECT-TYPE
        SYNTAX  INTEGER{
                  master(1),
                  slave(2)
                }
        MAX-ACCESS  read-write 
        STATUS  current
        DESCRIPTION
               ""
        ::= { replication 1 }

        genSnapshot OBJECT-TYPE
        SYNTAX  INTEGER{
                   disable(0),
                   enable(1)
                }
        MAX-ACCESS  read-write 
        STATUS  current
        DESCRIPTION
               ""
        ::= { replication 2 }

        mobilityMode OBJECT-TYPE
        SYNTAX  INTEGER{
                   disable(0),
                   enable(1)
                }
        MAX-ACCESS  read-write 
        STATUS  current
        DESCRIPTION
               "enable/disable mobility between blue servers"
        ::= { mobility 1 }
        
        mobilityMeshKey OBJECT-TYPE
        SYNTAX  DisplayString
        MAX-ACCESS  read-write 
        STATUS  current
        DESCRIPTION
               "Community mesh key"
        ::= { mobility 2 }
        

        -- the slave  Group
        -- Contains the information about the slave

        -- the slave table
        slaveTable     OBJECT-TYPE
        SYNTAX   SEQUENCE OF SlaveEntry
        MAX-ACCESS            not-accessible
        STATUS             current
        DESCRIPTION    "A list of slave entries."
              ::= { replication 3 }

        slaveEntry OBJECT-TYPE
        SYNTAX  SlaveEntry
        MAX-ACCESS  not-accessible
        STATUS  current
        DESCRIPTION
             ""
        INDEX   { slaveId }
        ::= { slaveTable 1 }

        SlaveEntry ::=
              SEQUENCE {
                  slaveId
                      Integer32,
                      slaveEnabled
                      INTEGER,
                  slaveAddress
                      OCTET STRING,
                  slaveNotes
                      DisplayString,
                  slaveRowStatus
                      RowStatus,
                  slaveMobility
                      INTEGER
        }

        slaveId OBJECT-TYPE
        SYNTAX  Integer32(1..2147483647)
        MAX-ACCESS  not-accessible
        STATUS  current
        DESCRIPTION
               ""
        ::= { slaveEntry 1 }

        slaveEnabled OBJECT-TYPE
        SYNTAX  INTEGER{
                   no(0),
                   yes(1)
                }
        MAX-ACCESS  read-create
        STATUS  current
        DESCRIPTION
               ""
        ::= { slaveEntry 2 }

        slaveAddress OBJECT-TYPE
        SYNTAX  OCTET STRING(SIZE(1..50))
        MAX-ACCESS  read-create
        STATUS  current
        DESCRIPTION
               ""
        ::= { slaveEntry 3 }

        slaveNotes OBJECT-TYPE
        SYNTAX  DisplayString
        MAX-ACCESS  read-create
        STATUS  current
        DESCRIPTION
               ""
        ::= { slaveEntry 4 }

        slaveRowStatus OBJECT-TYPE
        SYNTAX  RowStatus 
        MAX-ACCESS  read-create
        STATUS  current
        DESCRIPTION
               "The Row status attribute for row handling"
        ::= { slaveEntry 5 }

        slaveMobility OBJECT-TYPE
        SYNTAX  INTEGER{
                   disable(0),
                   enable(1)
                }
        MAX-ACCESS  read-create
        STATUS  current
        DESCRIPTION
               ""
        ::= { slaveEntry 6 }



        -- the connection Group
        -- Contains the information about the policy

        -- the connection table
        connectionTable     OBJECT-TYPE
        SYNTAX   SEQUENCE OF ConnectionEntry
        MAX-ACCESS            not-accessible
        STATUS             current
        DESCRIPTION    "List of active connections"
              ::= { connection 1 }

        connectionEntry OBJECT-TYPE
        SYNTAX  ConnectionEntry
        MAX-ACCESS  not-accessible
        STATUS  current
        DESCRIPTION
             "Entry containing information about a particular active connection."
        INDEX   { connectionId }
        ::= { connectionTable 1 }

        ConnectionEntry ::=
              SEQUENCE {
                  connectionId
                      Integer32,
                  connectionName
                      DisplayString,
                  connectionIp
                      BlueIpAddress,
                  connectionMac
                      OCTET STRING,
                  connectionRoleId
                      Integer32,
                  connectionUserId
                      Integer32,
                  connectionLoginTime
                       DateAndTime,
                  connectionChecked
                      TimeTicks,
                  connectionBytes
                      Integer32,
                  connectionCurRate
                      Integer32,
                  connectionExpiry
                      Integer32,
                  connectionDev
                      OCTET STRING,
                  connectionHost
                      DisplayString,
                  connectionUnReg
                      Integer32,
                  connectionAP
                      OCTET STRING,
                  connectionLoginAttempt
                      Integer32,
                  connectionLoginAttemptCnt
                      Integer32,
                  connectionRoamMac
                      OCTET STRING
        }

        connectionId  OBJECT-TYPE
        SYNTAX  Integer32(1..2147483647)
        MAX-ACCESS  not-accessible
        STATUS  current
        DESCRIPTION
               "Index for this table"
        ::= { connectionEntry 1 }

        connectionName  OBJECT-TYPE
        SYNTAX  DisplayString
        MAX-ACCESS  read-only
        STATUS  current
        DESCRIPTION
               "Connection name"
        ::= { connectionEntry 2 }

        connectionIp  OBJECT-TYPE
        SYNTAX  BlueIpAddress
        MAX-ACCESS  read-write 
        STATUS  current
        DESCRIPTION
               "Ip address of the machine from where the connection is established"
        ::= { connectionEntry 3 }

        connectionMac OBJECT-TYPE
        SYNTAX OCTET STRING(SIZE(6..17))
        MAX-ACCESS  read-write
        STATUS  current
        DESCRIPTION
               "The Mac address of the machine from where the connection is established"
        ::= { connectionEntry 4 }

        connectionRoleId OBJECT-TYPE
        SYNTAX  Integer32
        MAX-ACCESS  read-write
        STATUS  current
        DESCRIPTION
               "The role id associated with this connection"
        ::= { connectionEntry 5 }

        connectionUserId OBJECT-TYPE
        SYNTAX  Integer32
        MAX-ACCESS  read-write
        STATUS  current
        DESCRIPTION
               "User id associated with this connection"
        ::= { connectionEntry 6 }

        connectionLoginTime OBJECT-TYPE
        SYNTAX  DateAndTime
        MAX-ACCESS  read-write
        STATUS  current
        DESCRIPTION
               "User login time"
        ::= { connectionEntry 7 }

        connectionChecked OBJECT-TYPE
        SYNTAX  TimeTicks
        MAX-ACCESS  read-write
        STATUS  current
        DESCRIPTION
               ""
        ::= { connectionEntry 8 }

        connectionBytes OBJECT-TYPE
        SYNTAX  Integer32
        MAX-ACCESS  read-write
        STATUS  current
        DESCRIPTION
               ""
        ::= { connectionEntry 9 }

        connectionCurRate OBJECT-TYPE
        SYNTAX  Integer32
        MAX-ACCESS  read-write
        STATUS  current
        DESCRIPTION
               ""
        ::= { connectionEntry 10 }

        connectionExpiry OBJECT-TYPE
        SYNTAX  Integer32
        MAX-ACCESS  read-write
        STATUS  current
        DESCRIPTION
               ""
        ::= { connectionEntry 11 }

        connectionDev OBJECT-TYPE
        SYNTAX  OCTET STRING (SIZE(1..11))
        MAX-ACCESS  read-write
        STATUS  current
        DESCRIPTION
               ""

        ::= { connectionEntry 12 }

        connectionHost OBJECT-TYPE
        SYNTAX  DisplayString
        MAX-ACCESS  read-write
        STATUS  current
        DESCRIPTION
               ""
        ::= { connectionEntry 13 }

        connectionUnReg OBJECT-TYPE
        SYNTAX  Integer32
        MAX-ACCESS  read-write
        STATUS  current
        DESCRIPTION
               ""
        ::= { connectionEntry 14 }

        connectionAP OBJECT-TYPE
        SYNTAX  OCTET STRING(SIZE(1..20))
        MAX-ACCESS  read-write
        STATUS  current
        DESCRIPTION
               ""
        ::= { connectionEntry 15 }

        connectionLoginAttempt OBJECT-TYPE
        SYNTAX  Integer32
        MAX-ACCESS  read-write
        STATUS  current
        DESCRIPTION
               ""
        ::= { connectionEntry 16 }

        connectionLoginAttemptCnt OBJECT-TYPE
        SYNTAX  Integer32
        MAX-ACCESS  read-write
        STATUS  current
        DESCRIPTION
               ""
        ::= { connectionEntry 17 }

        connectionRoamMac OBJECT-TYPE
        SYNTAX OCTET STRING(SIZE(6..17))
        MAX-ACCESS  read-write
        STATUS  current
        DESCRIPTION
               "The Mac address of the roaming machine"
        ::= { connectionEntry 18 }


        -- the role Group
        -- Contains the role information 

        -- the role table

        roleTable     OBJECT-TYPE
        SYNTAX   SEQUENCE OF RoleEntry
        MAX-ACCESS            not-accessible
        STATUS             current
        DESCRIPTION    "A list of role entries."
              ::= { roles 1 }

        roleEntry OBJECT-TYPE
        SYNTAX  RoleEntry
        MAX-ACCESS  not-accessible
        STATUS  current
        DESCRIPTION
             "A role entry containing information about a particular role."
        INDEX   { roleId }
        ::= { roleTable 1 }

        RoleEntry ::=
              SEQUENCE {
                  roleId
                      Integer32,
                  roleName
                      OCTET STRING,
                  roleType
                      OCTET STRING,
                  roleQosRate
                       OCTET STRING,
                  roleQosQnt
                      Integer32,
                  roleVpn
                       INTEGER,
                  roleInherit
                      Integer32,
                  roleUnGuestLogin
                      Integer32,
                  roleUnUserLogin
                      Integer32,
                  roleNotes
                      DisplayString,
                  roleQosUserIn
                      Integer32,
                  roleQosUserOut
                      Integer32,
                  roleQosPriorityIn
                      Integer32,
                  roleQosPriorityOut
                      Integer32,
                  roleQosPriInOverride
                       OCTET STRING,
                  roleQosPriOutOverride
                       OCTET STRING,
                 roleQosDscpIn
                      Integer32,
                 roleQosDscpOut
                      Integer32,
                  roleQosDscpInOverride
                       OCTET STRING,
                  roleQosDscpOutOverride
                       OCTET STRING,
                  roleQosRateOut
                      Integer32,
                  roleQosRateQntOut
                      OCTET STRING,
                  roleVlanId
                      Integer32,
                  roleRedirect
                       OCTET STRING,
                  roleRowStatus
                      RowStatus 
        }
        roleId OBJECT-TYPE
        SYNTAX  Integer32(1..2147483647)
        MAX-ACCESS  not-accessible 
        STATUS  current
        DESCRIPTION
               "Index for this table"
        ::= { roleEntry 1 }

        roleName OBJECT-TYPE
        SYNTAX  OCTET STRING (SIZE(1..50))
        MAX-ACCESS  read-create 
        STATUS  current
        DESCRIPTION
               "A unique name associated with this role"
        ::= { roleEntry 2 }

        roleType OBJECT-TYPE
        SYNTAX  OCTET STRING (SIZE(1..3))
        MAX-ACCESS  read-create
        STATUS  current
        DESCRIPTION
                ""
        ::= { roleEntry 3 }

        roleQosRate OBJECT-TYPE
        SYNTAX  OCTET STRING (SIZE(1..5))
        MAX-ACCESS  read-create
        STATUS  current
        DESCRIPTION
                "The units of bandwidth allocated"
        ::= { roleEntry 4 }

        roleQosQnt OBJECT-TYPE
        SYNTAX  Integer32
        MAX-ACCESS  read-create
        STATUS  current
        DESCRIPTION
                "The total bandwidth allocated to all users with this role"
        ::= { roleEntry 5 }

        roleVpn OBJECT-TYPE
        SYNTAX  INTEGER {
                   none(1),
                   pptp (2),
                   modarate(3)
                }
        MAX-ACCESS  read-create
        STATUS  current
        DESCRIPTION
                "Requires the user to connect to the BSC-1000 
                 with a vpn of this type already enabled"
        ::= { roleEntry 6 }

        roleInherit OBJECT-TYPE
        SYNTAX  Integer32
        MAX-ACCESS  read-create
        STATUS  current
        DESCRIPTION
                "Role id of the role to be inherited from"
        ::= { roleEntry 7 }

        roleUnGuestLogin OBJECT-TYPE
        SYNTAX  Integer32
        MAX-ACCESS  read-create
        STATUS  current
        DESCRIPTION
                ""
        ::= { roleEntry 8 }

        roleUnUserLogin OBJECT-TYPE
        SYNTAX  Integer32
        MAX-ACCESS  read-create
        STATUS  current
        DESCRIPTION
                ""
        ::= { roleEntry 9 }

        roleNotes OBJECT-TYPE
        SYNTAX  DisplayString
        MAX-ACCESS  read-create
        STATUS  current
        DESCRIPTION
              "User Notes"
        ::= { roleEntry 10 }

--      ::= { roleEntry 11 }

        roleQosUserIn OBJECT-TYPE
        SYNTAX  Integer32
        MAX-ACCESS  read-create
        STATUS  current
        DESCRIPTION
                ""
        ::= { roleEntry 12 }

        roleQosUserOut OBJECT-TYPE
        SYNTAX  Integer32
        MAX-ACCESS  read-create
        STATUS  current
        DESCRIPTION
                ""
        ::= { roleEntry 13 }

        roleQosPriorityIn OBJECT-TYPE
        SYNTAX  Integer32
        MAX-ACCESS  read-create
        STATUS  current
        DESCRIPTION
                ""
        ::= { roleEntry 14 }

        roleQosPriorityOut OBJECT-TYPE
        SYNTAX  Integer32
        MAX-ACCESS  read-create
        STATUS  current
        DESCRIPTION
                ""
        ::= { roleEntry 15 }

        roleQosPriInOverride OBJECT-TYPE
        SYNTAX  OCTET STRING (SIZE(1))
        MAX-ACCESS  read-create
        STATUS  current
        DESCRIPTION
                ""
        ::= { roleEntry 16 }

        roleQosPriOutOverride OBJECT-TYPE
        SYNTAX  OCTET STRING (SIZE(1))
        MAX-ACCESS  read-create
        STATUS  current
        DESCRIPTION
                ""
        ::= { roleEntry 17 }


        roleQosDscpIn OBJECT-TYPE
        SYNTAX  Integer32
        MAX-ACCESS  read-create
        STATUS  current
        DESCRIPTION
                ""
        ::= { roleEntry 18 }

        roleQosDscpOut OBJECT-TYPE
        SYNTAX  Integer32
        MAX-ACCESS  read-create
        STATUS  current
        DESCRIPTION
                ""
        ::= { roleEntry 19 }

        roleQosDscpInOverride OBJECT-TYPE
        SYNTAX  OCTET STRING (SIZE(1))
        MAX-ACCESS  read-create
        STATUS  current
        DESCRIPTION
                ""
        ::= { roleEntry 20 }

        roleQosDscpOutOverride OBJECT-TYPE
        SYNTAX  OCTET STRING (SIZE(1))
        MAX-ACCESS  read-create
        STATUS  current
        DESCRIPTION
                ""
        ::= { roleEntry 21 }

        roleQosRateOut OBJECT-TYPE
        SYNTAX  Integer32
        MAX-ACCESS  read-create
        STATUS  current
        DESCRIPTION
                ""
        ::= { roleEntry 22 }

        roleQosRateQntOut OBJECT-TYPE
        SYNTAX  OCTET STRING (SIZE(1..5))
        MAX-ACCESS  read-create
        STATUS  current
        DESCRIPTION
                ""
        ::= { roleEntry 23 }

        roleVlanId OBJECT-TYPE
        SYNTAX  Integer32
        MAX-ACCESS  read-create
        STATUS  current
        DESCRIPTION
                ""
        ::= { roleEntry 24 }

        roleRedirect OBJECT-TYPE
        SYNTAX  OCTET STRING (SIZE(1..5))
        MAX-ACCESS  read-create
        STATUS  current
        DESCRIPTION
                ""
        ::= { roleEntry 25 }

        roleRowStatus OBJECT-TYPE
        SYNTAX  RowStatus 
        MAX-ACCESS  read-create
        STATUS  current
        DESCRIPTION
               "The Row status attribute for row handling"
        ::= { roleEntry 26 }


        -- the serviceMgmt  Group

        -- the serviceMgmt table
        serviceMgmtTable     OBJECT-TYPE
        SYNTAX   SEQUENCE OF ServiceMgmtEntry
        MAX-ACCESS            not-accessible
        STATUS             current
        DESCRIPTION    ""
              ::= { serviceMgmt 1 }

        serviceMgmtEntry OBJECT-TYPE
        SYNTAX  ServiceMgmtEntry
        MAX-ACCESS  not-accessible
        STATUS  current
        DESCRIPTION
             ""
        INDEX   { serviceMgmtId }

        ::= { serviceMgmtTable 1 }

        ServiceMgmtEntry ::=
              SEQUENCE {
                  serviceMgmtId
                       Integer32,
                  serviceMgmtName
                      DisplayString,
                  serviceMgmtOptStatus
                      INTEGER,
                  serviceMgmtDesr
                     DisplayString
        }
        serviceMgmtId OBJECT-TYPE
        SYNTAX  Integer32(1..2147483647)
        MAX-ACCESS  not-accessible
        STATUS  current
        DESCRIPTION
               "Service mgmt table Index"
        ::= { serviceMgmtEntry 1 }

        serviceMgmtName OBJECT-TYPE
        SYNTAX  DisplayString 
        MAX-ACCESS  read-only
        STATUS  current
        DESCRIPTION
               "Service name"
        ::= { serviceMgmtEntry 2 }

        serviceMgmtOptStatus OBJECT-TYPE
        SYNTAX  INTEGER {
                   start  (1),
                   stop   (2),
                   restart(3),
                   noopt  (4)  
                } 
        MAX-ACCESS  read-write
        STATUS  current
        DESCRIPTION
               "To start, stop or to retart different services. The default 
                value is noopt. This object does not hold  the current status 
                of the service instead it holds the last operation performed 
                on the selected service via SNMP."  
        ::= { serviceMgmtEntry 3 }

        serviceMgmtDesr OBJECT-TYPE
        SYNTAX  DisplayString 
        MAX-ACCESS  read-only
        STATUS  current
        DESCRIPTION
               "Contains service status message."
        ::= { serviceMgmtEntry 4 }

        -- summary group

        -- user summary

        userSumNoOfUsr OBJECT-TYPE
        SYNTAX  Integer32 
        MAX-ACCESS  read-only
        STATUS  current
        DESCRIPTION
               "Total number of users."
        ::= { userSummary 1 }

        userSumNoOfLogdInUsr OBJECT-TYPE
        SYNTAX  Integer32 
        MAX-ACCESS  read-only
        STATUS  current
        DESCRIPTION
               "Total number of logged in users."
        ::= { userSummary 2 }


        userSumNoOfLogdVPNUsr OBJECT-TYPE
        SYNTAX  Integer32 
        MAX-ACCESS  read-only
        STATUS  current
        DESCRIPTION
               "Total number of logged in VPN tunnel users."
        ::= { userSummary 3 }

        usmSumTtlBandWthInUse OBJECT-TYPE
        SYNTAX  Integer32 
        MAX-ACCESS  read-only
        STATUS  current
        DESCRIPTION
               "Total bandwidth currently in use."
        ::= { userSummary 4 }
        -- user session group information

        -- system stats group

        sysStatCpuUtil OBJECT-TYPE
        SYNTAX  Integer32
        MAX-ACCESS  read-only

        STATUS  current
        DESCRIPTION
               "CPU utilization in percentage."
        ::= { systemStats 1 }

        sysStatMemUtil OBJECT-TYPE
        SYNTAX  Integer32
        MAX-ACCESS  read-only
        STATUS  current
        DESCRIPTION
               "Memory utilization in Kilo bytes."
        ::= { systemStats 2 }


        sysStatTotalDiskSpace OBJECT-TYPE
        SYNTAX  Integer32
        MAX-ACCESS  read-only
        STATUS  current
        DESCRIPTION
               "Total Disk space."
        ::= { systemStats 3 }


        sysStatDiskSpaceUsed OBJECT-TYPE
        SYNTAX  Integer32
        MAX-ACCESS  read-only
        STATUS  current
        DESCRIPTION
               "Disk space used."
        ::= { systemStats 4 }

        sysStatDiskSpaceFree OBJECT-TYPE
        SYNTAX  Integer32
        MAX-ACCESS  read-only
        STATUS  current
        DESCRIPTION
               "Disk space free."
        ::= { systemStats 5 }

        sysStatLOgSpaceUsed OBJECT-TYPE
        SYNTAX  Integer32
        MAX-ACCESS  read-only
        STATUS  current
        DESCRIPTION
               "Log space used in percentage."
        ::= { systemStats 6 }

        sysStatNeedRestart OBJECT-TYPE
        SYNTAX  INTEGER {
                no(0),
                yes(1)
                }
        MAX-ACCESS  read-only
        STATUS  current
        DESCRIPTION
               "Log space used in percentage."
        ::= { systemStats 7 }

        -- the certificate Group
        certTable     OBJECT-TYPE
        SYNTAX   SEQUENCE OF CertEntry
        MAX-ACCESS            not-accessible
        STATUS             current
        DESCRIPTION    "A list of cert entries."
              ::= { certificate 1 }

        certEntry OBJECT-TYPE
        SYNTAX  CertEntry
        MAX-ACCESS  not-accessible
        STATUS  current
        DESCRIPTION
             "A certEntry containing information 
              about certificates."
        INDEX   { certId }
        ::= { certTable 1 }

        CertEntry ::=
              SEQUENCE {
                  certId
                      Integer32,
                  certType
                      DisplayString,
                  certSubject
                      DisplayString,
                  certStartDate
                      DisplayString,
                  certEndDate
                      DisplayString,
                  certIssuer
                      DisplayString,
                  certName
                      DisplayString,
                  certOrg
                      DisplayString,
                  certContent
                      OCTET STRING,
                  certPkey
                      DisplayString,
                  certPkeyAlgo
                      DisplayString,
                  certPkeySize
                      Integer32,
                  certSerial
                      DisplayString,
                  certSignAlgo
                      DisplayString,
                  certVersion
                      Integer32,
                  certRowStatus
                      RowStatus 
         }
        certId OBJECT-TYPE
        SYNTAX  Integer32(1..2147483647)
        MAX-ACCESS  not-accessible
        STATUS  current
        DESCRIPTION
               "A unique id  for each cert."
        ::= { certEntry 1 }

        certType OBJECT-TYPE
        SYNTAX  DisplayString
        MAX-ACCESS  read-create
        STATUS  current
        DESCRIPTION
               "Certificate type"
        ::= { certEntry 2 }

        certSubject OBJECT-TYPE
        SYNTAX  DisplayString
        MAX-ACCESS  read-create
        STATUS  current
        DESCRIPTION
               ""
        ::= { certEntry 3 }

        certStartDate OBJECT-TYPE
        SYNTAX  DisplayString
        MAX-ACCESS  read-create
        STATUS  current
        DESCRIPTION
               ""
        ::= { certEntry 4 }

        certEndDate OBJECT-TYPE
        SYNTAX  DisplayString
        MAX-ACCESS  read-create
        STATUS  current
        DESCRIPTION
               ""
        ::= { certEntry 5 }

        certIssuer OBJECT-TYPE
        SYNTAX  DisplayString
        MAX-ACCESS  read-create
        STATUS  current
        DESCRIPTION
               ""
        ::= { certEntry 6 }

        certName OBJECT-TYPE
        SYNTAX  DisplayString
        MAX-ACCESS  read-create
        STATUS  current
        DESCRIPTION
               ""
        ::= { certEntry 7 }

        certOrg OBJECT-TYPE
        SYNTAX  DisplayString
        MAX-ACCESS  read-create
        STATUS  current
        DESCRIPTION
               ""
        ::= { certEntry 8 }

        certContent OBJECT-TYPE
        SYNTAX  OCTET STRING(SIZE(0..65535))
        MAX-ACCESS  read-create
        STATUS  current
        DESCRIPTION
               ""
        ::= { certEntry 9 }

        certPkey OBJECT-TYPE
        SYNTAX  DisplayString
        MAX-ACCESS  read-create
        STATUS  current
        DESCRIPTION
               ""
        ::= { certEntry 10 }

        certPkeyAlgo OBJECT-TYPE
        SYNTAX  DisplayString
        MAX-ACCESS  read-create
        STATUS  current
        DESCRIPTION
               ""
        ::= { certEntry 11 }

        certPkeySize OBJECT-TYPE
        SYNTAX  Integer32
        MAX-ACCESS  read-create
        STATUS  current
        DESCRIPTION
               ""
        ::= { certEntry 12 }

        certSerial OBJECT-TYPE
        SYNTAX  DisplayString
        MAX-ACCESS  read-create
        STATUS  current
        DESCRIPTION
               ""
        ::= { certEntry 13 }

        certSignAlgo OBJECT-TYPE
        SYNTAX  DisplayString
        MAX-ACCESS  read-create
        STATUS  current
        DESCRIPTION
               ""
        ::= { certEntry 14 }

        certVersion OBJECT-TYPE
        SYNTAX  Integer32
        MAX-ACCESS  read-create
        STATUS  current
        DESCRIPTION
               ""
        ::= { certEntry 15 }

        certRowStatus OBJECT-TYPE
        SYNTAX  RowStatus 
        MAX-ACCESS  read-create
        STATUS  current
        DESCRIPTION
               ""
        ::= { certEntry 16 }

        -- the vlan  Group
        -- Contains the information about the vlan

        -- the vlan table
        vlanTable     OBJECT-TYPE
        SYNTAX   SEQUENCE OF VlanEntry
        MAX-ACCESS            not-accessible
        STATUS             current
        DESCRIPTION    "A list of vlan entries."
              ::= { vlan 1 }

        vlanEntry OBJECT-TYPE
        SYNTAX  VlanEntry
        MAX-ACCESS  not-accessible
        STATUS  current
        DESCRIPTION
             ""
        INDEX   { vlanRowId }
        ::= { vlanTable 1 }

        VlanEntry ::=
              SEQUENCE {
                  vlanRowId
                      Integer32,
                  vlanName
                      OCTET STRING,
                  vlanId
                      Integer32,
                  vlanNotes
                      DisplayString,
                  vlanRowStatus
                      RowStatus 
        }
        vlanRowId OBJECT-TYPE
        SYNTAX  Integer32(1..2147483647)
        MAX-ACCESS  not-accessible
        STATUS  current
        DESCRIPTION
               "Index"
        ::= { vlanEntry 1 }

        vlanName OBJECT-TYPE
        SYNTAX  OCTET STRING (SIZE(1..50)) 
        MAX-ACCESS  read-create
        STATUS  current
        DESCRIPTION
               "Unique name for this vlan"
        ::= { vlanEntry 2 }

        vlanId OBJECT-TYPE
        SYNTAX  Integer32 
        MAX-ACCESS  read-create
        STATUS  current
        DESCRIPTION
               ""
        ::= { vlanEntry 3 }

        vlanNotes OBJECT-TYPE
        SYNTAX  DisplayString 
        MAX-ACCESS  read-create
        STATUS  current
        DESCRIPTION
               "Notes"
        ::= { vlanEntry 4 }

        vlanRowStatus OBJECT-TYPE
        SYNTAX  RowStatus 
        MAX-ACCESS  read-create
        STATUS  current
        DESCRIPTION
               "The Row status attribute for row handling"
        ::= { vlanEntry 5 }
      
        -- the vlan group table

        vlanGrpTable OBJECT-TYPE
        SYNTAX          SEQUENCE OF VlanGrpEntry
        MAX-ACCESS          not-accessible
        STATUS          current
        DESCRIPTION    
              "To define the vlan groups."
              ::= { vlan 2 }

        vlanGrpEntry OBJECT-TYPE
        SYNTAX          VlanGrpEntry
        MAX-ACCESS          not-accessible
        STATUS          current
        DESCRIPTION
             ""
        INDEX   { vlanGrpId }
        ::= { vlanGrpTable 1 }

        VlanGrpEntry ::=
              SEQUENCE {
                  vlanGrpId
                      Integer32,
                  vlanGrpName
                      OCTET STRING,
                  vlanGrpRowStatus
                       RowStatus 
        }

        vlanGrpId OBJECT-TYPE
        SYNTAX  Integer32(1..2147483647)
        MAX-ACCESS  not-accessible
        STATUS  current
        DESCRIPTION

               "Table index"
        ::= { vlanGrpEntry 1 }


        vlanGrpName OBJECT-TYPE
        SYNTAX  OCTET STRING(SIZE(1..50))
        MAX-ACCESS  read-create
        STATUS  current
        DESCRIPTION
               "Unique name for every vlan group"
        ::= { vlanGrpEntry 2 }

        vlanGrpRowStatus OBJECT-TYPE
        SYNTAX  RowStatus 
        MAX-ACCESS  read-create
        STATUS  current
        DESCRIPTION
               "The Row status attribute for row handling"
        ::= { vlanGrpEntry 3 }

        -- the vlan group member table

        vlanGrpMemTable OBJECT-TYPE
        SYNTAX          SEQUENCE OF VlanGrpMemEntry
        MAX-ACCESS          not-accessible
        STATUS          current
        DESCRIPTION    
              "To define the vlan group member table."
              ::= { vlan 3 }

        vlanGrpMemEntry OBJECT-TYPE
        SYNTAX          VlanGrpMemEntry
        MAX-ACCESS          not-accessible
        STATUS          current
        DESCRIPTION
             ""
        INDEX   { vlanGrpId,vlanGrpMemId}
        ::= { vlanGrpMemTable 1 }

        VlanGrpMemEntry ::=
              SEQUENCE {
                  vlanGrpMemId
                      Integer32,
                  vlanGrpMemRowStatus
                       RowStatus 
        }

        vlanGrpMemId OBJECT-TYPE
        SYNTAX  Integer32(1..2147483647)
        MAX-ACCESS  not-accessible
        STATUS  current
        DESCRIPTION
               "Table index"
        ::= { vlanGrpMemEntry 1 }


        vlanGrpMemRowStatus OBJECT-TYPE
        SYNTAX  RowStatus 
        MAX-ACCESS  read-create
        STATUS  current
        DESCRIPTION
               "The Row status attribute for row handling"
        ::= { vlanGrpMemEntry 2 }


        -- the schedule  Group
        -- Contains the information about the schedule

        -- the sched table
        schedTable     OBJECT-TYPE
        SYNTAX   SEQUENCE OF SchedEntry
        MAX-ACCESS            not-accessible
        STATUS             current
        DESCRIPTION    "A list of schedule entries."
              ::= { schedule 1 }

        schedEntry OBJECT-TYPE
        SYNTAX  SchedEntry
        MAX-ACCESS  not-accessible
        STATUS  current
        DESCRIPTION
             "List of scheds"
        INDEX   { schedRowId }
        ::= { schedTable 1 }

        SchedEntry ::=
              SEQUENCE {
                  schedRowId
                      Integer32,
                  schedName
                      OCTET STRING,
                  schedAllDay
                      INTEGER,
                  schedEveryDay
                      INTEGER,
                  schedStartDateAndTime
                      LocalDateAndTime,
                  schedEndDateAndTime
                      LocalDateAndTime,
                  schedMonth
                      INTEGER,
                  schedWeekDay
                      INTEGER,
                  schedDayOfMonth
                      Integer32,
                  schedRowStatus
                      RowStatus 
        }
        schedRowId OBJECT-TYPE
        SYNTAX  Integer32(1..2147483647)
        MAX-ACCESS  not-accessible
        STATUS  current
        DESCRIPTION
               "Index"
        ::= { schedEntry 1 }


        schedName OBJECT-TYPE
        SYNTAX  OCTET STRING (SIZE(1..50)) 
        MAX-ACCESS  read-create
        STATUS  current
        DESCRIPTION
               "Unique name for this schedule"
        ::= { schedEntry 2 }

        schedAllDay OBJECT-TYPE
        SYNTAX  INTEGER {
                   disable(0),
                   enable(1)
                }
        MAX-ACCESS  read-create
        STATUS  current
        DESCRIPTION
               ""
        ::= { schedEntry 3 }

        schedEveryDay OBJECT-TYPE
        SYNTAX  INTEGER {
                   disable(0),
                   enable(1)
        }    
        MAX-ACCESS  read-create
        STATUS  current
        DESCRIPTION
               ""
        ::= { schedEntry 4 }

        schedStartDateAndTime OBJECT-TYPE
        SYNTAX  LocalDateAndTime 
        MAX-ACCESS  read-create
        STATUS  current
        DESCRIPTION
               ""
        ::= { schedEntry 5 }

        schedEndDateAndTime OBJECT-TYPE

        SYNTAX  LocalDateAndTime 
        MAX-ACCESS  read-create
        STATUS  current
        DESCRIPTION
               ""
        ::= { schedEntry 6 }

        schedMonth OBJECT-TYPE
        SYNTAX  INTEGER {
                 january(1),
                 february(2),
                 march(3),
                 april(4),
                 may(5),
                 june(6),
                 july(7),
                 august(8),
                 september(9),
                 october(10),
                 november(11),
                 december(12)
                 }    
        MAX-ACCESS  read-create
        STATUS  current
        DESCRIPTION
               ""
        ::= { schedEntry 7 }


        schedWeekDay OBJECT-TYPE
        SYNTAX  INTEGER {
                sunday(1),
                monday(2),
                tuesday(3),
                wednesday(4),
                thursday(5),
                friday(6),
                saturday(7)
                }    
        MAX-ACCESS  read-create
        STATUS  current
        DESCRIPTION
               ""
        ::= { schedEntry 8 }


        schedDayOfMonth OBJECT-TYPE
        SYNTAX  Integer32 
        MAX-ACCESS  read-create
        STATUS  current
        DESCRIPTION
               ""
        ::= { schedEntry 9 }

        schedRowStatus OBJECT-TYPE
        SYNTAX  RowStatus 
        MAX-ACCESS  read-create
        STATUS  current
        DESCRIPTION
               ""
        ::= { schedEntry 10 }

        -- the sched group table

        schedGrpTable OBJECT-TYPE
        SYNTAX          SEQUENCE OF SchedGrpEntry
        MAX-ACCESS          not-accessible
        STATUS          current
        DESCRIPTION    
              "To define the schedule groups."
              ::= { schedule 2 }

        schedGrpEntry OBJECT-TYPE
        SYNTAX          SchedGrpEntry
        MAX-ACCESS          not-accessible
        STATUS          current
        DESCRIPTION
             ""
        INDEX   { schedGrpId }
        ::= { schedGrpTable 1 }

        SchedGrpEntry ::=
              SEQUENCE {
                  schedGrpId
                      Integer32,
                  schedGrpName
                      OCTET STRING,
                  schedGrpRowStatus
                       RowStatus 
        }

        schedGrpId OBJECT-TYPE
        SYNTAX  Integer32(1..2147483647)
        MAX-ACCESS  not-accessible
        STATUS  current
        DESCRIPTION
               "Table index"
        ::= { schedGrpEntry 1 }


        schedGrpName OBJECT-TYPE
        SYNTAX  OCTET STRING(SIZE(1..50))
        MAX-ACCESS  read-create
        STATUS  current
        DESCRIPTION
               "Unique name for every sched group"
        ::= { schedGrpEntry 2 }

        schedGrpRowStatus OBJECT-TYPE
        SYNTAX  RowStatus 
        MAX-ACCESS  read-create
        STATUS  current
        DESCRIPTION
               "The Row status attribute for row handling"
        ::= { schedGrpEntry 3 }


        -- the sched group member table

        schedGrpMemTable OBJECT-TYPE
        SYNTAX          SEQUENCE OF SchedGrpMemEntry
        MAX-ACCESS          not-accessible
        STATUS          current
        DESCRIPTION    
              "To define the schedule group members"
              ::= { schedule 3 }

        schedGrpMemEntry OBJECT-TYPE
        SYNTAX          SchedGrpMemEntry
        MAX-ACCESS          not-accessible
        STATUS          current
        DESCRIPTION
             ""
        INDEX   { schedGrpId,schedGrpMemId}
        ::= { schedGrpMemTable 1 }

        SchedGrpMemEntry ::=
              SEQUENCE {
                  schedGrpMemId
                      Integer32,
                  schedGrpMemRowStatus
                       RowStatus 
        }

        schedGrpMemId OBJECT-TYPE
        SYNTAX  Integer32(1..2147483647)
        MAX-ACCESS  not-accessible
        STATUS  current
        DESCRIPTION
               "Table index"
        ::= { schedGrpMemEntry 1 }

        schedGrpMemRowStatus OBJECT-TYPE
        SYNTAX  RowStatus 
        MAX-ACCESS  read-create
        STATUS  current
        DESCRIPTION
               "The Row status attribute for row handling"
        ::= { schedGrpMemEntry 2 }

        -- the snmpTrapMgmt  Group
        -- Contains the information about the snmpTrapMgmt settings 

        -- the snmpTrapMgmt table
        snmpTrapMgmtTable     OBJECT-TYPE
        SYNTAX   SEQUENCE OF SnmpTrapMgmtEntry
        MAX-ACCESS            not-accessible
        STATUS             current
        DESCRIPTION    ""
              ::= { snmpTrapConf 1 }

        snmpTrapMgmtEntry OBJECT-TYPE
        SYNTAX  SnmpTrapMgmtEntry
        MAX-ACCESS  not-accessible
        STATUS  current
        DESCRIPTION
             "An snmpTrapMgmtEntry containing snmp client 
             ipaddress and the trap community string  for trap forwarding"
        INDEX   { snmpTrapMgmtId}
        ::= { snmpTrapMgmtTable 1 }
        SnmpTrapMgmtEntry ::=
              SEQUENCE {
                  snmpTrapMgmtId
                      Integer32,
                  snmpTrapMgmtIpAddress
                      BlueIpAddress,
                  snmpTrapMgmtCommunity
                      DisplayString,
                  snmpTrapMgmtRowStatus
                      RowStatus 
        }
        snmpTrapMgmtId OBJECT-TYPE
        SYNTAX  Integer32(1..2147483647)
        MAX-ACCESS  not-accessible 
        STATUS  current
        DESCRIPTION
               ""
        ::= { snmpTrapMgmtEntry 1 }

        snmpTrapMgmtIpAddress OBJECT-TYPE
        SYNTAX  BlueIpAddress
        MAX-ACCESS  read-create
        STATUS  current
        DESCRIPTION
               ""
        ::= { snmpTrapMgmtEntry 2 }

        snmpTrapMgmtCommunity OBJECT-TYPE
        SYNTAX  DisplayString 
        MAX-ACCESS  read-create
        STATUS  current
        DESCRIPTION
               ""
        ::= { snmpTrapMgmtEntry 3 }

        snmpTrapMgmtRowStatus OBJECT-TYPE
        SYNTAX  RowStatus 
        MAX-ACCESS  read-create
        STATUS  current
        DESCRIPTION
               "The Row status attribute for row handling"
        ::= { snmpTrapMgmtEntry 4 }

 
        -- the blueEvent  Group
        -- Contains the information about the blueEvent settings 

        -- the blueEvent table
        blueEventTable     OBJECT-TYPE
        SYNTAX   SEQUENCE OF BlueEventEntry
        MAX-ACCESS            not-accessible
        STATUS             current
        DESCRIPTION    ""
              ::= { snmpTrapConf 2 }

        blueEventEntry OBJECT-TYPE
        SYNTAX  BlueEventEntry
        MAX-ACCESS  not-accessible
        STATUS  current
        DESCRIPTION
             "To enable/disable traps"
        INDEX   { btId }
        ::= { blueEventTable 1 }
        BlueEventEntry ::=
              SEQUENCE {
                  btId
                      Integer32,
                  btName
                      DisplayString,
                  btEventOptStatus
                      INTEGER
        }

-- To enable or disable  traps        

        btId OBJECT-TYPE
        SYNTAX  Integer32(1..2147483647)
        MAX-ACCESS  not-accessible
        STATUS  current
        DESCRIPTION
               "Index"
        ::= { blueEventEntry 1 }

        btName OBJECT-TYPE
        SYNTAX  DisplayString 
        MAX-ACCESS  read-only
        STATUS  current
        DESCRIPTION
               "Trap name"
        ::= { blueEventEntry 2 }

        btEventOptStatus OBJECT-TYPE
        SYNTAX  INTEGER {
                   disable(0),
                   enable(1)
        }    
        MAX-ACCESS  read-write
        STATUS  current
        DESCRIPTION
               ""
        ::= { blueEventEntry 3 }

        -- the stThreshold  Group
        -- To set the threshold for the system performance 
        -- related attributes to log messages or to send traps
        -- or to failover  

        -- the stThreshold table
        stThresholdTable     OBJECT-TYPE
        SYNTAX   SEQUENCE OF StThresholdEntry
        MAX-ACCESS            not-accessible
        STATUS             current
        DESCRIPTION    ""
              ::= { systemTracker 1 }

        stThresholdEntry OBJECT-TYPE
        SYNTAX  StThresholdEntry
        MAX-ACCESS  not-accessible
        STATUS  current
        DESCRIPTION
             "To set threshold value for performance related
             attributes for sending traps and to predict the failover. 
             This is a static table and has entries for the following
             attributes.
             Average CPU usage
             High Memory Swap 
             High Disk Usage"
        INDEX   { stThresholdId}
        ::= { stThresholdTable 1 }
        StThresholdEntry ::=
              SEQUENCE {
                  stThresholdId
                      Integer32,
                  stThresholdAttrName
                      DisplayString,
                  stThresholdToLogMessage
                      Integer32,
                  stThresholdToSendTrap
                      Integer32,
                  stThresholdToFailover
                      Integer32
        }

        stThresholdId OBJECT-TYPE
        SYNTAX  Integer32(1..2147483647)
        MAX-ACCESS  not-accessible 
        STATUS  current
        DESCRIPTION
               ""
        ::= { stThresholdEntry 1 }

        stThresholdAttrName OBJECT-TYPE
        SYNTAX  DisplayString 
        MAX-ACCESS  read-only
        STATUS  current
        DESCRIPTION
               "The name of the attribute"
        ::= { stThresholdEntry 2 }


        stThresholdToLogMessage OBJECT-TYPE
        SYNTAX  Integer32 
        MAX-ACCESS  read-create
        STATUS  current
        DESCRIPTION
               "Threshold for logging messages"
        ::= { stThresholdEntry 3 }

        stThresholdToSendTrap OBJECT-TYPE
        SYNTAX  Integer32 
        MAX-ACCESS  read-create
        STATUS  current
        DESCRIPTION
               "Threshold for sending snmp traps"
        ::= { stThresholdEntry 4 }

        stThresholdToFailover OBJECT-TYPE
        SYNTAX  Integer32 
        MAX-ACCESS  read-create
        STATUS  current
        DESCRIPTION
               "Threshold for system failover"
        ::= { stThresholdEntry 5 }

-- Notification group
-- notifyObjects group

        ntyobjLevel OBJECT-TYPE
        SYNTAX  OCTET STRING(SIZE(1..20))
        MAX-ACCESS  accessible-for-notify
        STATUS  current
        DESCRIPTION
               "Event priority or log level."
        ::= { notifyObjects 1}

        ntyobjName OBJECT-TYPE
        SYNTAX  OCTET STRING(SIZE(1..255))
        MAX-ACCESS  accessible-for-notify
        STATUS  current
        DESCRIPTION
             "The name of the object that triggered the event.
              In case of no objects assosicated with
              failures, the value will be NULL.  "
                ::= { notifyObjects 2 }

        ntyobjDesc OBJECT-TYPE
        SYNTAX  OCTET STRING(SIZE(0..512))
        MAX-ACCESS  accessible-for-notify
        STATUS  current
        DESCRIPTION
             "Description about event/trap"
        ::= { notifyObjects 3 }

        ntyobjOID OBJECT-TYPE
        SYNTAX  OBJECT IDENTIFIER
        MAX-ACCESS  accessible-for-notify
        STATUS  current
        DESCRIPTION
             "The OID of the object that triggered the event"
        ::= { notifyObjects 4 }

        ntyobjValue OBJECT-TYPE
        SYNTAX  OCTET STRING(SIZE(0..255))
        MAX-ACCESS  accessible-for-notify
        STATUS  current
        DESCRIPTION
             "The value of the object that triggered
              the event at the time of event occurrence"
        ::= { notifyObjects 5 }


-- blueGeneralTraps group

    blueGeneralTraps0 OBJECT IDENTIFIER ::= { blueGeneralTraps 0 }

    btLinkUp NOTIFICATION-TYPE
    OBJECTS { ntyobjLevel,ntyobjName,ntyobjDesc}
    STATUS  current
    DESCRIPTION
            "Link up trap.
             ntyobjLevel   - Indicate the priority or log level
             ntyobjObjName - The name of the object that triggered the event
             ntyobjDesc    - Description about the event/trap 
             "
    ::= { blueGeneralTraps0 1 }

    btLinkDown NOTIFICATION-TYPE
    OBJECTS { ntyobjLevel,ntyobjName,ntyobjDesc}
    STATUS  current
    DESCRIPTION
            "Link down trap. 
             "
    ::= { blueGeneralTraps0 2 }

    btSystemGeneralTrap NOTIFICATION-TYPE
    OBJECTS { ntyobjLevel,ntyobjName,ntyobjDesc}
    STATUS  current
    DESCRIPTION
            "System status trap. 
             ntyobjLevel   - Indicate the priority or log level
             ntyobjObjName - The name of the object that triggered the event
             ntyobjDesc    - Description about the event/trap 
             "
    ::= { blueGeneralTraps0 3 }

-- configChangeTraps group

    blueConfigTraps0 OBJECT IDENTIFIER ::= { blueConfigTraps 0 }

    cctSystemConfChange NOTIFICATION-TYPE
    OBJECTS { ntyobjLevel,ntyobjName,ntyobjDesc}

    STATUS  current
    DESCRIPTION
            "This trap will be sent on any system level Configuration
            changes. 
             ntyobjLevel   - Indicate the priority or log level
             ntyobjObjName - The name of the object that triggered the event
             ntyobjDesc    - Description about the event/trap 
             "
    ::= { blueConfigTraps0 1 }

    cctUserConfChange NOTIFICATION-TYPE
    OBJECTS { ntyobjLevel,ntyobjName,ntyobjDesc}
    STATUS  current
    DESCRIPTION
            "User configuration change trap. 
             ntyobjLevel   - Indicate the priority or log level
             ntyobjObjName - The name of the object that triggered the event
             ntyobjDesc    - Description about the event/trap 
             "
    ::= { blueConfigTraps0 2 }


    cctExternalServConfChange NOTIFICATION-TYPE
    OBJECTS { ntyobjLevel,ntyobjName,ntyobjDesc}
    STATUS  current
    DESCRIPTION
            "External configuration change trap. 
             ntyobjLevel   - Indicate the priority or log level
             ntyobjObjName - The name of the object that triggered the event
             ntyobjDesc    - Description about the event/trap 
             "
    ::= { blueConfigTraps0 3 }

    cctRoleConfChange NOTIFICATION-TYPE
    OBJECTS { ntyobjLevel,ntyobjName,ntyobjDesc}
    STATUS  current
    DESCRIPTION
            "Role configuration changes. 
             ntyobjLevel   - Indicate the priority or log level
             ntyobjObjName - The name of the object that triggered the event
             ntyobjDesc    - Description about the event/trap 
             "
    ::= { blueConfigTraps0 4 }

    cctDestinationConfChange NOTIFICATION-TYPE
    OBJECTS { ntyobjLevel,ntyobjName,ntyobjDesc}
    STATUS  current
    DESCRIPTION
            "Destination configuration changes. 
             ntyobjLevel   - Indicate the priority or log level
             ntyobjObjName - The name of the object that triggered the event
             ntyobjDesc    - Description about the event/trap 
             "
    ::= { blueConfigTraps0 5 }



    cctServiceConfChange NOTIFICATION-TYPE
    OBJECTS { ntyobjLevel,ntyobjName,ntyobjDesc}
    STATUS  current
    DESCRIPTION
            "Service configuration change traps. 
             ntyobjLevel   - Indicate the priority or log level
             ntyobjObjName - The name of the object that triggered the event
             ntyobjDesc    - Description about the event/trap 
             "
    ::= { blueConfigTraps0 6 }


    cctNetworkConfChange NOTIFICATION-TYPE
    OBJECTS { ntyobjLevel,ntyobjName,ntyobjDesc}
    STATUS  current
    DESCRIPTION
            "Network configuration change trap. 
             ntyobjLevel   - Indicate the priority or log level
             ntyobjObjName - The name of the object that triggered the event
             ntyobjDesc    - Description about the event/trap 
             "
    ::= { blueConfigTraps0 7 }


    cctVpnConfChange NOTIFICATION-TYPE
    OBJECTS { ntyobjLevel,ntyobjName,ntyobjDesc}
    STATUS  current
    DESCRIPTION
            "VPN Configuration change trap. 
             ntyobjLevel   - Indicate the priority or log level
             ntyobjObjName - The name of the object that triggered the event
             ntyobjDesc    - Description about the event/trap 
             "
    ::= { blueConfigTraps0 8 }

    cctMobilityConfChange NOTIFICATION-TYPE
    OBJECTS { ntyobjLevel,ntyobjName,ntyobjDesc}
    STATUS  current
    DESCRIPTION
            "Mobility configuration change trap. 
             ntyobjLevel   - Indicate the priority or log level
             ntyobjObjName - The name of the object that triggered the event
             ntyobjDesc    - Description about the event/trap 
             "
    ::= { blueConfigTraps0 9 }

    cctProcessConfChange NOTIFICATION-TYPE
    OBJECTS { ntyobjLevel,ntyobjName,ntyobjDesc}
    STATUS  current
    DESCRIPTION
            "Process configuration change trap. 
             ntyobjLevel   - Indicate the priority or log level
             ntyobjObjName - The name of the object that triggered the event
             ntyobjDesc    - Description about the event/trap 
             "
    ::= { blueConfigTraps0 10 }

--FailureTraps group

    blueFailureTraps0 OBJECT IDENTIFIER ::= { blueFailureTraps 0 }

    btSysGeneralFailure  NOTIFICATION-TYPE
    OBJECTS { ntyobjLevel,ntyobjName,ntyobjDesc}
    STATUS  current
    DESCRIPTION
            "System failure trap. 
             ntyobjLevel   - Indicate the priority or log level
             ntyobjObjName - The name of the object that triggered the event.
                         In case of no objects assosicated with
                         failures, the value will be NULL.
             
             ntyobjDesc    - Description about the event/trap 
             "
    ::= { blueFailureTraps0 1 }

    btUserLoginFailure  NOTIFICATION-TYPE
    OBJECTS { ntyobjLevel,ntyobjName,ntyobjDesc}
    STATUS  current
    DESCRIPTION
            "User login failure trap. 
             ntyobjLevel   - Indicate the priority or log level
             ntyobjObjName - The name of the object that triggered the event.
                         In case of no objects assosicated with
                         failures, the value will be NULL.
             
             ntyobjDesc    - Description about the event/trap 
             "
    ::= { blueFailureTraps0 2 }

    btProcessFailure  NOTIFICATION-TYPE
    OBJECTS { ntyobjLevel,ntyobjName,ntyobjDesc}
    STATUS  current
    DESCRIPTION

            "Process failure trap. 
             ntyobjLevel   - Indicate the priority or log level
             ntyobjObjName - The name of the object that triggered the event.
                         In case of no objects assosicated with
                         failures, the value will be NULL.
             
             ntyobjDesc    - Description about the event/trap 
             "
    ::= { blueFailureTraps0 3 }

    btAuthFailure  NOTIFICATION-TYPE
    OBJECTS { ntyobjLevel,ntyobjName,ntyobjDesc}
    STATUS  current
    DESCRIPTION
            " Authentication failure trap. 
             ntyobjLevel   - Indicate the priority or log level
             ntyobjObjName - The name of the object that triggered the event.
                         In case of no objects assosicated with
                         failures, the value will be NULL.
             ntyobjDesc    - Description about the event/trap 
             "
    ::= { blueFailureTraps0 4 }

    btSystemFailover  NOTIFICATION-TYPE
    OBJECTS { ntyobjLevel,ntyobjName,ntyobjDesc}
    STATUS  current
    DESCRIPTION
            "This trap will be sent on system failover. 
             ntyobjObjName - The name of the object that triggered the event.
                         In case of no objects assosicated with
                         failures, the value will be NULL.
             ntyobjDesc    - Description about the event/trap 
             "
    ::= { blueFailureTraps0 5 }

--blueThresholdTraps group

    blueThresholdTraps0 OBJECT IDENTIFIER ::= { blueThresholdTraps 0 }


    btConditionalEvent NOTIFICATION-TYPE
    OBJECTS { ntyobjLevel,ntyobjOID,ntyobjValue,ntyobjDesc}
    STATUS  current
    DESCRIPTION
            "This trap will be sent if the threshold have been met for
            the underlaying Object. 
             ntyobjLevel    - Indicate the trap priority or log level
             ntyobjObjOID  - The OID of the object that triggered the event
             ntyobjObjValue - The value of the object that triggered
                          the event at the time of event occurrence.
             trDesc     - Description about the event/trap 
             "

    ::= { blueThresholdTraps0 1 }

    btCpuLoadEvent NOTIFICATION-TYPE
    OBJECTS { ntyobjLevel,ntyobjOID,ntyobjValue,ntyobjDesc}
    STATUS  current
    DESCRIPTION
            "This trap will be sent if the threshold have been met for
            the CPU usage. 
             ntyobjLevel    - Indicate the trap priority or log level
             ntyobjObjOID  - The OID of the object that triggered the event
             ntyobjObjValue - The value of the object that triggered
                          the event at the time of event occurrence.
             trDesc     - Description about the event/trap 
             "
    ::= { blueThresholdTraps0 2 }
    btMemSwapUsageEvent NOTIFICATION-TYPE
    OBJECTS { ntyobjLevel,ntyobjOID,ntyobjValue,ntyobjDesc}
    STATUS  current
    DESCRIPTION
            "This trap will be sent if the threshold have been met for
            the memory or swap space. 
             ntyobjLevel    - Indicate the trap priority or log level
             ntyobjObjOID  - The OID of the object that triggered the event
             ntyobjObjValue - The value of the object that triggered
                          the event at the time of event occurrence.
             trDesc     - Description about the event/trap 
             "
    ::= { blueThresholdTraps0 3 }

    btDiskUsageEvent NOTIFICATION-TYPE
    OBJECTS { ntyobjLevel,ntyobjOID,ntyobjValue,ntyobjDesc}
    STATUS  current
    DESCRIPTION
            "This trap will be sent if the threshold have been met for
            the Disk usage Object. 
             ntyobjLevel    - Indicate the trap priority or log level
             ntyobjObjOID  - The OID of the object that triggered the event
             ntyobjObjValue - The value of the object that triggered
                          the event at the time of event occurrence.
             trDesc     - Description about the event/trap 
             "
    ::= { blueThresholdTraps0 4 }
  END
