-- ***********************************************
-- PAN-PRODUCT-MIB.my
--
-- MIB for the platform specific MIB objects implemented by
-- Palo Alto devices.
-- ***********************************************

PAN-PRODUCTS-MIB DEFINITIONS ::= BEGIN

	IMPORTS
		MODULE-IDENTITY, OBJECT-IDENTITY,
		OBJECT-TYPE, NOTIFICATION-TYPE,
		Integer32
			FROM SNMPv2-SMI
--		MODULE-COMPLIANCE, OBJECT-GROUP
--			FROM SNMPv2-CONF
		DisplayString, TruthValue
			FROM SNMPv2-TC
		TcChassisType
			FROM PAN-GLOBAL-TC
		panModules, panProductsMibs
			FROM PAN-GLOBAL-REG;

	panProductsMibsModule MODULE-IDENTITY
		LAST-UPDATED			"201304151650Z"
		ORGANIZATION			"Palo Alto Networks"
		CONTACT-INFO			"
					Customer Support
					Palo Alto Networks
					4401 Great America Pkwy
					Santa Clara, CA 95054-1211

					+1 866-898-9087
					support at paloaltonetworks dot com"

		DESCRIPTION				"
			A MIB module containing definitions of managed objects
			implemented by specific Palo Alto Networks' products."

		REVISION				"201304151650Z"
		DESCRIPTION				"
			Rev 2.0
			Updated with PA-7000, GP-100 and WF-500 products."
		REVISION				"201102091610Z"
		DESCRIPTION				"
			Rev 1.0
			Initial version of MIB module PAN-PRODUCTS-MIB."

		::= { panModules 4 }

	panPA-4050 OBJECT-IDENTITY
		STATUS					current
		DESCRIPTION				"
			Sub-tree for PA-4050 specific objects."
		::= { panProductsMibs 1 }

	panPA-4020 OBJECT-IDENTITY
		STATUS					current
		DESCRIPTION				"
			Sub-tree for PA-4020 specific objects."
		::= { panProductsMibs 2 }

	panPA-2050 OBJECT-IDENTITY
		STATUS					current
		DESCRIPTION				"
			Sub-tree for PA-2050 specific objects."
		::= { panProductsMibs 3 }

	panPA-2020 OBJECT-IDENTITY
		STATUS					current
		DESCRIPTION				"
			Sub-tree for PA-2020 specific objects."
		::= { panProductsMibs 4 }

	panPA-4060 OBJECT-IDENTITY
		STATUS					current
		DESCRIPTION				"
			Sub-tree for PA-4060 specific objects."
		::= { panProductsMibs 5 }

	panPA-500 OBJECT-IDENTITY
		STATUS					current
		DESCRIPTION				"
			Sub-tree for PA-500 specific objects."
		::= { panProductsMibs 6 }

	panPanorama OBJECT-IDENTITY
		STATUS					current
		DESCRIPTION				"
			Sub-tree for Panorama specific objects."
		::= { panProductsMibs 7 }

	panPA-5060 OBJECT-IDENTITY
		STATUS					current
		DESCRIPTION				"
			Sub-tree for PA-5060 specific objects."
		::= { panProductsMibs 8 }

	panPA-5050 OBJECT-IDENTITY
		STATUS					current
		DESCRIPTION				"
			Sub-tree for PA-5050 specific objects."
		::= { panProductsMibs 9 }

	panPA-5020 OBJECT-IDENTITY
		STATUS					current
		DESCRIPTION				"
			Sub-tree for PA-5020 specific objects."
		::= { panProductsMibs 11 }

	panPA-200 OBJECT-IDENTITY
		STATUS					current
		DESCRIPTION				"
			Sub-tree for PA-200 specific objects."
		::= { panProductsMibs 12 }

	panPA-3050 OBJECT-IDENTITY
		STATUS					current
		DESCRIPTION				"
			Sub-tree for PA-3050 specific objects."
		::= { panProductsMibs 17 }

	panPA-3020 OBJECT-IDENTITY
		STATUS					current
		DESCRIPTION				"
			Sub-tree for PA-3020 specific objects."
		::= { panProductsMibs 18 }

	panPA-3060 OBJECT-IDENTITY
		STATUS					current
		DESCRIPTION				"
			Sub-tree for PA-3060 specific objects."
		::= { panProductsMibs 19 }

    panPA-3200 OBJECT-IDENTITY
        STATUS					current
        DESCRIPTION				"
            Sub-tree for PA-3200 specific objects."
        ::= { panProductsMibs 20 }

    panPA-3250 OBJECT-IDENTITY
        STATUS					current
        DESCRIPTION				"
            Sub-tree for PA-3250 specific objects."
        ::= { panProductsMibs 21 }

	panPA-5260 OBJECT-IDENTITY
		STATUS					current
		DESCRIPTION				"
			Sub-tree for PA-5260 specific objects."
		::= { panProductsMibs 22 }

	panPA-5250 OBJECT-IDENTITY
		STATUS					current
		DESCRIPTION				"
			Sub-tree for PA-5250 specific objects."
		::= { panProductsMibs 23 }

	panPA-5220 OBJECT-IDENTITY
		STATUS					current
		DESCRIPTION				"
			Sub-tree for PA-5220 specific objects."
		::= { panProductsMibs 24 }


	panPA-VM OBJECT-IDENTITY
		STATUS					current
		DESCRIPTION				"
			Sub-tree for PA-VM specific objects."
		::= { panProductsMibs 29 }

	panM-100 OBJECT-IDENTITY
		STATUS					current
		DESCRIPTION				"
			Sub-tree for M-100 specific objects."
		::= { panProductsMibs 30 }
	
	panPA-7050 OBJECT-IDENTITY
		STATUS					current
		DESCRIPTION				"
			Sub-tree for PA-7050 specific objects."
		::= { panProductsMibs 31 }

	panGP-100 OBJECT-IDENTITY
		STATUS					current
		DESCRIPTION				"
			Sub-tree for GP-100 specific objects."
		::= { panProductsMibs 32 }

	panWF-500 OBJECT-IDENTITY
		STATUS					current
		DESCRIPTION				"
			Sub-tree for WF-500 specific objects."
		::= { panProductsMibs 33 }

	panPA-7080 OBJECT-IDENTITY
		STATUS					current
		DESCRIPTION				"
			Sub-tree for PA-7080 specific objects."
		::= { panProductsMibs 34 }

	panM-500 OBJECT-IDENTITY
		STATUS					current
		DESCRIPTION				"
			Sub-tree for M-500 specific objects."
		::= { panProductsMibs 35 }
		
	panPA-820 OBJECT-IDENTITY
		STATUS					current
		DESCRIPTION				"
			Sub-tree for PA-820 specific objects."
		::= { panProductsMibs 36 }

	panPA-850 OBJECT-IDENTITY
		STATUS					current
		DESCRIPTION				"
			Sub-tree for PA-850 specific objects."
		::= { panProductsMibs 37 }

	panPA-220 OBJECT-IDENTITY
		STATUS					current
		DESCRIPTION				"
			Sub-tree for PA-220 specific objects."
		::= { panProductsMibs 38 }

	panM-600 OBJECT-IDENTITY
		STATUS					current
		DESCRIPTION				"
			Sub-tree for M-600 specific objects."
		::= { panProductsMibs 39 }
	
	panM-200 OBJECT-IDENTITY
		STATUS					current
		DESCRIPTION				"
			Sub-tree for M-200 specific objects."
		::= { panProductsMibs 40 }

	panPA-220R OBJECT-IDENTITY
		STATUS					current
		DESCRIPTION				"
			Sub-tree for PA-220R specific objects."
		::= { panProductsMibs 41 }
		
        panPA-5280 OBJECT-IDENTITY
                STATUS					current
                DESCRIPTION				"
                       Sub-tree for PA-5280 specific objects."
                ::= { panProductsMibs 42 }
     panPA-3220 OBJECT-IDENTITY
        STATUS                  current
        DESCRIPTION             "
            Sub-tree for PA-3220 specific objects."
        ::= { panProductsMibs 43 }
    
    panPA-3260 OBJECT-IDENTITY
       STATUS                  current
       DESCRIPTION             "
           Sub-tree for PA-3260 specific objects."
       ::= { panProductsMibs 44 }

	panWF-600 OBJECT-IDENTITY
		STATUS					current
		DESCRIPTION				"
			Sub-tree for WF-600 specific objects."
		::= { panProductsMibs 45 }

	panPA-220-ZTP OBJECT-IDENTITY
		STATUS					current
		DESCRIPTION				"
			Sub-tree for PA-220-ZTP specific objects."
		::= { panProductsMibs 46 }
		
	panPA-220R-ZTP OBJECT-IDENTITY
		STATUS					current
		DESCRIPTION				"
			Sub-tree for PA-220R-ZTP specific objects."
		::= { panProductsMibs 47 }
		
	panPA-820-ZTP OBJECT-IDENTITY
		STATUS					current
		DESCRIPTION				"
			Sub-tree for PA-820-ZTP specific objects."
		::= { panProductsMibs 48 }
		
	panPA-850-ZTP OBJECT-IDENTITY
		STATUS					current
		DESCRIPTION				"
			Sub-tree for PA-850-ZTP specific objects."
		::= { panProductsMibs 49 }
		
    panPA-3250-ZTP OBJECT-IDENTITY
        STATUS					current
        DESCRIPTION				"
            Sub-tree for PA-3250-ZTP specific objects."
        ::= { panProductsMibs 50 }

    panPA-3220-ZTP OBJECT-IDENTITY
        STATUS                  current
        DESCRIPTION             "
            Sub-tree for PA-3220-ZTP specific objects."
        ::= { panProductsMibs 51 }
    
    panPA-3260-ZTP OBJECT-IDENTITY
       STATUS                  current
       DESCRIPTION             "
           Sub-tree for PA-3260-ZTP specific objects."
        ::= { panProductsMibs 52 }

    panPA-410 OBJECT-IDENTITY
       STATUS                  current
       DESCRIPTION             "
           Sub-tree for PA-410 specific objects."
        ::= { panProductsMibs 53 }

    panPA-440 OBJECT-IDENTITY
       STATUS                  current
       DESCRIPTION             "
           Sub-tree for PA-440 specific objects."
        ::= { panProductsMibs 54 }

    panPA-450 OBJECT-IDENTITY
       STATUS                  current
       DESCRIPTION             "
           Sub-tree for PA-450 specific objects."
        ::= { panProductsMibs 55 }

    panPA-460 OBJECT-IDENTITY
       STATUS                  current
       DESCRIPTION             "
           Sub-tree for PA-460 specific objects."
        ::= { panProductsMibs 56 }

    panPA-5450 OBJECT-IDENTITY
       STATUS                  current
       DESCRIPTION             "
           Sub-tree for PA-5450 specific objects."
        ::= { panProductsMibs 57 }
    
    panM-300 OBJECT-IDENTITY
       STATUS		       current
       DESCRIPTION	       "
	   Sub-tree for M-300 specific objects."
	::= { panProductsMibs 58 }
    
    panM-700 OBJECT-IDENTITY
       STATUS		       current
       DESCRIPTION	       "
	   Sub-tree for M-700 specific objects."
	::= { panProductsMibs 59 }
    
    panWF-500-B OBJECT-IDENTITY
       STATUS		       current
       DESCRIPTION	       "
	   Sub-tree for WF-500-B specific objects."
	::= { panProductsMibs 60 }

    panPA-3410 OBJECT-IDENTITY
       STATUS                  current
       DESCRIPTION             "
           Sub-tree for PA-3410 specific objects."
        ::= { panProductsMibs 61 }

    panPA-3420 OBJECT-IDENTITY
       STATUS                  current
       DESCRIPTION             "
           Sub-tree for PA-3420 specific objects."
        ::= { panProductsMibs 62 }

    panPA-3430 OBJECT-IDENTITY
       STATUS                  current
       DESCRIPTION             "
           Sub-tree for PA-3430 specific objects."
        ::= { panProductsMibs 63 }

    panPA-3440 OBJECT-IDENTITY
       STATUS                  current
       DESCRIPTION             "
           Sub-tree for PA-3440 specific objects."
        ::= { panProductsMibs 64 }

    panPA-5410 OBJECT-IDENTITY
       STATUS                  current
       DESCRIPTION             "
           Sub-tree for PA-5410 specific objects."
        ::= { panProductsMibs 65 }

    panPA-5420 OBJECT-IDENTITY
       STATUS                  current
       DESCRIPTION             "
           Sub-tree for PA-5420 specific objects."
        ::= { panProductsMibs 66 }

    panPA-5430 OBJECT-IDENTITY
       STATUS                  current
       DESCRIPTION             "
           Sub-tree for PA-5430 specific objects."
        ::= { panProductsMibs 67 }

	panProcessingCards OBJECT-IDENTITY
		STATUS					current
		DESCRIPTION				"
			Sub-tree for Processing line card specific objects."
		::= { panProductsMibs 100 }

	panFans OBJECT-IDENTITY
		STATUS					current
		DESCRIPTION				"
			Sub-tree for Fan specific objects."
		::= { panProductsMibs 101 }

	panPowerSupplies OBJECT-IDENTITY
		STATUS					current
		DESCRIPTION				"
			Sub-tree for Power supply specific objects."
		::= { panProductsMibs 102 }

-- Processing line cards

	panPA-7000-SMC OBJECT-IDENTITY
		STATUS					current
		DESCRIPTION				"
			PA-7000 series Switch management card."
		::= { panProcessingCards 1 }

	panPA-7000-LPC OBJECT-IDENTITY
		STATUS					current
		DESCRIPTION				"
			PA-7000 series Log Processing card."
		::= { panProcessingCards 2 }

	panPA-7000-20G-NPC OBJECT-IDENTITY
		STATUS					current
		DESCRIPTION				"
			PA-7000 series 20G Network Processing card."
		::= { panProcessingCards 3 }

	panPA-7080-SMC OBJECT-IDENTITY
		STATUS					current
		DESCRIPTION				"
			PA-7080 Switch management card."
		::= { panProcessingCards 4 }

	panPA-7050-SMC-B OBJECT-IDENTITY
		STATUS					current
		DESCRIPTION				"
			PA-7050 Bennu Switch management card."
		::= { panProcessingCards 5 }

	panPA-7000-LFC-A OBJECT-IDENTITY
		STATUS					current
		DESCRIPTION				"
			PA-7000 series Log Forwarding card."
		::= { panProcessingCards 6 }

	panPA-7000-100G-NPC-A OBJECT-IDENTITY
		STATUS					current
		DESCRIPTION				"
			PA-7000 series 100G Network Processing card."
		::= { panProcessingCards 7 }

	panPA-7080-SMC-B OBJECT-IDENTITY
		STATUS					current
		DESCRIPTION				"
			PA-7080 Bennu Switch management card."
		::= { panProcessingCards 8 }

	panPA-7000-DPC-A OBJECT-IDENTITY
		STATUS					current
		DESCRIPTION				"
			PA-7000 series Data Processing card, 4 CPUs."
		::= { panProcessingCards 9 }

	panPA-5450-NC-A OBJECT-IDENTITY
		STATUS					current
		DESCRIPTION				"
			PA-5450 Network card."
		::= { panProcessingCards 10 }

	panPA-5450-DPC-A OBJECT-IDENTITY
		STATUS					current
		DESCRIPTION				"
			PA-5450 Data Processing card."
		::= { panProcessingCards 11 }

	panPA-5450-MPC-A OBJECT-IDENTITY
		STATUS					current
		DESCRIPTION				"
			PA-5450 Management card."
		::= { panProcessingCards 12 }
END
