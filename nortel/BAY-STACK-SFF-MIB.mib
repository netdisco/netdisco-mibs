BAY-STACK-SFF-MIB DEFINITIONS ::= BEGIN

IMPORTS
    OBJECT-TYPE, MODULE-IDENTITY, Integer32
        FROM SNMPv2-SMI
    InterfaceIndex
        FROM IF-MIB
    bayStackMibs
        FROM SYNOPTICS-ROOT-MIB;

bayStackDdiSfpMib MODULE-IDENTITY
    LAST-UPDATED    "201206050000Z"
    ORGANIZATION    "Avaya"
    CONTACT-INFO    "Avaya"
    DESCRIPTION
        "Avaya SFF MIB

         Copyright 2012 Avaya, Inc.
         All rights reserved.
         This Avaya SNMP Management Information Base
         Specification embodies Avaya's confidential and
         proprietary intellectual property. Avaya retains
         all title and ownership in the Specification, including any
         revisions.

         This Specification is supplied 'AS IS,' and Avaya
         makes no warranty, either express or implied, as to the use,
         operation, condition, or performance of the Specification."

    REVISION "201206050000Z" --  5 June 2012
    DESCRIPTION "v2: Added DDI SFP threshold reached traps."

    REVISION "200806030000Z" -- 03 June 2008
    DESCRIPTION "v1:  Initial version."

    ::= { bayStackMibs 29 }

bsDdiSfpNotifications OBJECT IDENTIFIER ::= { bayStackDdiSfpMib 0 }
bsDdiSfpObjects       OBJECT IDENTIFIER ::= { bayStackDdiSfpMib 1 }

-- -------------------------------------------------------------
-- Textual Conventions
-- -------------------------------------------------------------

-- -------------------------------------------------------------
-- Scalar Objects
-- -------------------------------------------------------------

-- -------------------------------------------------------------
-- SFF Table
-- -------------------------------------------------------------

bsDdiSfpTable OBJECT-TYPE
    SYNTAX SEQUENCE OF BsDdiSfpEntry
    MAX-ACCESS not-accessible
    STATUS current
    DESCRIPTION
        "This table contains information about DDI SFPs.  Entries will
        exist in this table only for DDI SFP ports."
    ::= { bsDdiSfpObjects 2 }

bsDdiSfpEntry OBJECT-TYPE
    SYNTAX BsDdiSfpEntry
    MAX-ACCESS not-accessible
    STATUS current
    DESCRIPTION
        "SFF interface settings."
    INDEX { bsDdiSfpIfIndex }
    ::= { bsDdiSfpTable 1 }

BsDdiSfpEntry ::=
    SEQUENCE {
        bsDdiSfpIfIndex                    InterfaceIndex,
        bsDdiSfpCalibration                INTEGER,
        bsDdiSfpRxPowerMeasurement         INTEGER,
        bsDdiSfpTempValue                  Integer32,
        bsDdiSfpTempLowAlarmThreshold      Integer32,
        bsDdiSfpTempLowWarnThreshold       Integer32,
        bsDdiSfpTempHighAlarmThreshold     Integer32,
        bsDdiSfpTempHighWarnThreshold      Integer32,
        bsDdiSfpVoltageValue               Integer32,
        bsDdiSfpVoltageLowAlarmThreshold   Integer32,
        bsDdiSfpVoltageLowWarnThreshold    Integer32,
        bsDdiSfpVoltageHighAlarmThreshold  Integer32,
        bsDdiSfpVoltageHighWarnThreshold   Integer32,
        bsDdiSfpBiasValue                  Integer32,
        bsDdiSfpBiasLowAlarmThreshold      Integer32,
        bsDdiSfpBiasLowWarnThreshold       Integer32,
        bsDdiSfpBiasHighAlarmThreshold     Integer32,
        bsDdiSfpBiasHighWarnThreshold      Integer32,
        bsDdiSfpTxPowerValue               Integer32,
        bsDdiSfpTxPowerLowAlarmThreshold   Integer32,
        bsDdiSfpTxPowerLowWarnThreshold    Integer32,
        bsDdiSfpTxPowerHighAlarmThreshold  Integer32,
        bsDdiSfpTxPowerHighWarnThreshold   Integer32,
        bsDdiSfpRxPowerValue               Integer32,
        bsDdiSfpRxPowerLowAlarmThreshold   Integer32,
        bsDdiSfpRxPowerLowWarnThreshold    Integer32,
        bsDdiSfpRxPowerHighAlarmThreshold  Integer32,
        bsDdiSfpRxPowerHighWarnThreshold   Integer32
    }

bsDdiSfpIfIndex OBJECT-TYPE
    SYNTAX      InterfaceIndex
    MAX-ACCESS  not-accessible
    STATUS      current
    DESCRIPTION "Identifies the ifIndex of the SFF port."
    ::= { bsDdiSfpEntry 1 }
 
bsDdiSfpCalibration OBJECT-TYPE
    SYNTAX      INTEGER {
                    internal(1),
                    external(2)
                }
    MAX-ACCESS  read-only
    STATUS      current
    DESCRIPTION
        "This object indicates whether the actual values read from EEPROM
        internally within an implementation are already calibrated to the
        appropriate units (Volts, mA, dB, etc), or whether these values
        are first converted to appropriate units.  The value external(2)
        indicates that the values as read from EEPROM must be converted.
        Note that this is only an indication of what happens internally
        within an implementation, and does not have any effect on the
        values of other columns in this table."
    ::= { bsDdiSfpEntry 2 }
 
bsDdiSfpRxPowerMeasurement OBJECT-TYPE
    SYNTAX      INTEGER {
                    oma(1),
                    averagePower(2)
                }
    MAX-ACCESS  read-only
    STATUS      current
    DESCRIPTION
        "This object indicates the measurement type used for the received
        power.  A value of oma(1) indicates Optical Modulation Amplitude
        (OMA)."
    ::= { bsDdiSfpEntry 3 }
 
bsDdiSfpTempValue OBJECT-TYPE
    SYNTAX      Integer32 (-1280000..1280000)
    MAX-ACCESS  read-only
    STATUS      current
    DESCRIPTION
        "The actual temperature value, measured in 1/10000 Celsius."
    ::= { bsDdiSfpEntry 4 }
 
bsDdiSfpTempLowAlarmThreshold OBJECT-TYPE
    SYNTAX      Integer32 (-1280000..1280000)
    MAX-ACCESS  read-only
    STATUS      current
    DESCRIPTION
        "The low alarm temperature threshold, measure in 1/10000 Celsius."
    ::= { bsDdiSfpEntry 5 }
 
bsDdiSfpTempLowWarnThreshold OBJECT-TYPE
    SYNTAX      Integer32 (-1280000..1280000)
    MAX-ACCESS  read-only
    STATUS      current
    DESCRIPTION
        "The low warn temperature threshold, measure in 1/10000 Celsius."
    ::= { bsDdiSfpEntry 6 }
 
bsDdiSfpTempHighAlarmThreshold OBJECT-TYPE
    SYNTAX      Integer32 (-1280000..1280000)
    MAX-ACCESS  read-only
    STATUS      current
    DESCRIPTION
        "The high alarm temperature threshold, measure in 1/10000 Celsius."
    ::= { bsDdiSfpEntry 7 }
 
bsDdiSfpTempHighWarnThreshold OBJECT-TYPE
    SYNTAX      Integer32 (-1280000..1280000)
    MAX-ACCESS  read-only
    STATUS      current
    DESCRIPTION
        "The high warn temperature threshold, measure in 1/10000 Celsius."
    ::= { bsDdiSfpEntry 8 }
 
bsDdiSfpVoltageValue OBJECT-TYPE
    SYNTAX      Integer32 (0..65500)
    MAX-ACCESS  read-only
    STATUS      current
    DESCRIPTION
        "The actual voltage value, measured in 1/10000 volts."
    ::= { bsDdiSfpEntry 9 }
 
bsDdiSfpVoltageLowAlarmThreshold OBJECT-TYPE
    SYNTAX      Integer32 (0..65500)
    MAX-ACCESS  read-only
    STATUS      current
    DESCRIPTION
        "The low alarm voltage threshold, measured in 1/10000 volts."
    ::= { bsDdiSfpEntry 10 }
 
bsDdiSfpVoltageLowWarnThreshold OBJECT-TYPE
    SYNTAX      Integer32 (0..65500)
    MAX-ACCESS  read-only
    STATUS      current
    DESCRIPTION
        "The low warn voltage threshold, measured in 1/10000 volts."
    ::= { bsDdiSfpEntry 11 }
 
bsDdiSfpVoltageHighAlarmThreshold OBJECT-TYPE
    SYNTAX      Integer32 (0..65500)
    MAX-ACCESS  read-only
    STATUS      current
    DESCRIPTION
        "The high alarm voltage threshold, measured in 1/10000 volts."
    ::= { bsDdiSfpEntry 12 }
 
bsDdiSfpVoltageHighWarnThreshold OBJECT-TYPE
    SYNTAX      Integer32 (0..65500)
    MAX-ACCESS  read-only
    STATUS      current
    DESCRIPTION
        "The high warn voltage threshold, measured in 1/10000 volts."
    ::= { bsDdiSfpEntry 13 }
 
bsDdiSfpBiasValue OBJECT-TYPE
    SYNTAX      Integer32 (0..1280000)
    MAX-ACCESS  read-only
    STATUS      current
    DESCRIPTION
        "The actual bias value, measured in 1/10000 mA."
    ::= { bsDdiSfpEntry 14 }
 
bsDdiSfpBiasLowAlarmThreshold OBJECT-TYPE
    SYNTAX      Integer32 (0..1280000)
    MAX-ACCESS  read-only
    STATUS      current
    DESCRIPTION
        "The low alarm bias threshold, measured in 1/10000 mA."
    ::= { bsDdiSfpEntry 15 }
 
bsDdiSfpBiasLowWarnThreshold OBJECT-TYPE
    SYNTAX      Integer32 (0..1280000)
    MAX-ACCESS  read-only
    STATUS      current
    DESCRIPTION
        "The low warn bias threshold, measured in 1/10000 mA."
    ::= { bsDdiSfpEntry 16 }
 
bsDdiSfpBiasHighAlarmThreshold OBJECT-TYPE
    SYNTAX      Integer32 (0..1280000)
    MAX-ACCESS  read-only
    STATUS      current
    DESCRIPTION
        "The high alarm bias threshold, measured in 1/10000 mA."
    ::= { bsDdiSfpEntry 17 }
 
bsDdiSfpBiasHighWarnThreshold OBJECT-TYPE
    SYNTAX      Integer32 (0..1280000)
    MAX-ACCESS  read-only
    STATUS      current
    DESCRIPTION
        "The high warn bias threshold, measured in 1/10000 mA."
    ::= { bsDdiSfpEntry 18 }
 
bsDdiSfpTxPowerValue OBJECT-TYPE
    SYNTAX      Integer32 (-400000..83000)
    MAX-ACCESS  read-only
    STATUS      current
    DESCRIPTION
        "The actual transmit power value, measured in 1/10000 dBm."
    ::= { bsDdiSfpEntry 19 }
 
bsDdiSfpTxPowerLowAlarmThreshold OBJECT-TYPE
    SYNTAX      Integer32 (-400000..83000)
    MAX-ACCESS  read-only
    STATUS      current
    DESCRIPTION
        "The low alarm transmit power threshold, measured in 1/10000 dBm."
    ::= { bsDdiSfpEntry 20 }
 
bsDdiSfpTxPowerLowWarnThreshold OBJECT-TYPE
    SYNTAX      Integer32 (-400000..83000)
    MAX-ACCESS  read-only
    STATUS      current
    DESCRIPTION
        "The low warn transmit power threshold, measured in 1/10000 dBm."
    ::= { bsDdiSfpEntry 21 }
 
bsDdiSfpTxPowerHighAlarmThreshold OBJECT-TYPE
    SYNTAX      Integer32 (-400000..83000)
    MAX-ACCESS  read-only
    STATUS      current
    DESCRIPTION
        "The high alarm transmit power threshold, measured in 1/10000 dBm."
    ::= { bsDdiSfpEntry 22 }
 
bsDdiSfpTxPowerHighWarnThreshold OBJECT-TYPE
    SYNTAX      Integer32 (-400000..83000)
    MAX-ACCESS  read-only
    STATUS      current
    DESCRIPTION
        "The high warn transmit power threshold, measured in 1/10000 dBm."
    ::= { bsDdiSfpEntry 23 }
 
bsDdiSfpRxPowerValue OBJECT-TYPE
    SYNTAX      Integer32 (-400000..83000)
    MAX-ACCESS  read-only
    STATUS      current
    DESCRIPTION
        "The actual receive power value, measured in 1/10000 dBm."
    ::= { bsDdiSfpEntry 24 }
 
bsDdiSfpRxPowerLowAlarmThreshold OBJECT-TYPE
    SYNTAX      Integer32 (-400000..83000)
    MAX-ACCESS  read-only
    STATUS      current
    DESCRIPTION
        "The low alarm receive power threshold, measured in 1/10000 dBm."
    ::= { bsDdiSfpEntry 25 }
 
bsDdiSfpRxPowerLowWarnThreshold OBJECT-TYPE
    SYNTAX      Integer32 (-400000..83000)
    MAX-ACCESS  read-only
    STATUS      current
    DESCRIPTION
        "The low warn receive power threshold, measured in 1/10000 dBm."
    ::= { bsDdiSfpEntry 26 }
 
bsDdiSfpRxPowerHighAlarmThreshold OBJECT-TYPE
    SYNTAX      Integer32 (-400000..83000)
    MAX-ACCESS  read-only
    STATUS      current
    DESCRIPTION
        "The high alarm receive power threshold, measured in 1/10000 dBm."
    ::= { bsDdiSfpEntry 27 }
 
bsDdiSfpRxPowerHighWarnThreshold OBJECT-TYPE
    SYNTAX      Integer32 (-400000..83000)
    MAX-ACCESS  read-only
    STATUS      current
    DESCRIPTION
        "The high warn receive power threshold, measured in 1/10000 dBm."
    ::= { bsDdiSfpEntry 28 }

-- -------------------------------------------------------------
-- Notifications
-- -------------------------------------------------------------

bsDdiSfpTempAlarm NOTIFICATION-TYPE
     OBJECTS {
                 bsDdiSfpTempValue
             }
     STATUS      current
     DESCRIPTION
         "This notification is generated when a transceiver's temperature reaches an alarm level."
     ::= { bsDdiSfpNotifications 1 }

bsDdiSfpTempWarn NOTIFICATION-TYPE
     OBJECTS {
                 bsDdiSfpTempValue
             }
     STATUS      current
     DESCRIPTION
         "This notification is generated when a transceiver's temperature reaches a warning level."
     ::= { bsDdiSfpNotifications 2 }

bsDdiSfpTempNormal NOTIFICATION-TYPE
     OBJECTS {
                 bsDdiSfpTempValue
             }
     STATUS      current
     DESCRIPTION
         "This notification is generated when a transceiver's temperature reaches normal operating level.
          The notification is triggered after the transceiver's temperature has reached a warning or alarm
          level and then returns to normal level."
     ::= { bsDdiSfpNotifications 3 }

bsDdiSfpVoltageAlarm NOTIFICATION-TYPE
     OBJECTS {
                 bsDdiSfpVoltageValue
             }
     STATUS      current
     DESCRIPTION
         "This notification is generated when a transceiver's voltage reaches an alarm level."
     ::= { bsDdiSfpNotifications 4 }

bsDdiSfpVoltageWarn NOTIFICATION-TYPE
     OBJECTS {
                 bsDdiSfpVoltageValue
             }
     STATUS      current
     DESCRIPTION
         "This notification is generated when a transceiver's voltage reaches a warning level."
     ::= { bsDdiSfpNotifications 5 }

bsDdiSfpVoltageNormal NOTIFICATION-TYPE
     OBJECTS {
                 bsDdiSfpVoltageValue
             }
     STATUS      current
     DESCRIPTION
         "This notification is generated when a transceiver's voltage reaches normal operating level.
          The notification is triggered after the transceiver's voltage has reached a warning or alarm
          level and then returns to normal level."
     ::= { bsDdiSfpNotifications 6 }

bsDdiSfpBiasAlarm NOTIFICATION-TYPE
     OBJECTS {
                 bsDdiSfpBiasValue
             }
     STATUS      current
     DESCRIPTION
         "This notification is generated when a transceiver's bias reaches an alarm level."
     ::= { bsDdiSfpNotifications 7 }

bsDdiSfpBiasWarn NOTIFICATION-TYPE
     OBJECTS {
                 bsDdiSfpBiasValue
             }
     STATUS      current
     DESCRIPTION
         "This notification is generated when a transceiver's bias reaches a warning level."
     ::= { bsDdiSfpNotifications 8 }

bsDdiSfpBiasNormal NOTIFICATION-TYPE
     OBJECTS {
                 bsDdiSfpBiasValue
             }
     STATUS      current
     DESCRIPTION
         "This notification is generated when a transceiver's bias reaches normal operating level.
          The notification is triggered after the transceiver's bias has reached a warning or alarm
          level and then returns to normal level."
     ::= { bsDdiSfpNotifications 9 }

bsDdiSfpTxAlarm NOTIFICATION-TYPE
     OBJECTS {
                 bsDdiSfpTxPowerValue
             }
     STATUS      current
     DESCRIPTION
         "This notification is generated when a transceiver's transmit power reaches an alarm level."
     ::= { bsDdiSfpNotifications 10 }

bsDdiSfpTxWarn NOTIFICATION-TYPE
     OBJECTS {
                 bsDdiSfpTxPowerValue
             }
     STATUS      current
     DESCRIPTION
         "This notification is generated when a transceiver's transmit power reaches a warning level."
     ::= { bsDdiSfpNotifications 11 }

bsDdiSfpTxNormal NOTIFICATION-TYPE
     OBJECTS {
                 bsDdiSfpTxPowerValue
             }
     STATUS      current
     DESCRIPTION
         "This notification is generated when a transceiver's transmit power reaches normal operating level.
          The notification is triggered after the transceiver's transmit power has reached a warning or alarm
          level and then returns to normal level."
     ::= { bsDdiSfpNotifications 12 }

bsDdiSfpRxAlarm NOTIFICATION-TYPE
     OBJECTS {
                 bsDdiSfpRxPowerValue
             }
     STATUS      current
     DESCRIPTION
         "This notification is generated when a transceiver's receive power reaches an alarm level."
     ::= { bsDdiSfpNotifications 13 }

bsDdiSfpRxWarn NOTIFICATION-TYPE
     OBJECTS {
                 bsDdiSfpRxPowerValue
             }
     STATUS      current
     DESCRIPTION
         "This notification is generated when a transceiver's receive power reaches a warning level."
     ::= { bsDdiSfpNotifications 14 }

bsDdiSfpRxNormal NOTIFICATION-TYPE
     OBJECTS {
                 bsDdiSfpRxPowerValue
             }
     STATUS      current
     DESCRIPTION
         "This notification is generated when a transceiver's receive power reaches normal operating level.
          The notification is triggered after the transceiver's receive power has reached a warning or alarm
          level and then returns to normal level."
     ::= { bsDdiSfpNotifications 15 }

END
