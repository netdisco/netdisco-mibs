BAY-STACK-LLDP-EXT-DOT3-MIB DEFINITIONS ::= BEGIN

IMPORTS
    MODULE-IDENTITY, OBJECT-TYPE, Integer32
        FROM SNMPv2-SMI
    lldpXdot3LocPowerEntry, lldpXdot3RemPowerEntry
        FROM LLDP-EXT-DOT3-MIB
    bayStackMibs
        FROM SYNOPTICS-ROOT-MIB;

bayStackLldpXDot3Mib MODULE-IDENTITY
    LAST-UPDATED "201410220000Z"
    ORGANIZATION "Avaya Inc."
    CONTACT-INFO "avaya.com"
    DESCRIPTION
        "This MIB module is an extension to the standard LLDP-EXT-DOT3 MIB."

    REVISION    "201410220000Z"  -- October 22, 2014
    DESCRIPTION "Ver 1:  Initial version."

    ::= { bayStackMibs 47 }

bsLldpXDot3Notifications OBJECT IDENTIFIER ::= { bayStackLldpXDot3Mib 0 }
bsLldpXDot3Objects       OBJECT IDENTIFIER ::= { bayStackLldpXDot3Mib 1 }

bsLldpXdot3Config     OBJECT IDENTIFIER ::= { bsLldpXDot3Objects 1 } 
bsLldpXdot3LocalData  OBJECT IDENTIFIER ::= { bsLldpXDot3Objects 2 } 
bsLldpXdot3RemoteData OBJECT IDENTIFIER ::= { bsLldpXDot3Objects 3 } 

-- 
-- *********************************************************** 
-- 
-- Textual Conventions
-- 
-- *********************************************************** 


-- ===========================================================================
-- bsLldpXdot3LocPowerTable
-- ===========================================================================

bsLldpXdot3LocPowerTable OBJECT-TYPE 
    SYNTAX      SEQUENCE OF BsLldpXdot3LocPowerEntry 
    MAX-ACCESS  not-accessible 
    STATUS      current 
    DESCRIPTION 
        "This table contains one row per port of PSE PoE
        information on the local system known to this agent."
    ::= { bsLldpXdot3LocalData 1 } 

bsLldpXdot3LocPowerEntry OBJECT-TYPE 
    SYNTAX      BsLldpXdot3LocPowerEntry 
    MAX-ACCESS  not-accessible 
    STATUS      current 
    DESCRIPTION 
        "Information about a particular port PoE information."
    AUGMENTS { lldpXdot3LocPowerEntry } 
    ::= { bsLldpXdot3LocPowerTable 1 } 

BsLldpXdot3LocPowerEntry ::= SEQUENCE { 
      bsLldpXdot3LocPowerType              INTEGER, 
      bsLldpXdot3LocPowerSource            INTEGER, 
      bsLldpXdot3LocPowerPriority          INTEGER, 
      bsLldpXdot3LocPDRequestedPowerValue  Integer32, 
      bsLldpXdot3LocPSEAllocatedPowerValue Integer32 
}

bsLldpXdot3LocPowerType OBJECT-TYPE
    SYNTAX      INTEGER {
                    type2pse(1),
                    type2pd(2),
                    type1pse(3),
                    type1pd(4)
                }
    MAX-ACCESS  read-only
    STATUS      current
    DESCRIPTION
        "A GET attribute that returns whether the local system is a PSE or
        a PD and whether it is Type 1 or Type 2."
    REFERENCE
        "802.3at, Section 30.12.2"
    ::= { bsLldpXdot3LocPowerEntry 1 }

bsLldpXdot3LocPowerSource OBJECT-TYPE
    SYNTAX      INTEGER {
                    unknown(1),
                    primaryPs(2),
                    backupPs(3),
                    reserved(4)
                }
    MAX-ACCESS  read-only
    STATUS      current
    DESCRIPTION
        "A GET attribute indicating the PSE Power Sources of the local system.
        A PSE indicates whether it is being powered by a primary power
        source; a backup power source; or unknown.

        A value primaryPs(2) indicates that the device advertises its power source
        as primary.

        A value backupPs(3) indicates that the device advertises its power source
        as backup."
    REFERENCE
        "802.3at, Section 30.12.2"
    ::= { bsLldpXdot3LocPowerEntry 2 }

bsLldpXdot3LocPowerPriority OBJECT-TYPE
    SYNTAX      INTEGER  {
                    unknown(1),
                    critical(2),
                    high(3),
                    low(4)
                }
    MAX-ACCESS  read-only
    STATUS      current
    DESCRIPTION
        "Reflects the PD power priority that is being advertised on this
        PSE port.

        If both locally configure priority and
        ldpXMedRemXPoEPDPowerPriority are available on this port, it is
        a matter of local policy which one takes precedence. This object
        reflects the active value on this port.

        If the priority is not configured or known by the PD, the value
        unknown(1) will be returned.

        A value critical(2) indicates that the device advertises its power
        Priority as critical, as per RFC 3621.

        A value high(3) indicates that the device advertises its power
        Priority as high, as per RFC 3621.

        A value low(4) indicates that the device advertises its power
        Priority as low, as per RFC 3621."
    REFERENCE
        "802.3at, Section 30.12.2"
    ::= { bsLldpXdot3LocPowerEntry 3 }

bsLldpXdot3LocPDRequestedPowerValue OBJECT-TYPE
    SYNTAX      Integer32 (1..255)
    UNITS      "tenth of watt"
    MAX-ACCESS  read-only
    STATUS      current
    DESCRIPTION
        "A GET attribute that returns the PD requested power value. For a PSE,
        it is the power value that the PSE mirrors back to the remote system.
        This is the PD requested power value that was used by the PSE to
        compute the power it has currently allocated to the remote system.
        It is expressed in units of 0.1 watts."
    REFERENCE
        "802.3at, Section 30.12.2"
    ::= { bsLldpXdot3LocPowerEntry 4 }

bsLldpXdot3LocPSEAllocatedPowerValue OBJECT-TYPE
    SYNTAX      Integer32 (1..255)
    UNITS      "tenth of watt"
    MAX-ACCESS  read-only
    STATUS      current
    DESCRIPTION
        "A GET attribute that returns the PSE allocated power value. For a PSE,
        it is the power value that the PSE has currently allocated to the
        remote system. The PSE allocated power value is the  maximum input
        average power that the PSE wants the PD to ever draw under this
        allocation if it is accepted. It is expressed in units of 0.1 watts."
    REFERENCE
        "802.3at, Section 30.12.2"
    ::= { bsLldpXdot3LocPowerEntry 5 }

-- ===========================================================================
-- bsLldpXdot3RemPowerTable
-- ===========================================================================

bsLldpXdot3RemPowerTable OBJECT-TYPE 
    SYNTAX      SEQUENCE OF BsLldpXdot3RemPowerEntry 
    MAX-ACCESS  not-accessible 
    STATUS      current 
    DESCRIPTION 
        "This table contains information about the PoE device type
        as advertised by the remote system."
    ::= { bsLldpXdot3RemoteData 1 } 

bsLldpXdot3RemPowerEntry OBJECT-TYPE 
    SYNTAX      BsLldpXdot3RemPowerEntry 
    MAX-ACCESS  not-accessible 
    STATUS      current 
    DESCRIPTION 
            "Information about a particular port component." 
    AUGMENTS { lldpXdot3RemPowerEntry } 
    ::= { bsLldpXdot3RemPowerTable 1 } 

BsLldpXdot3RemPowerEntry ::= SEQUENCE { 
      bsLldpXdot3RemPowerType              INTEGER, 
      bsLldpXdot3RemPowerSource            INTEGER, 
      bsLldpXdot3RemPowerPriority          INTEGER, 
      bsLldpXdot3RemPDRequestedPowerValue  Integer32, 
      bsLldpXdot3RemPSEAllocatedPowerValue Integer32 
}

bsLldpXdot3RemPowerType OBJECT-TYPE
    SYNTAX      INTEGER {
                    type2pse(1),
                    type2pd(2),
                    type1pse(3),
                    type1pd(4)
                }
    MAX-ACCESS  read-only
    STATUS      current
    DESCRIPTION
        "A GET attribute that returns whether the remote system is a PSE
        or a PD and whether it is Type 1 or Type 2."
    REFERENCE
        "802.3at, Section 30.12.3"
    ::= { bsLldpXdot3RemPowerEntry 1 }

bsLldpXdot3RemPowerSource OBJECT-TYPE
    SYNTAX      INTEGER {
                    unknown(1),
                    pse(2),
                    reserved(3),
                    pseAndLocal(4)
                }
    MAX-ACCESS  read-only
    STATUS      current
    DESCRIPTION
        "A GET attribute that returns the power sources of the remote system.
        When the remote system is a PD, it indicates whether it is being
        powered by: a PSE and locall; locally only; by a PSE only; or unknown."
    REFERENCE
        "802.3at, Section 30.12.3"
    ::= { bsLldpXdot3RemPowerEntry 2 }

bsLldpXdot3RemPowerPriority OBJECT-TYPE
    SYNTAX      INTEGER  {
                    unknown(1),
                    critical(2),
                    high(3),
                    low(4)
                }
    MAX-ACCESS  read-only
    STATUS      current
    DESCRIPTION
        "A GET operation returns the priority of the PD system received from
        the remote system. For a PD, this is the priority that the remote
        system has assigned to the PD."
    REFERENCE
        "802.3at, Section 30.12.3"
    ::= { bsLldpXdot3RemPowerEntry 3 }

bsLldpXdot3RemPDRequestedPowerValue OBJECT-TYPE
    SYNTAX      Integer32 (1..255)
    UNITS      "tenth of watt"
    MAX-ACCESS  read-only
    STATUS      current
    DESCRIPTION
        "A GET attribute that for a PSE returs the the PD requested power value
        received from the remote system. It is expressed in units of 0.1 watts."
    REFERENCE
        "802.3at, Section 30.12.3"
    ::= { bsLldpXdot3RemPowerEntry 4 }

bsLldpXdot3RemPSEAllocatedPowerValue OBJECT-TYPE
    SYNTAX      Integer32 (1..255)
    UNITS      "tenth of watt"
    MAX-ACCESS  read-only
    STATUS      current
    DESCRIPTION
        "A GET attribute that for a PSE returns the PSE allocated power value
        that was used by the remote system to compute the power value that it
        has currently requested from the PSE. It is expressed in units of
        0.1 watts."
    REFERENCE
        "802.3at, Section 30.12.3"
    ::= { bsLldpXdot3RemPowerEntry 5 }

END
