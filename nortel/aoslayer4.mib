-- COPYRIGHT NOTICE
-- Copyright (c) Nortel Networks, 2004
-- All rights reserved
-- 
-- HISTORY
-- $Log$
-- Revision submit_cheetah_20297/1 2006/05/02 06:02:15 rvakkala
-- Fixed conflicting registration because of merging.
-- 
-- Revision submit_cheetah_19277/2 2006/05/02 04:44:13 rvakkala
-- Fixed CRQ01007809 Added lack of mibs support to SNMP.
-- 
-- Revision submit_cheetah_20213/1 2006/04/27 05:36:38 rvakkala
-- Corrected misspelled slbPortSyamntecState.
-- 
-- Revision submit_cheetah_18044/2 2006/04/26 04:24:55 rvakkala
-- Fixed CRQ01191419, Added Mib support for /i/sl/port, /i/sl/se/sslport.
-- 
-- Revision submit_cheetah_19277/1 2006/05/02 04:34:10 rvakkala
-- Fixed CRQ01007809 Added lack of mibs support to SNMP.
-- 
-- Revision submit_cheetah_18659/1 2006/03/08 07:55:14 bfrancis
-- .Fixed - AAS/Wrong behavior with L7 persistency when receiving corrupted TCP checksum
-- 
-- Revision submit_cheetah_18044/1 2006/04/26 04:15:04 rvakkala
-- Fixed CRQ01191419, Added Mib support for /i/sl/port, /i/sl/se/sslport.
-- 
-- Revision submit_cheetah_16973/1 2006/01/27 23:29:03 angamuth
-- Support for Symantec statistics
-- 
-- Revision submit_cheetah_16727/2 2006/01/23 05:08:30 rvakkala
-- Fixed Q01269377 SLB Sess Attack Alert Allowable Limit is 1-2097104 but
-- should be 2097100 and Q01272370 Service range under Buddy Server should
-- be 9-65534 not 14-65534.
-- 
-- Revision submit_cheetah_16636/1 2006/01/10 04:51:54 rvakkala
-- Ported connection pooling support from 23.0 branch
-- and chaged value of gslbNewCfgRuleDelete to 9.
-- 
-- Revision submit_cheetah_16727/1 2006/01/23 04:54:22 rvakkala
-- Fixed Q01269377 SLB Sess Attack Alert Allowable Limit is 1-2097104 but
-- should be 2097100 and Q01272370 Service range under Buddy Server should
-- be 9-65534 not 14-65534
-- 
-- Revision submit_cheetah_16378/1 2005/12/06 15:29:30 rramana
-- CR Q01226413: WebUI/SNMP support for invalid_fins counter.
-- 
-- Revision submit_cheetah_16281/1 2005/11/30 16:32:32 coman
-- Ported #16159 from the elmo branch
-- 
-- Revision submit_cheetah_16214/1 2005/11/29 11:20:46 drosu
-- Ported gslbCurCfgRuleDname and gslbNewCfgRuleDname from elmo branch.
-- 
-- Revision submit_cheetah_16175/1 2005/11/25 13:09:35 drosu
-- Added gslbCurCfgRuleDname and gslbNewCfgRuleDname leaves in
-- gslbCurCfgRuleTable/gslbNewCfgRuleTable.
-- 
-- Revision submit_cheetah_16159/1 2005/11/24 14:35:53 coman
-- Fix for GSLB resource record range
-- 
-- Revision submit_cheetah_14778/1 2005/10/04 13:35:59 dillibab
-- Added group info. to real server rport information table.
-- 
-- Revision submit_cheetah_14320/1 2005/09/09 19:36:04 angamuth
-- Moved SymantecState from SLB port table to Security port table.
-- 
-- Revision submit_cheetah_13952/1 2005/08/25 14:59:29 rvakkala
-- Revised earlier fix of 1187524 Should allow prefix range 0-128.
-- 
-- Revision submit_cheetah_13760/1 2005/08/12 21:12:33 jamesob
-- CR Q01131953-01 :  Correct mib range for vports.
-- 
-- Revision submit_cheetah_13703/1 2005/08/10 23:36:11 rrekha
-- Fixed build error.
-- 
-- Revision submit_cheetah_13653/1 2005/08/10 20:58:25 rrekha
-- Fixed Cougar build errors.
-- 
-- Revision submit_cheetah_13572/2 2005/08/10 10:51:34 rvakkala
-- Added MIB support for /stats/slb/virt<x>/ vipaddress.
-- 
-- Revision submit_cheetah_13608/2 2005/08/10 10:37:04 rvakkala
-- Fixed CR Q01187524: Should allow prefix range as 0-128 for ipv6.
-- 
-- Revision submit_cheetah_13635/1 2005/08/10 05:46:14 rrekha
-- Converted excludes in Makefile to #if defines in the *.raw and *.ctl files.
-- 
-- Revision submit_cheetah_13563/1 2005/08/05 17:39:20 rrekha
-- Moved all the BWM related flags into the raw files.
-- 
-- Revision submit_cheetah_13608/1 2005/08/10 10:24:58 rvakkala
-- Fixed CRQ01187524 Should accept prefix as 0-128 for ipv6.
-- 
-- Revision submit_cheetah_13572/1 2005/08/10 10:41:34 rvakkala
-- ADDED MIB support for /stats/slb/virt<x>/ vipaddress
-- 
-- Revision submit_cheetah_13198/2 2005/08/03 10:02:51 rvakkala
-- Fixed CR Q01156936.
-- 
-- Revision submit_cheetah_13244/1 2005/07/25 20:54:16 rrekha
-- Fixed Q01179203: slbNewCfgWlmIpAddr/slbNewCfgWlmPort should be read-create
-- variables.
-- 
-- Revision submit_cheetah_13198/1 2005/08/03 09:34:02 rvakkala
-- Fixed CR1156936 Set health check script number greater than 16.
-- 
-- Revision submit_cheetah_12855/2 2005/07/13 09:36:51 angamuth
-- Merged with previous changes.
-- 
-- Revision submit_cheetah_12614/1 2005/07/08 13:11:55 rvakkala
-- Added MIBs for SNMP support for IPV6 slb statistics.
-- 
-- Revision submit_cheetah_12904/2 2005/07/02 06:51:26 dillibab
-- Merged with previous changes.
-- 
-- Revision submit_cheetah_12735/1 2005/06/29 13:58:22 rvakkala
-- Added range for prefix length of filter sprefix,dprefix.
-- 
-- Revision submit_cheetah_12904/1 2005/07/02 05:37:39 dillibab
-- Fixed Q01128664; Modified the range of virtual service port as
-- per CLI(14..65534).
-- 
-- Revision submit_cheetah_12855/1 2005/07/13 09:16:44 angamuth
-- Added a MIB variable for /c/slb/port x/symantec ena/dis command.
-- 
-- Revision submit_cheetah_12565/1 2005/06/16 13:18:58 rvakkala
-- Added IPv6 objects for filter and virtual server configuration.
-- 
-- Revision submit_cheetah_12226/2 2005/06/08 09:36:47 rvakkala
-- Changed SNMP support for Buddy Server as per changes done in CLI.
-- 
-- Revision submit_cheetah_12479/1 2005/06/06 10:37:52 rvakkala
-- Corrected spelling error in session mirror stats.
-- 
-- Revision submit_cheetah_12407/1 2005/05/27 18:35:29 jbuswell
-- Q01123065: Added support for Africa as GSLB Region, newly established.
-- 
-- Revision submit_cheetah_12113/3 2005/05/25 10:35:21 rvakkala
-- Added MIB support for Media Portal Nat.
-- 
-- Revision submit_cheetah_12217/2 2005/05/25 10:00:17 rvakkala
-- Added MIB support for RTSP enhancement.
-- 
-- Revision submit_cheetah_12268/1 2005/05/25 09:04:46 rvakkala
-- Added MIB support for session mirror statistics
-- 
-- Revision submit_cheetah_12113/2 2005/05/25 10:30:16 rvakkala
-- Added MIB support for Media Portal Nat
-- 
-- Revision submit_cheetah_12163/2 2005/05/20 05:20:10 rvakkala
-- Added MIB support for session mirror statistics.
-- 
-- Revision submit_cheetah_12226/1 2005/06/08 09:24:07 rvakkala
-- Changed SNMP support for Buddy server as per changes done in CLI.
-- 
-- Revision submit_cheetah_12114/2 2005/05/18 09:50:29 rvakkala
-- Added MIB support for session mirroring.
-- 
-- Revision submit_cheetah_12217/1 2005/05/25 09:50:18 rvakkala
-- Added MIB support for RTSP enhancement.
-- 
-- Revision submit_cheetah_12159/1 2005/05/17 09:09:43 rvakkala
-- Added  MIB support for /c/slb/virt<x>/service rtsp/softgrid
-- 
-- Revision submit_cheetah_12163/1 2005/05/20 05:11:38 rvakkala
-- Added MIBS for session mirror statistics.
-- 
-- Revision submit_cheetah_12113/1 2005/05/25 10:10:45 rvakkala
-- Added MIB support for Media Portal Nat.
-- 
-- Revision submit_cheetah_11834/1 2005/05/12 09:50:20 rvakkala
-- Added MIBs for buddy servers.
-- 
-- Revision submit_cheetah_12114/1 2005/05/18 09:34:50 rvakkala
-- Added MIB support for session mirroring
-- 
-- Revision submit_cheetah_11747/2 2005/04/29 05:40:39 rvakkala
-- Changed the range to allow user the configured service timeout value to be 0.
-- 
-- Revision submit_cheetah_11792/1 2005/04/28 00:46:18 ravi
-- Added SNMP code for Backup Server Enhancement
-- 
-- Revision submit_cheetah_11747/1 2005/04/29 04:26:42 rvakkala
-- Changed the MIB range to allow user the configured service timeout value to be 0.
-- 
-- Revision submit_cheetah_11630/2 2005/04/23 10:43:51 hponnuru
-- Merged with previous changes.
-- 
-- Revision submit_cheetah_11567/2 2005/04/19 13:05:40 rvakkala
-- Added mib variables for Virtual Service Timeout
-- 
-- Revision submit_cheetah_11619/1 2005/04/18 18:31:10 yatsze
-- Clean up GSLB mib objects
-- 
-- Revision submit_cheetah_11527/1 2005/04/18 14:00:36 dillibab
-- Fixed build error came due to submit # 11502
-- 
-- Revision submit_cheetah_11502/2 2005/04/18 05:54:20 rvakkala
-- Added SNMP support for cfg/slb/filt<x>/adv/layer7/sip
-- 
-- Revision submit_cheetah_11630/1 2005/04/23 10:28:14 hponnuru
-- Added MIB variables for VmaSport.
-- 
-- Revision submit_cheetah_11404/2 2005/04/13 08:22:13 hponnuru
-- Added SNMP support for /c/slb/filt #/adv/security/parsechn
-- 
-- Revision submit_cheetah_11530/1 2005/04/12 12:37:48 rvakkala
-- Fixed build error in Elmo build.
-- 
-- Revision submit_cheetah_11404/1 2005/04/13 06:17:18 hponnuru
-- Added SNMP support for /c/slb/filt #/adv/security/parsechn.
-- 
-- Revision submit_cheetah_11502/1 2005/04/18 05:33:17 rvakkala
-- Added mib variables for SIP NAT
-- 
-- Revision submit_cheetah_11567/1 2005/04/19 06:02:19 rvakkala
-- Added mib variables forVirtual Service Timeout
-- 
-- Revision submit_cheetah_11406/1 2005/04/12 08:52:42 rvakkala
-- added MIB variables for WLM
-- 
-- Revision submit_cheetah_11367/1 2005/03/31 20:50:50 yatsze
-- Add stats for threshold exceeded
-- 
-- Revision submit_cheetah_11302/1 2005/03/25 21:31:57 yuhuang
-- Q00985537: Added wts to the health check type list.
-- 
-- Revision submit_cheetah_11273/1 2005/03/23 21:54:59 yatsze
-- Add gslbCurCfgGenNoResp and gslbNewCfgGenNoResp
-- 
-- Revision submit_cheetah_11186/1 2005/03/15 02:46:59 rrekha
-- Remove the following flags from Makefile and added to the *.raw
-- files : WLM_SASP, SLB_SIP, X_FORWARDED_FOR, SLB_PBIND_CIP_NORPORT,
-- SLB_PORT_BIND
-- 
-- Revision submit_cheetah_11111/1 2005/03/07 11:54:17 dillibab
-- Corrected valid range specification as per CLI for Time Window
-- and Hold Down duration for rate limiting.
-- 
-- Revision submit_cheetah_11093/2 2005/03/03 01:20:30 rrekha
-- merged out.
-- 
-- Revision submit_cheetah_11078/2 2005/03/02 21:50:50 yuhuang
-- Merged with submit 11025
-- 
-- Revision submit_cheetah_11078/1 2005/03/02 21:37:42 yuhuang
-- Q00930992: Added mib objects for subdmac command for the feature
-- pattern match redir filter.
-- 
-- Revision submit_cheetah_11093/1 2005/03/03 01:14:53 rrekha
-- Added SNMP support for SIP options health check.
-- 
-- Revision submit_cheetah_11025/1 2005/03/02 20:54:26 rrekha
-- SNMP support for WLM SASP.
-- 
-- Revision submit_cheetah_11082/1 2005/03/02 11:14:23 mmacnt
-- Q001028659 - Allow operator to supply name for VIP
-- 
-- Revision submit_cheetah_11042/1 2005/03/02 02:34:45 bshao
-- CR 971821:  Added code to support 64 scriptable health checks.
-- 
-- Revision submit_cheetah_10951/1 2005/03/01 15:50:49 yatsze
-- Change server selected to server returned
-- 
-- Revision submit_cheetah_10393/1 2005/01/05 21:01:27 mmacnt
-- code reorg - moved from lib/agent
-- 
-- Revision submit_cheetah_10527/1 2004/12/17 19:39:27 yuhuang
-- Added mibs for WTS and userhash in current and new config tables.
-- 
-- Revision submit_cheetah_10334/1 2004/11/20 01:28:49 dillibab
-- Added SNMP objects to configure insert cookie dname state.
-- 
-- Revision submit_cheetah_10253/1 2004/11/19 15:54:25 yatsze
-- Add more GSLB stats
-- 
-- Revision submit_cheetah_10174/1 2004/11/11 01:06:18 rrekha
-- Fixed Q01024711: Correct range for fltCur/NewCfgNatTimeout.
-- 
-- Revision submit_cheetah_9807/1 2004/10/19 14:17:30 dillibab
-- Added objects for addition/removal networks to metrics of rule.
-- Added bmap object for networks that are configured to metric of rule.
-- 
-- Revision submit_cheetah_9680/1 2004/10/05 19:37:41 yatsze
-- Add DNS persistence
-- 
-- Revision submit_cheetah_9482/1 2004/10/04 19:55:24 rrekha
-- Correct the description for slbSessionInfoFlag.
-- 
-- Revision submit_cheetah_9542/1 2004/09/23 01:02:26 rrekha
-- Added range for fltCurCfgProtocol/fltNewCfgProtocol.
-- 
-- Revision submit_cheetah_9464/1 2004/09/21 07:16:26 dillibab
-- Added SNMP mib objects for  Filter reverse sesssion entries.
-- 
-- Revision submit_cheetah_9386/1 2004/09/13 22:24:00 bshao
-- CR 976805: Added code to support 64 bytes of domain name size and
-- 34 bytes of host name size
-- 
-- Revision submit_cheetah_9196/1 2004/09/01 21:43:01 rrekha
-- Minor changes for SMIv2 compliance.
-- 
-- Revision submit_cheetah_8846/1 2004/08/11 00:59:40 rrekha
-- Changed slbNewCfgDrecordIndex to read-only.
-- 
-- Revision submit_cheetah_8717/1 2004/08/05 15:14:17 yatsze
-- Add support for remote vip
-- 
-- Revision submit_cheetah_8688/1 2004/08/04 20:35:33 rrekha
-- Obsolete fltCur/NewCfgUrlRedir as there is another variable
-- fltCur/NewCfgL7DenyState for the same.
-- 
-- Revision submit_cheetah_8578/1 2004/07/30 00:36:18 rrekha
-- Update the copyright header.
-- 
-- Revision submit_cheetah_8371/1 2004/07/15 23:18:46 rrekha
-- Changed name for slbCur/NewCfgSmtport to slbCur/NewCfgSmtportNum as 
-- per Wendell's request.
-- 
-- Revision submit_cheetah_8279/1 2004/07/12 09:36:34 dillibab
-- Changed syntax of slbNewCfgSmtportIndex to Integer32.
-- 
-- Revision submit_cheetah_8256/2 2004/07/10 09:54:32 dillibab
-- Merged with previous changes.
-- 
-- Revision submit_cheetah_8262/1 2004/07/09 22:12:10 rrekha
-- Fixed Q00933924: Added more description for objects 
-- slbCur/NewCfgGroupHealthCheckFormula.
-- 
-- Revision submit_cheetah_8172/2 2004/07/09 15:01:34 dillibab
-- Merged with previous changes.
-- 
-- Revision submit_cheetah_8236/1 2004/07/09 13:52:20 yatsze
-- REmove enum persistence since GSLB_ENH_PERS is not defined
-- 
-- Revision submit_cheetah_8188/1 2004/07/07 20:04:30 yatsze
-- Add GSLB_ENH_PERS flag
-- 
-- Revision submit_cheetah_8172/1 2004/07/09 14:45:16 dillibab
-- Added mib objects for SMT Port configuration.
-- 
-- Revision submit_cheetah_8256/1 2004/07/10 09:10:56 dillibab
-- Added mib object slbOperGroupRealServerTable for oper real server groups.
-- 
-- Revision submit_cheetah_8092/1 2004/07/03 03:42:46 rrekha
-- Fixed Q00936962: Added mib objects slbCurCfgGroupOperatorAccess and 
-- slbNewCfgGroupOperatorAccess.
-- 
-- Revision submit_cheetah_8102/1 2004/07/01 07:36:57 dillibab
-- Added mib object for Dbind in filter tables.
-- 
-- Revision submit_cheetah_8034/1 2004/06/29 03:25:57 dillibab
-- Added mib object for Fast Health Check of Real Server.
-- 
-- Revision submit_cheetah_8006/2 2004/06/28 09:17:09 dillibab
-- Merged with previous changes.
-- 
-- Revision submit_cheetah_8035/1 2004/06/25 23:53:25 rrekha
-- Fixed Q00811049: Do not obsolete hcsNewCfgAddOpenCmd since it will be 
-- used when UDP_SCRIPT_HC is not defined.
-- 
-- Revision submit_cheetah_8006/1 2004/06/28 09:06:18 dillibab
-- Added mib variable for Advance Group Health Check Formula for Real Server Group.
-- 
-- Revision submit_cheetah_7993/1 2004/06/23 23:31:29 rrekha
-- Fixed Q00933897: slbNewCfgVirtServiceXForwardedFor should have max-access 
-- of read-create not read-only.
-- 
-- Revision submit_cheetah_7887/1 2004/06/22 19:57:35 yatsze
-- Add mib objects gslbCurCfgGenRemSiteUpdateIntervalSeconds and gslbNewCfgGenRemSiteUpdateIntervalSeconds
-- 
-- Revision submit_cheetah_7844/1 2004/06/16 19:54:26 yatsze
-- Rename DNS redirect to DNS direct
-- 
-- Revision submit_cheetah_7746/2 2004/06/14 12:47:42 dillibab
-- Merged with previous changes.
-- 
-- Revision submit_cheetah_7798/2 2004/06/11 23:47:17 rrekha
-- Merged with previous changes.
-- 
-- Revision submit_cheetah_7788/1 2004/06/11 17:40:12 ocheung
-- Q00811049:  Allow script send and expect content to be greater than
-- 255 characters because the CLI can now support up to 512 characters
-- in a single input line.
-- 
-- Revision submit_cheetah_7798/1 2004/06/11 23:38:48 rrekha
-- Added more enums to MIB object slbSessionInfoFlag.
-- 
-- Revision submit_cheetah_7733/1 2004/06/09 19:02:38 rtsai
-- CR916928:LDAP L7 Slb stats show wrong information.
-- Removed LDAP stats from EMS and WBUI because most of
-- stats are for debugging only and can not be counted correctly
-- due to the mix of L4 and L7 processing.
-- 
-- Revision submit_cheetah_7746/1 2004/06/14 06:12:22 dillibab
-- Added support to Rport metric.
-- 
-- Revision submit_cheetah_7634/3 2004/06/02 20:24:08 yatsze
-- Clean up code
-- 
-- Revision submit_cheetah_7566/1 2004/05/27 18:38:51 yatsze
-- Add support to configure DSSP version 1 or 2
-- 
-- Revision submit_cheetah_7562/1 2004/05/26 19:41:56 yatsze
-- Merge pass and stop metric to none
-- 
-- Revision submit_cheetah_7133/1 2004/05/12 22:51:00 rtsai
-- Added fltCurCfgEgressPip and fltNewCfgEgressPip.
-- 
-- Revision submit_cheetah_7240/1 2004/05/10 20:26:47 yatsze
-- Add mib object for add/remove rule and add/remove virtual server/remote real server
-- 
-- Revision submit_cheetah_7209/1 2004/05/10 15:16:42 yatsze
-- Add mib objects gslbStatGeo and gslbStatPers
-- 
-- Revision submit_cheetah_7194/1 2004/05/07 16:06:43 yatsze
-- Add mib objects for enhanced GSLB
-- 
-- Revision submit_cheetah_7172/1 2004/05/06 17:16:49 yatsze
-- Add GSLB mib objects for gslbInfo, gslbStats and gslbOper
-- 
-- Revision submit_cheetah_7152/1 2004/05/04 20:37:28 yatsze
-- Add mib objects for enhanced GSLB
-- 
-- Revision submit_cheetah_7117/1 2004/05/04 14:21:03 yatsze
-- Add mib objects for enhanced GSLB
-- 
-- Revision submit_cheetah_7112/1 2004/04/30 19:36:55 yatsze
-- Add gslb stats mib objects for enhanced GSLB
-- 
-- Revision submit_cheetah_7087/2 2004/04/30 15:54:09 yatsze
-- Add mib objects for enhanced GSLB
-- 
-- Revision submit_cheetah_7087/1 2004/04/30 12:39:58 yatsze
-- Added gslbEnhNetworkCfg and gslbRuleCfg mib objects
-- 
-- Revision submit_cheetah_6824/2 2004/04/03 02:15:27 ocheung
-- Udpated description for OffsetCmd, DepthCmd, and WaitCmd.
-- 
-- Revision submit_cheetah_6824/1 2004/04/01 00:53:22 ocheung
-- Corrected SYNTAX for hcsNewCfgAddOffsetCmd, hcsNewCfgAddWaitCmd, and
-- hcsNewCfgAddDepthCmd.
-- 
-- Revision submit_cheetah_6776/1 2004/03/31 00:06:07 ocheung
-- Added MIBs, SNMP agent, and WebUI support for FILT_IDS_GRP.
-- 
-- Revision submit_cheetah_6763/1 2004/03/25 00:11:23 ocheung
-- Added MIBs, SNMP agent, and WebUI support for TCP_BIN_SCRIPT.
-- 
-- Revision submit_cheetah_6703/1 2004/03/20 00:29:45 rtsai
-- obsoleted slbCurCfgProxyGratArp, slbNewCfgProxyGratArp and
-- slbStatSpMaintTcpFragments  
-- Added slbCurCfgPortBind,slbNewCfgPortBind, 
-- slbCurCfgVirtServiceEgressPip,
-- slbNewCfgVirtServiceEgressPip.
-- 
-- Revision submit_cheetah_6511/1 2004/03/16 00:37:06 rtsai
-- Added mib for pipout command in virtual service menu.
-- 
-- Revision submit_cheetah_6382/1 2004/02/25 23:22:32 rtsai
-- Added httphead health check.
-- 
-- Revision submit_cheetah_6217/1 2004/01/29 00:53:38 rrekha
-- Added SNMP support for pbind norport feature.
-- 
-- Revision submit_cheetah_6177/1 2004/01/27 20:20:28 rtsai
-- Removed l7 ldap unneeded stats mibs.
-- 
-- Revision submit_cheetah_5951/1 2003/12/18 22:17:24 rrekha
-- Fixed Q00813835: Added MIB objects fltCurCfgAclIpLength and
-- fltNewCfgAclIpLength to configure IP packet length.
-- 
-- Revision submit_cheetah_5890/1 2003/12/15 23:37:52 rrekha
-- Added 64 bit counters for real server, group and virtual server
-- octets.
-- 
-- Revision submit_cheetah_5841/1 2003/12/05 22:59:06 rrekha
-- Converted MIBs to SMIv2. 
-- 
-- Revision submit_cheetah_5733/1 2003/11/20 00:07:56 abhijitk
-- SNMP MIB/agent for 802.1p filter matching.
-- 
-- Revision submit_cheetah_5684/1 2003/11/17 23:44:17 vprayaga
-- Initial checkin for IEEE 8023ad lag MIB.
-- 
-- Revision submit_cheetah_5666/1 2003/11/12 22:58:22 rrekha
-- Fixed Q00787939: Correct the range for fltCurCfgHttpRedirMappingFromStr,
-- fltCurCfgHttpRedirMappingToStr, fltNewCfgHttpRedirMappingFromStr and
-- fltNewCfgHttpRedirMappingToStr.
-- 
-- Revision submit_cheetah_5552/1 2003/11/03 21:51:07 rrekha
-- Fixed Q00780526: Added SNMP support to ena/dis real server
-- per group.
-- 
-- Revision submit_cheetah_5476/2 2003/10/30 18:44:04 ocheung
-- Merged file.
-- 
-- Revision submit_cheetah_5466/1 2003/10/28 21:34:58 rrekha
-- Fixed Q00778686: Added MIB support for SIP health check.
-- 
-- Revision submit_cheetah_5476/1 2003/10/30 18:29:00 ocheung
-- Added SNMP and WebUI support for additional commands for   
-- UDP scripted health check (nsend, nexpect, depth).
-- 
-- Revision submit_cheetah_5454/1 2003/10/28 01:51:15 rrekha
-- Correct range for slbCurCfgRealServerTimout/slbNewCfgRealServerTimeout.
-- 
-- Revision submit_cheetah_5448/1 2003/10/25 17:36:33 rrekha
-- Fixed typo in comment which was causing build error.
-- 
-- Revision submit_cheetah_5447/1 2003/10/25 00:12:54 rrekha
-- Fixed Q00769816: Correct range for MIB objects slbCurCfgGroupHealthCheckUrl
-- and slbNewCfgGroupHealthCheckUrl to 0-127.
-- Fixed Q00769810: Correct range for MIB objects slbCurCfgRealServerIdsvlan
-- and slbNewCfgRealServerIdsvlan to 0-4090.
-- Fixed Q00769811: Remove range for MIB variables slbCurCfgRealServerIdsport
-- and slbNewCfgRealServerIdsport. The range for these should be 
-- got from the MIB agPortTableMaxEnt.
-- 
-- Revision submit_cheetah_5338/1 2003/10/14 17:39:32 yatsze
-- Port CP_GSLB_DOMAINS from Tigon
-- 
-- Revision submit_cheetah_5316/1 2003/10/14 14:26:46 yatsze
-- Port CP_GSLB_HTTP_PROXY from Tigon
-- 
-- Revision submit_cheetah_5236/1 2003/10/03 01:54:09 ocheung
-- Added MIB, SNMP agent, and WebUI support for scripted health 
-- check wait window (SCRIPT_WAIT_CMD).
-- 
-- Revision submit_cheetah_5230/1 2003/10/02 02:07:56 ocheung
-- Added MIB and SNMP agent support for UDP scripted health check.
-- 
-- Revision submit_cheetah_5213/1 2003/09/30 18:43:37 yuhuang
-- Added range for idsvlan and idsport MIB objects.
-- 
-- Revision submit_cheetah_4435/1 2003/08/12 22:59:49 rrekha
-- Changed name of mib file for cheetah*.mib to aos*.mib.
-- 
-- Revision submit_cheetah_4181/1 2003/07/24 23:40:22 rtsai
-- Added MIBs for  HTTP redirect mapping table and filter pattern
-- group. 
-- Added MIB for HTTP X-Forwarded-For.
-- 
-- Revision submit_cheetah_4094/1 2003/07/22 00:34:18 rrekha
-- Added SNMP support for SIP load balancing.
-- 
-- Revision submit_cheetah_3944/1 2003/07/16 17:44:50 ocheung
-- Added fltCurCfgLayer7ParseAll, fltNewCfgLayer7ParseAll,
-- fltCurCfgSecurityParseAll, fltNewCfgSecurityParseAll.
-- Obsoleted slbCurCfgSlowage and slbNewCfgSlowage, and add
-- slbCurCfgNewSlowage and slbNewCfgNewSlowage.
-- 
-- Revision submit_cheetah_3792/1 2003/07/07 21:25:13 yhuang1
-- L7_SLB_LDAP: added ldap statistics.
-- 
-- Revision submit_cheetah_3709/1 2003/07/03 19:00:42 yuhuang
-- Added MIB objects idsvlan and idsport in current and new real server configuration.
-- 
-- Revision submit_cheetah_3757/1 2003/07/02 02:12:59 ocheung
-- Fixed Q00695588.  Removed weightedHash from slbCurCfgGroupMetric
-- and slbNewCfgGroupMetric because this feature is for the next
-- release (21.1).
-- 
-- Revision submit_cheetah_3577/1 2003/06/30 18:02:27 rtsai
-- Added peerpip mib under sync.
-- 
-- Revision submit_cheetah_3676/1 2003/06/25 21:17:58 yhuang1
-- IP_ACL, UDP_BLAST: clean up old code.
-- 
-- Revision submit_cheetah_3584/1 2003/06/23 20:07:05 yhuang1
-- UDP_BLAST: moved under security item.
-- 
-- Revision submit_cheetah_3504/1 2003/06/18 21:15:49 yhuang1
-- UDP_BLAST: changed packet limit value.
-- 
-- Revision submit_cheetah_3499/1 2003/06/17 17:23:11 andyrao
-- Changed the name of the MIB variable slbCurCfgVirtServiceDamBlk to
-- slbCurCfgVirtServiceDirect.  Changed the name of the MIB variable
-- slbNewCfgVirtServiceDamBlk to slbNewCfgVirtServiceDirect.  Also
-- made changes to the descriptions of both of these MIB variables.
-- 
-- Revision submit_cheetah_3475/1 2003/06/12 23:38:55 andyrao
-- Removed the definition of the MIB variable 'slbStatMaintDamBlkPkts'.
-- 
-- Revision submit_cheetah_3421/1 2003/06/10 18:14:36 yatsze
-- Add Advanced Global SLB mib
-- 
-- Revision submit_cheetah_3269/1 2003/05/30 17:27:38 rrekha
-- Ported fix for Q00638073: Added mib object for real server response time.
-- Also added real server weight in the slbVirtServicesInfoTable.
-- 
-- Revision submit_cheetah_3249/1 2003/05/23 19:18:18 yatsze
-- Add code for RTSP health check
-- 
-- Revision submit_cheetah_3227/1 2003/05/22 17:58:52 yuhuang
-- Changed MIB objects slbCurCfgVlanBind and slbNewCfgVlanBind to
-- slbCurCfgRtsVlan and slbNewCfgRtsVlan.
-- 
-- Revision submit_cheetah_3159/2 2003/05/16 22:58:43 rmundhra
-- Merging out.
-- 
-- Revision submit_cheetah_3122/2 2003/05/16 01:51:50 rtsai
-- Merged code.
-- 
-- Revision submit_cheetah_3161/1 2003/05/16 00:25:14 rrekha
-- Added proper description for slbCurCfgGroupRealThreshold and 
-- slbNewCfgGroupRealThreshold.
-- 
-- Revision submit_cheetah_3122/1 2003/05/16 00:40:40 rtsai
-- Added stats mibs for ENH_RATE_LIM.
-- 
-- Revision submit_cheetah_3159/1 2003/05/16 22:36:13 rmundhra
-- Added SNMP support for SLB session attack detection.
-- 
-- Revision submit_cheetah_3061/1 2003/05/13 18:01:17 rtsai
-- Changed pipNewCfgPip mib to be read only.
-- 
-- Revision submit_cheetah_3065/2 2003/05/09 17:47:54 andyrao
-- Modified the access level of slbNewCfgGroupPhashMask from read-only 
-- to read-write.
-- 
-- Revision submit_cheetah_3065/1 2003/05/09 17:43:40 andyrao
-- Defined two new MIB variables: slbCurCfgGroupPhashMask and
-- slbNewCfgGroupPhashMask.
-- 
-- Revision submit_cheetah_3046/2 2003/05/08 23:17:12 andyrao
-- Merged out.
-- 
-- Revision submit_cheetah_3056/1 2003/05/08 22:24:16 rtsai
-- Fixed virtual service stats table entry number.
-- 
-- Revision submit_cheetah_2810/2 2003/05/08 21:27:29 rtsai
-- Merged code.
-- 
-- Revision submit_cheetah_3045/1 2003/05/08 20:47:47 ocheung
-- Added support for SCRIPT_HC_WAIT feature.
-- 
-- Revision submit_cheetah_2810/1 2003/05/08 17:47:12 rtsai
-- Changed Virtual Service Stats table to have 3 indexes instead of 2 indexes.
-- Added fltNewCfgProxyIp and fltCurCfgProxyIp to filter table.
-- 
-- Revision submit_cheetah_3027/1 2003/05/07 23:02:53 yuhuang
-- Added MIB objects slbCurCfgGroupMinmissHash and slbNewCfgGroupMinmissHash.
-- 
-- Revision submit_cheetah_2881/1 2003/05/07 02:14:34 ocheung
-- Added support for WEIGHTED_HASH, WAP_ADD_HC, ENH_RATE_LIM,
-- UDP_PMATCH_FILT, and UDP_SCRIPT_HC features.
-- 
-- Revision submit_cheetah_2892/1 2003/05/02 23:08:29 rrekha
-- SNMP_HC_WEIGHT: Added mib objects to ena/dis SNMP health check
-- weights.
-- 
-- Revision submit_cheetah_2850/1 2003/05/01 20:31:39 rmundhra
-- Added MIB object for retrieving the max sessions
-- that can be present in the session table at any
-- given time.
-- 
-- Revision submit_cheetah_2809/1 2003/04/25 21:39:42 yhuang1
-- IP_ACL: added MIBs.
-- 
-- Revision submit_cheetah_2807/2 2003/04/25 20:48:20 andyrao
-- Merged out.
-- 
-- Revision submit_cheetah_2437/1 2003/04/25 18:14:11 rtsai
-- Added MIB for ECMP, Virtual Service Stats.
-- 
-- Revision submit_cheetah_2784/2 2003/04/24 20:46:52 yuhuang
-- Merged with previous submit.
-- 
-- Revision submit_cheetah_2784/1 2003/04/24 20:34:49 yuhuang
-- Added MIB objects slbCurCfgVlanBind and slbNewCfgVlanBind for the
-- VLAN bind real server lookup.
-- 
-- Revision submit_cheetah_2691/1 2003/04/24 01:13:56 yhuang1
-- UDP_BLAST: added SNMP mib and some agent support.
-- 
-- Revision submit_cheetah_2736/1 2003/04/22 22:17:27 rrekha
-- Added MIB objects for SNMP HC extension, under real server
-- table slbNewCfgRealServerCommString/slbCurCfgRealServerCommString
-- and slbNewCfgRealServerOid/slbcurCfgRealServerOid
-- 
-- Revision submit_cheetah_2730/1 2003/04/22 01:43:01 hkavulur
-- Support for INBOUND_LINKLB
-- 
-- Revision submit_cheetah_2587/1 2003/04/11 18:15:41 yhuang1
-- SESSION_RESET: added WebUI and SNMP support.
-- 
-- Revision submit_cheetah_2576/1 2003/04/11 16:35:30 rtsai
-- Changed the name of constants for PipBaseType.
-- 
-- Revision submit_cheetah_2547/1 2003/04/10 18:58:06 yhuang1
-- L7_SLB_LDAP: WebUI and SNMP support added.
-- 
-- Revision submit_cheetah_2544/2 2003/04/08 18:47:27 andyrao
-- Merge out.
-- 
-- Revision submit_cheetah_2513/1 2003/04/08 18:33:36 yhuang1
-- SLB_THASH: WebUI and SNMP support added.
-- 
-- Revision submit_cheetah_1843/1 2003/04/05 01:40:16 rtsai
-- Added MIBs for PIP table.
-- 
-- Revision submit_cheetah_2475/1 2003/04/02 18:01:39 andyrao
-- Modified the definition of the MIB variables radiusAcctReqWithFramedIp
-- and radiusAcctReqWithoutFramedIp.
-- 
-- Revision submit_cheetah_2430/1 2003/03/28 01:53:43 rrekha
-- Added MIB variables for current/new config table size for 
-- filter, real server, real server group and virtual server tables.
-- 
-- Revision submit_cheetah_2439/1 2003/03/27 22:20:13 andyrao
-- Defined the following new MIB variables: fltCurCfgRadiusWapPersist,
-- fltNewCfgRadiusWapPersist, radiusAcctReqWithFramedIp, and
-- radiusActReqWithoutFramedIp.
-- 
-- Revision submit_cheetah_2270/2 2003/03/26 22:38:46 rmundhra
-- Merging out.
-- 
-- Revision submit_cheetah_2402/1 2003/03/25 17:35:18 andyrao
-- Changed the definitions of the MIB variables fltCurCfgAction and 
-- fltNewCfgAction back to their original values.
-- 
-- Revision submit_cheetah_2398/1 2003/03/24 18:56:38 andyrao
-- Small change to the definitions of the MIB variables fltCurCfgAction
-- and fltNewCfgAction.
-- 
-- Revision submit_cheetah_2373/1 2003/03/21 00:12:16 andyrao
-- Modified the MIB variables fltCurCfgAction and fltNewCfgAction by
-- adding the 'goto' action.  Defined 2 new MIB variables called
-- fltCurCfgGotoFilter and fltNewCfgGotoFilter.  These variables are
-- the "filter ID for the goto action".
-- 
-- Revision submit_cheetah_2334/1 2003/03/18 21:11:12 andyrao
-- Modified the MIB variables slbCurCfgGroupMetric and slbNewCfgGroupMetric
-- to include support for phash.
-- 
-- Revision submit_cheetah_2285/1 2003/03/14 19:18:28 andyrao
-- Modified the MIB variables slbCurCfgGroupHealthCheckLayer and
-- slbNewCfgGroupHealthCheckLayer to include the Radius access, TFTP,
-- and WTP health checks.
-- 
-- Revision submit_cheetah_2213/1 2003/03/13 19:42:39 smiao
-- Collected NAAP stats info based on per port, not per SP.
-- Obsoleted NAAP link level ack packet alloc, free and fail stats, since there
-- was no need to store the allocated ack packet in the array buffer.  
-- 
-- Revision submit_cheetah_2270/1 2003/03/26 22:09:48 rmundhra
-- Initial checkin for Session Table via SNMP.
-- 
-- Revision submit_cheetah_2260/1 2003/03/12 20:52:08 andyrao
-- The last check-in caused the OIDs to change; this checkin undoes
-- that.
-- 
-- Revision submit_cheetah_2259/1 2003/03/12 18:03:12 andyrao
-- Added the following MIB objects:
-- slbCurCfgVirtServiceSelectiveDam
-- slbNewCfgVirtServiceSelectiveDam
-- wapSelectiveDamPkts
-- 
-- Revision submit_cheetah_2181/1 2003/03/05 22:39:37 rrekha
-- Added MIB descriptions for 2208/2216 PIPs.
-- 
-- Revision submit_cheetah_1919/1 2003/02/05 20:03:18 rrekha
-- Changed the include paths for integrating support
-- for SNMP V3 Windmanage Stack.
-- 
-- Revision submit_cheetah_1779/1 2003/01/06 22:21:00 rrekha
-- Fixed Q00584200: Changed enum for slbRealServerInfoHealthLayer.
-- 
-- Revision submit_cheetah_1688/1 2002/12/11 22:09:09 rrekha
-- SNMP_HC: slbCurCfgGroupHealthCheckLayer/slbNewCfgGroupHealthCheckLayer now 
-- have enums to support SNMP health check.
-- 
-- Revision submit_cheetah_1679/1 2002/12/11 01:07:30 rrekha
-- SNMP_HC: Added support for SNMP health checks.
-- 
-- Revision submit_cheetah_1027/1 2002/12/09 19:16:01 rrekha
-- Added MIB objects gslbCurCfgGenEncrypt/gslbNewCfgGenEncrypt.
-- 
-- Revision submit_cheetah_1581/1 2002/11/26 21:47:03 rmundhra
-- Modified the range for fltCurCfgVlan and fltNewCfgVlan
-- to 4090.
-- 
-- Revision submit_cheetah_1568/1 2002/11/25 22:13:06 rmundhra
-- CR Q00501984: Ported from 10.0 
-- RFE: GSLB proximity w/ lookups enabled to consider
-- hostname.
-- 
-- Revision submit_cheetah_1528/1 2002/11/19 18:43:01 rrekha
-- Fixed Q00539233: Added slbVirtServicesInfoTable.
-- 
-- Revision submit_cheetah_1517/1 2002/11/15 01:14:21 rrekha
-- Fixed Q00549333: For slbNewCfgVirtServicePBind/slbCurCfgVirtServicePBind
-- changes the names in the enum so that they are consistent with CLI.
-- 
-- Revision submit_cheetah_1427/1 2002/11/01 23:44:12 rrekha
-- Fixed Q00550261: Added auxiliary session table and per SP 
-- auxiliary session table statistics.
-- 
-- Revision submit_cheetah_1394/1 2002/10/29 18:34:03 rrekha
-- Added slbRealServerRportInfoTable which gives the status of 
-- each rport.
-- Also added slbRealServerInfoVlan.
-- 
-- Revision submit_cheetah_1326/1 2002/10/22 00:49:40 rrekha
-- Added MIB variables slbCurCfgProxyGratArp/slbNewCfgProxyGratArp.
-- 
-- Revision submit_cheetah_1243/1 2002/10/15 19:32:19 rrekha
-- Added SSL maintenance statistics.
-- 
-- Revision submit_cheetah_1151/1 2002/10/09 01:13:15 rrekha
-- Fixed Q00533798: Added MIB objects which clear the SLB
-- nonop stats.
-- 
-- Revision submit_cheetah_1080/1 2002/10/02 19:59:28 rrekha
-- Fixed Q00528095 : Added GSLB virtual server statistics.
-- 
-- Revision submit_cheetah_1073/2 2002/10/01 02:03:29 rrekha
-- Merged with previous version.
-- 
-- Revision submit_cheetah_1032/1 2002/09/30 18:30:14 rmundhra
-- Added PIP changes for MODEL_2224.
-- 
-- Revision submit_cheetah_1073/1 2002/10/01 02:02:04 rrekha
-- Added slbNewCfgGroupIdsFlood/slbCurCfgGroupIdsFlood for
-- ids group flood feature.
-- 
-- Revision submit_cheetah_1033/1 2002/09/25 23:58:28 rrekha
-- Fixed Q00528095 : Added MIB objects for GSLB group stats.
-- 
-- Revision submit_cheetah_926/1 2002/09/16 17:38:21 rrekha
-- Removed WAP DMA read/write statistics. These stats are for Tigon only.
-- 
-- Revision submit_cheetah_883/1 2002/09/06 20:57:52 rrekha
-- Fixed Q00514078: Changed enum for fltNewCfgInvert/fltCurCfgInvert
-- to enabled/disabled to be consistent with CLI.
-- 
-- Revision submit_cheetah_848/1 2002/09/04 18:44:34 rmundhra
-- Fixed CR Q00512410: WebUI: L4 PIP configuration shows
-- wrong ports for both 2424 and 2448.
-- Modified descriptions for pip configuration objects
-- to reflect the ports affected based on different
-- hardware platforms.
-- 
-- Revision submit_cheetah_826/1 2002/09/03 18:14:23 rrekha
-- Added MIBs for filter statistics per SP.
-- 
-- Revision submit_cheetah_322/1 2002/07/10 01:41:45 rrekha
-- Fixed Q00479767: Remove slbNewCfgRealGroupIdslb/slbCurCfgRealGroupIdslb
-- as they are no longer used. Added support for group ids state and port.
-- 
-- Revision submit_cheetah_217/1 2002/06/26 20:28:35 rrekha
-- New mibs to support scriptable health checks.
-- 
-- Revision submit_cheetah_212/1 2002/06/25 17:58:40 rrekha
-- Fixed some typos in mib descriptions.
-- 
-- Revision ch_1_0_0_dev/15 2002/06/04 23:20:51 rrekha
-- Fixed Q00453911 : Added slb oper command to clear session table. 
-- Removed the per port clear oper command since it no longer applies per
-- port. This should fix the ASSERTs.
-- 
-- Revision ch_1_0_0_dev/14 2002/05/30 19:45:12 rmundhra
-- Porting RFE: GSLB no remote real server SLB.
-- 
-- Revision ch_1_0_0_dev/13 2002/05/29 18:44:49 rmundhra
-- Porting CR Q00421722 - RFE: Add support for global
-- enable/disable of Source MAC Address substitution.
-- When enabled supercedes value of individual real server
-- submac.
-- 
-- Revision ch_1_0_0_dev/12 2002/05/28 19:47:29 rrekha
-- Removed node tcpStats as it is no longer used.
-- 
-- Revision ch_1_0_0_dev/11 2002/05/28 19:40:10 rrekha
-- Removed the TCP statistics as tcpStatCurConns is present in the 
-- standard MIB-II and tcpStatHalfOpen has been added under the
-- layer7 maint statistics.
-- 
-- Revision ch_1_0_0_dev/10 2002/05/23 23:16:55 rrekha
-- Added object rtspStatBufferAllocs. 
-- Changed descriptions for ftpStats to be more meaningful.
-- 
-- Revision ch_1_0_0_dev/9 2002/05/21 18:04:25 rrekha
-- Correct the description for gslbCurCfgGenHttpRedirect and
-- gslbNewCfgGenHttpRedirect.
-- 
-- Revision ch_1_0_0_dev/8 2002/05/15 21:54:22 rrekha
-- Renamed slbStatPortRealServerTable and slbStatPortMaintTable
-- to slbStatSpRealServerTable and slbStatSpMaintTable as the stats
-- now are per SP not per port.
-- 
-- Revision ch_1_0_0_dev/7 2002/05/10 01:06:46 rrekha
-- Added missing statistics under slbMaintStats, slbStatPortMaintTable
-- and ftpStats.
-- 
-- Revision ch_1_0_0_dev/6 2002/05/09 17:52:09 rrekha
-- Rearranged objects under the virtual server and services tables to be 
-- more consistent with CLI.
-- 
-- Revision ch_1_0_0_dev/5 2002/05/02 23:53:32 rrekha
-- Rearranged nodes under slbGeneralCfg.
-- 
-- Revision ch_1_0_0_dev/4 2002/05/01 18:31:28 smiao
-- Removed VAM discards. Added LAND attacks.
-- 
-- Revision ch_1_0_0_dev/3 2002/04/23 21:47:01 smiao
-- Renamed node cheetah to aws-switches.
-- 
-- Revision ch_1_0_0_dev/2 2002/04/18 19:14:56 smiao
-- Removed slbCurCfgPortProxyIpAddr and slbNewCfgPortProxyIpAddr for Cheetah.
-- 
-- Revision ch_1_0_0_dev/1 2002/03/27 02:26:27 smiao
-- Checked in for PIP configurations support in CHEETAH.
-- 
-- Revision ch10latest_smiao/2 2002/02/13 01:41:23 smiao
-- 	Initial checked in for cheetah MIB files.
-- 
-- $EndLog$

ALTEON-CHEETAH-LAYER4-MIB DEFINITIONS ::= BEGIN

IMPORTS
    MODULE-IDENTITY, OBJECT-TYPE, Integer32, Counter32, Gauge32, Counter64,
    IpAddress, Unsigned32
        FROM SNMPv2-SMI
    DisplayString, PhysAddress
        FROM SNMPv2-TC
    aws-switch 
        FROM ALTEON-ROOT-MIB;

layer4 MODULE-IDENTITY
    LAST-UPDATED "200409010000Z" --  1 September, 2004
    ORGANIZATION "Nortel Networks"
    CONTACT-INFO "Rekha Singamsetty
                  Suresh Batchu

                  Nortel Networks
                  4655 Great America Parkway
                  Santa Clara CA 95054

                  +1 408 495 2400
                  rrekha@nortelnetworks.com
                  sbatchu@nortelnetworks.com"
    DESCRIPTION
        "The MIB module for the Alteon OS Layer 4 configuration, statistics 
         and information ."
    REVISION "200409010000Z"     -- 1 September, 2004
    DESCRIPTION
        "Added revision clause for SMIv2 compliance."
    ::= { aws-switch 4 }

layer4Configs     OBJECT IDENTIFIER ::= { layer4 1 }
layer4Stats       OBJECT IDENTIFIER ::= { layer4 2 }
layer4Info        OBJECT IDENTIFIER ::= { layer4 3 }
layer4Oper        OBJECT IDENTIFIER ::= { layer4 4 }

slbCfg  	  OBJECT IDENTIFIER ::= { layer4Configs 1 }
filterCfg  	  OBJECT IDENTIFIER ::= { layer4Configs 2 }
gslbCfg           OBJECT IDENTIFIER ::= { layer4Configs 3 }
layer4TableSize   OBJECT IDENTIFIER ::= { layer4Configs 4 }
wlmCfg            OBJECT IDENTIFIER ::= { layer4Configs 6 }

slbGeneralCfg  	  OBJECT IDENTIFIER ::= { slbCfg 1 }
realServerCfg  	  OBJECT IDENTIFIER ::= { slbCfg 2 }
realServerGroupCfg OBJECT IDENTIFIER ::= { slbCfg 3 }
virtualServerCfg  OBJECT IDENTIFIER ::= { slbCfg 4 }
portCfg           OBJECT IDENTIFIER ::= { slbCfg 5 }
syncCfg           OBJECT IDENTIFIER ::= { slbCfg 6 }
wapCfg            OBJECT IDENTIFIER ::= { slbCfg 7 }
waphcCfg          OBJECT IDENTIFIER ::= { slbCfg 8 }
synAttackDetCfg   OBJECT IDENTIFIER ::= { slbCfg 9 }
hcsCfg            OBJECT IDENTIFIER ::= { slbCfg 13 }
snmphcCfg         OBJECT IDENTIFIER ::= { slbCfg 14 }
pipTblCfg         OBJECT IDENTIFIER ::= { slbCfg 15 }
linklbCfg         OBJECT IDENTIFIER ::= { slbCfg 16 }
smtportCfg        OBJECT IDENTIFIER ::= { slbCfg 17 }

syncGeneralCfg    OBJECT IDENTIFIER ::= { syncCfg 1 }

gslbGeneralCfg    OBJECT IDENTIFIER ::= { gslbCfg 1 }
gslbSitesCfg      OBJECT IDENTIFIER ::= { gslbCfg 2 }
gslbEnhNetworkCfg OBJECT IDENTIFIER ::= { gslbCfg 4 }
gslbRuleCfg       OBJECT IDENTIFIER ::= { gslbCfg 5 }

slbSpStats  	  OBJECT IDENTIFIER ::= { layer4Stats  1 }
slbMaintStats     OBJECT IDENTIFIER ::= { layer4Stats  5 }
filterStats  	  OBJECT IDENTIFIER ::= { layer4Stats  6 }
gslbStats  	  OBJECT IDENTIFIER ::= { layer4Stats  7 }
wapStats          OBJECT IDENTIFIER ::= { layer4Stats  8 }
ftpStats          OBJECT IDENTIFIER ::= { layer4Stats  10 }
rtspStats	  OBJECT IDENTIFIER ::= { layer4Stats  11 }
tcpLimitStats     OBJECT IDENTIFIER ::= { layer4Stats  12 }
dnsSlbStats       OBJECT IDENTIFIER ::= { layer4Stats  13 }
sslSlbStats       OBJECT IDENTIFIER ::= { layer4Stats  16 }
sipStats	  OBJECT IDENTIFIER ::= { layer4Stats  20 }
sessMirrorStats          OBJECT IDENTIFIER ::= { layer4Stats  22 }

-- Real Server Table - Current Configuration

slbRealServerMaxSize OBJECT-TYPE
    SYNTAX Integer32 
    MAX-ACCESS read-only 
    STATUS current 
    DESCRIPTION 
        "The maximum number of entries in SLB RealServerTable." 
    ::= { realServerCfg 1 }

slbCurCfgRealServerTable OBJECT-TYPE
    SYNTAX SEQUENCE OF SlbCurCfgRealServerEntry
    MAX-ACCESS not-accessible
    STATUS current
    DESCRIPTION
        "The table of Real Server configuration in the current_config."
    ::= { realServerCfg 2 }

slbCurCfgRealServerEntry OBJECT-TYPE
    SYNTAX SlbCurCfgRealServerEntry
    MAX-ACCESS not-accessible
    STATUS current
    DESCRIPTION
        "Information about a particular Real Server configuration."
    INDEX { slbCurCfgRealServerIndex }
    ::= { slbCurCfgRealServerTable 1 }
 
SlbCurCfgRealServerEntry ::= SEQUENCE {
    slbCurCfgRealServerIndex           Integer32,
    slbCurCfgRealServerIpAddr          IpAddress,
    slbCurCfgRealServerWeight          INTEGER,
    slbCurCfgRealServerMaxConns        INTEGER,
    slbCurCfgRealServerTimeOut         INTEGER,
    slbCurCfgRealServerBackUp          Integer32,
    slbCurCfgRealServerPingInterval    INTEGER,
    slbCurCfgRealServerFailRetry       INTEGER,
    slbCurCfgRealServerSuccRetry       INTEGER,
    slbCurCfgRealServerState           INTEGER,
    slbCurCfgRealServerType            INTEGER,
    slbCurCfgRealServerName            DisplayString,
    slbCurCfgRealServerUrlBmap         OCTET STRING,
    slbCurCfgRealServerCookie          INTEGER,
    slbCurCfgRealServerExcludeStr      INTEGER,
    slbCurCfgRealServerSubmac          INTEGER,
    slbCurCfgRealServerProxy           INTEGER,
    slbCurCfgRealServerLdapwr          INTEGER,
    slbCurCfgRealServerOid             DisplayString,
    slbCurCfgRealServerCommString      DisplayString,
    slbCurCfgRealServerIdsvlan         INTEGER,
    slbCurCfgRealServerIdsport         Integer32,
    slbCurCfgRealServerAvail           INTEGER,
    slbCurCfgRealServerFastHealthCheck INTEGER,
    slbCurCfgRealServerSubdmac         INTEGER,
    slbCurCfgRealServerOverflow        INTEGER
    }

slbCurCfgRealServerIndex OBJECT-TYPE
    SYNTAX  Integer32
    MAX-ACCESS  read-only
    STATUS  current
    DESCRIPTION
        "The real server number" 
    ::= { slbCurCfgRealServerEntry 1 }

slbCurCfgRealServerIpAddr OBJECT-TYPE
    SYNTAX  IpAddress
    MAX-ACCESS  read-only
    STATUS  current
    DESCRIPTION
        "IP address of the real server identified by the instance of the 
         slbRealServerIndex." 
    ::= { slbCurCfgRealServerEntry 2 }

slbCurCfgRealServerWeight OBJECT-TYPE
    SYNTAX  INTEGER (1..48)
    MAX-ACCESS  read-only
    STATUS  current
    DESCRIPTION
        "The server weight." 
    ::= { slbCurCfgRealServerEntry 3 }

slbCurCfgRealServerMaxConns OBJECT-TYPE
    SYNTAX  INTEGER (0..200000)
    MAX-ACCESS  read-only
    STATUS  current
    DESCRIPTION
        "The maximum number of connections that are allowed." 
    ::= { slbCurCfgRealServerEntry 4 }

slbCurCfgRealServerTimeOut OBJECT-TYPE
    SYNTAX  INTEGER (2..32768)
    MAX-ACCESS  read-only
    STATUS  current
    DESCRIPTION
        "The maximum number of minutes an inactive connection remains open." 
    ::= { slbCurCfgRealServerEntry 5 }

slbCurCfgRealServerBackUp OBJECT-TYPE
    SYNTAX Integer32
    MAX-ACCESS  read-only
    STATUS  current
    DESCRIPTION
        "The backup server number for this server." 
    ::= { slbCurCfgRealServerEntry 6 }

slbCurCfgRealServerPingInterval OBJECT-TYPE
    SYNTAX  INTEGER (0..60)
    MAX-ACCESS  read-only
    STATUS  current
    DESCRIPTION
	"The interval between keep-alive (ping) attempts in number of seconds.
         Zero means disabling ping attempt."
    ::= { slbCurCfgRealServerEntry 7 }

slbCurCfgRealServerFailRetry OBJECT-TYPE
    SYNTAX  INTEGER  (1..63)
    MAX-ACCESS  read-only
    STATUS  current
    DESCRIPTION
        "The number of failed attempts to declare this server DOWN." 
    ::= { slbCurCfgRealServerEntry 8 }

slbCurCfgRealServerSuccRetry OBJECT-TYPE
    SYNTAX  INTEGER (1..63)
    MAX-ACCESS  read-only
    STATUS  current
    DESCRIPTION
        "The number of successful attempts to declare a server UP." 
    ::= { slbCurCfgRealServerEntry 9 }

slbCurCfgRealServerState OBJECT-TYPE
    SYNTAX  INTEGER {
	enabled(2),
	disabled(3)
	}
    MAX-ACCESS  read-only
    STATUS  current
    DESCRIPTION
        "Enable or disable this server." 
    ::= { slbCurCfgRealServerEntry 10 }

slbCurCfgRealServerType OBJECT-TYPE
    SYNTAX  INTEGER {
	local-server(1),
	remote-server(2)
	}
    MAX-ACCESS  read-only
    STATUS  current
    DESCRIPTION
        "The server type.  It participates in global server
	 load balancing when it is configured as remote-server." 
    ::= { slbCurCfgRealServerEntry 11 }

slbCurCfgRealServerName OBJECT-TYPE 
    SYNTAX  DisplayString (SIZE(0..31))
    MAX-ACCESS  read-only 
    STATUS  current 
    DESCRIPTION 
        "The name of the real server."  
    ::= { slbCurCfgRealServerEntry 12 }

slbCurCfgRealServerUrlBmap OBJECT-TYPE
    SYNTAX  OCTET STRING
    MAX-ACCESS  read-only
    STATUS  current
    DESCRIPTION
        "The URL Pathes selected for URL load balancing for by the real 
         server.  The selected URL Pathes are presented in a bitmap format.
         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

             where x : 1 - The represented URL Path is selected
                       0 - The represented URL Path is not selected"
    ::= { slbCurCfgRealServerEntry 13 }

slbCurCfgRealServerCookie OBJECT-TYPE
    SYNTAX  INTEGER {
        enabled(1),
        disabled(2)
        }
    MAX-ACCESS  read-only
    STATUS  current
    DESCRIPTION
        "The real server that will handle client requests that doesn't 
         contain an URL cookie if Cookie loadbalance is enabled." 
    ::= { slbCurCfgRealServerEntry 14 }

slbCurCfgRealServerExcludeStr OBJECT-TYPE
    SYNTAX  INTEGER {
	enabled(1),
	disabled(2)
	}
    MAX-ACCESS  read-only
    STATUS  current
    DESCRIPTION
        "The real server will handle requests that don't match the 
         loadbalance string if it is enabled."
    ::= { slbCurCfgRealServerEntry 15 }

slbCurCfgRealServerSubmac OBJECT-TYPE
    SYNTAX  INTEGER {
	enabled(1),
	disabled(2)
	}
    MAX-ACCESS  read-only
    STATUS  current
    DESCRIPTION
        "The real server config to enable/disable MAC SA substitution for 
         L4 traffic. If disabled (the default) we will NOT substitute the 
         MAC SA of client-to-server frames.  If enabled, we will substitute 
         the MAC SA."
    ::= { slbCurCfgRealServerEntry 16 }

slbCurCfgRealServerProxy OBJECT-TYPE
    SYNTAX  INTEGER {
	enabled(1),
	disabled(2)
	}
    MAX-ACCESS  read-only
    STATUS  current
    DESCRIPTION
        "The real server config to enable/disable client proxy operation."
    ::= { slbCurCfgRealServerEntry 17 }

slbCurCfgRealServerLdapwr OBJECT-TYPE
    SYNTAX  INTEGER {
        enabled(1),
        disabled(2)
        }
    MAX-ACCESS  read-only
    STATUS  current
    DESCRIPTION
        "The real server config to enable/disable LDAP write server."
    ::= { slbCurCfgRealServerEntry 18 }

slbCurCfgRealServerOid OBJECT-TYPE
    SYNTAX DisplayString (SIZE(0..255))
    MAX-ACCESS read-only
    STATUS current
    DESCRIPTION
        "The OID to be sent in the SNMP get request packet."
    ::= { slbCurCfgRealServerEntry 19 }

slbCurCfgRealServerCommString OBJECT-TYPE
    SYNTAX DisplayString (SIZE(0..32))
    MAX-ACCESS read-only
    STATUS current
    DESCRIPTION
        "The community string to be used in the SNMP get request packet."
    ::= { slbCurCfgRealServerEntry 20 }

slbCurCfgRealServerIdsvlan OBJECT-TYPE
    SYNTAX  INTEGER (0..4090)
    MAX-ACCESS  read-only
    STATUS  current
    DESCRIPTION
        "The VLAN to be associated with the IDS server."
    ::= { slbCurCfgRealServerEntry 21 }

slbCurCfgRealServerIdsport OBJECT-TYPE
    SYNTAX  Integer32
    MAX-ACCESS  read-only
    STATUS  current
    DESCRIPTION
        "The port to be connected to the IDS server."
    ::= { slbCurCfgRealServerEntry 22 }

slbCurCfgRealServerAvail OBJECT-TYPE
    SYNTAX  INTEGER (1..48)
    MAX-ACCESS  read-only
    STATUS  current
    DESCRIPTION
        "The remote real server Global SLB availability."
    ::= { slbCurCfgRealServerEntry 23 }

slbCurCfgRealServerFastHealthCheck OBJECT-TYPE
    SYNTAX  INTEGER {
        enabled(1),
        disabled(2)
        }
    MAX-ACCESS  read-only
    STATUS  current
    DESCRIPTION
        "The real server config to enable/disable Fast Health Check Operation."
    ::= { slbCurCfgRealServerEntry 24 }

slbCurCfgRealServerSubdmac OBJECT-TYPE
    SYNTAX  INTEGER {
        enabled(1),
        disabled(2)
        }
    MAX-ACCESS  read-only
    STATUS  current
    DESCRIPTION
        "The real server config to enable/disable MAC DA substitution for
         L4 traffic. If disabled, we will NOT substitute the MAC DA of
         client-to-server frames.  If enabled(default), we will substitute
         the MAC DA."
    ::= { slbCurCfgRealServerEntry 25 }

slbCurCfgRealServerOverflow OBJECT-TYPE
    SYNTAX  INTEGER {
        enabled(1),
        disabled(2)
        }
    MAX-ACCESS  read-only
    STATUS  current
    DESCRIPTION
        "The real server config to enable/disable Overflow. If enabled(default)
         allows Backup server to kick in if real server reaches maximum
         connections."
    ::= { slbCurCfgRealServerEntry 26 }


-- Real Server Table - New Configuration

slbNewCfgRealServerTable OBJECT-TYPE
    SYNTAX  SEQUENCE OF SlbNewCfgRealServerEntry
    MAX-ACCESS  not-accessible
    STATUS  current
    DESCRIPTION
        "The table of Real Server configuration in the new_config."
    ::= { realServerCfg 3 }

slbNewCfgRealServerEntry OBJECT-TYPE
    SYNTAX  SlbNewCfgRealServerEntry
    MAX-ACCESS  not-accessible
    STATUS  current
    DESCRIPTION
        "Information about a particular Real Server configuration."
    INDEX   { slbNewCfgRealServerIndex }
    ::= { slbNewCfgRealServerTable 1 }
 
SlbNewCfgRealServerEntry ::= SEQUENCE {
    slbNewCfgRealServerIndex           Integer32,
    slbNewCfgRealServerIpAddr          IpAddress,
    slbNewCfgRealServerWeight          INTEGER,
    slbNewCfgRealServerMaxConns        INTEGER,
    slbNewCfgRealServerTimeOut         INTEGER,
    slbNewCfgRealServerBackUp          Integer32,
    slbNewCfgRealServerPingInterval    INTEGER,
    slbNewCfgRealServerFailRetry       INTEGER,
    slbNewCfgRealServerSuccRetry       INTEGER,
    slbNewCfgRealServerState           INTEGER,
    slbNewCfgRealServerDelete          INTEGER,
    slbNewCfgRealServerType            INTEGER,
    slbNewCfgRealServerName            DisplayString,
    slbNewCfgRealServerUrlBmap         OCTET STRING,
    slbNewCfgRealServerAddUrl          Integer32,
    slbNewCfgRealServerRemUrl          Integer32,
    slbNewCfgRealServerCookie          INTEGER,
    slbNewCfgRealServerExcludeStr      INTEGER,
    slbNewCfgRealServerSubmac          INTEGER,
    slbNewCfgRealServerProxy           INTEGER,
    slbNewCfgRealServerLdapwr          INTEGER,
    slbNewCfgRealServerOid             DisplayString,
    slbNewCfgRealServerCommString      DisplayString,
    slbNewCfgRealServerIdsvlan         INTEGER,
    slbNewCfgRealServerIdsport         Integer32,
    slbNewCfgRealServerAvail           INTEGER,
    slbNewCfgRealServerFastHealthCheck INTEGER,
    slbNewCfgRealServerSubdmac         INTEGER,
    slbNewCfgRealServerOverflow        INTEGER
    }

slbNewCfgRealServerIndex OBJECT-TYPE
    SYNTAX  Integer32
    MAX-ACCESS  read-only
    STATUS  current
    DESCRIPTION
        "The real server number" 
    ::= { slbNewCfgRealServerEntry 1 }

slbNewCfgRealServerIpAddr OBJECT-TYPE
    SYNTAX  IpAddress
    MAX-ACCESS  read-create
    STATUS  current
    DESCRIPTION
        "IP address of the real server identified by the instance of 
         slbRealServerIndex." 
    ::= { slbNewCfgRealServerEntry 2 }

slbNewCfgRealServerWeight OBJECT-TYPE
    SYNTAX  INTEGER (1..48)
    MAX-ACCESS  read-create
    STATUS  current
    DESCRIPTION
        "The server weight." 
    ::= { slbNewCfgRealServerEntry 3 }

slbNewCfgRealServerMaxConns OBJECT-TYPE
    SYNTAX  INTEGER (0..200000)
    MAX-ACCESS  read-create
    STATUS  current
    DESCRIPTION
        "The maximum number of connections that are allowed." 
    ::= { slbNewCfgRealServerEntry 4 }

slbNewCfgRealServerTimeOut OBJECT-TYPE
    SYNTAX  INTEGER (2..32768)
    MAX-ACCESS  read-create
    STATUS  current
    DESCRIPTION
        "The maximum number of minutes an inactive connection remains open." 
    ::= { slbNewCfgRealServerEntry 5 }

slbNewCfgRealServerBackUp OBJECT-TYPE
    SYNTAX Integer32
    MAX-ACCESS  read-create
    STATUS  current
    DESCRIPTION
        "The backup server number for this server." 
    ::= { slbNewCfgRealServerEntry 6 }

slbNewCfgRealServerPingInterval OBJECT-TYPE
    SYNTAX  INTEGER (0..60)
    MAX-ACCESS  read-create
    STATUS  current
    DESCRIPTION
        "The interval between keep-alive (ping) attempts in number of 
         seconds. Zero means disabling ping attempt."
    ::= { slbNewCfgRealServerEntry 7 }

slbNewCfgRealServerFailRetry OBJECT-TYPE
    SYNTAX  INTEGER  (1..63)
    MAX-ACCESS  read-create
    STATUS  current
    DESCRIPTION
        "The number of failed attempts to declare this server DOWN." 
    ::= { slbNewCfgRealServerEntry 8 }

slbNewCfgRealServerSuccRetry OBJECT-TYPE
    SYNTAX  INTEGER (1..63)
    MAX-ACCESS  read-create
    STATUS  current
    DESCRIPTION
        "The number of successful attempts to declare a server UP." 
    ::= { slbNewCfgRealServerEntry 9 }

slbNewCfgRealServerState OBJECT-TYPE
    SYNTAX  INTEGER {
	enabled(2),
	disabled(3)
	}
    MAX-ACCESS  read-create
    STATUS  current
    DESCRIPTION
        "Enable or disable this server." 
    ::= { slbNewCfgRealServerEntry 10 }

slbNewCfgRealServerDelete OBJECT-TYPE
    SYNTAX  INTEGER {
        other(1),
        delete(2)
        }
    MAX-ACCESS  read-create
    STATUS  current
    DESCRIPTION
        "By setting the value to delete(2), the entire row is deleted."
    ::= { slbNewCfgRealServerEntry 11 }

slbNewCfgRealServerType OBJECT-TYPE
    SYNTAX  INTEGER {
        local-server(1),
	remote-server(2)
	}
    MAX-ACCESS  read-create
    STATUS  current
    DESCRIPTION
        "The server type.  It participates in global server load balancing 
         when it is configured as remote-server." 
    ::= { slbNewCfgRealServerEntry 12 }

slbNewCfgRealServerName OBJECT-TYPE 
    SYNTAX  DisplayString (SIZE(0..31))
    MAX-ACCESS  read-create 
    STATUS  current 
    DESCRIPTION 
        "The name of the real server."  
    ::= { slbNewCfgRealServerEntry 13 }

slbNewCfgRealServerUrlBmap OBJECT-TYPE
    SYNTAX  OCTET STRING
    MAX-ACCESS  read-only
    STATUS  current
    DESCRIPTION
        "The URL Pathes selected for URL load balancing for by the
	 real server.  The selected URL Pathes are presented in 
	 a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL Path is selected
                   0 - The represented URL Path is not selected"
    ::= { slbNewCfgRealServerEntry 14 }

slbNewCfgRealServerAddUrl OBJECT-TYPE
    SYNTAX  Integer32
    MAX-ACCESS  read-create
    STATUS  current
    DESCRIPTION
        "The URL Path (slbCurCfgUrlLbPathIndex) to be added to the 
         real server. A zero is returned when read."
    ::= { slbNewCfgRealServerEntry 15 }

slbNewCfgRealServerRemUrl OBJECT-TYPE
    SYNTAX  Integer32
    MAX-ACCESS  read-create
    STATUS  current
    DESCRIPTION
        "The URL Path (slbCurCfgUrlLbPathIndex) to be removed from 
         the real server. A zero is returned when read."
    ::= { slbNewCfgRealServerEntry 16 }

slbNewCfgRealServerCookie OBJECT-TYPE
    SYNTAX  INTEGER {
	enabled(1),
	disabled(2)
	}
    MAX-ACCESS  read-create
    STATUS  current
    DESCRIPTION
        "Enable or disable real server to handle client requests
         that don't contain a cookie if cookie loadbalance is enabled." 
    ::= { slbNewCfgRealServerEntry 17 }

slbNewCfgRealServerExcludeStr OBJECT-TYPE
    SYNTAX  INTEGER {
	enabled(1),
	disabled(2)
	}
    MAX-ACCESS  read-create
    STATUS  current
    DESCRIPTION
        "Enable or disable exclusionary matching string on real server."
    ::= { slbNewCfgRealServerEntry 18 }

slbNewCfgRealServerSubmac OBJECT-TYPE
    SYNTAX  INTEGER {
	enabled(1),
	disabled(2)
	}
    MAX-ACCESS  read-create
    STATUS  current
    DESCRIPTION
        "The real server config to enable/disable MAC SA substitution for 
         L4 traffic. If disabled (the default) we will NOT substitute the 
         MAC SA of client-to-server frames.  If enabled, we will substitute 
         the MAC SA."
    ::= { slbNewCfgRealServerEntry 19 }

slbNewCfgRealServerProxy OBJECT-TYPE
    SYNTAX  INTEGER {
	enabled(1),
	disabled(2)
	}
    MAX-ACCESS  read-create
    STATUS  current
    DESCRIPTION
        "The real server config to enable/disable client proxy operation."
    ::= { slbNewCfgRealServerEntry 20 }

slbNewCfgRealServerLdapwr OBJECT-TYPE
    SYNTAX  INTEGER {
        enabled(1),
        disabled(2)
        }
    MAX-ACCESS  read-create
    STATUS  current
    DESCRIPTION
        "The real server config to enable/disable LDAP write server."
    ::= { slbNewCfgRealServerEntry 21 }

slbNewCfgRealServerOid OBJECT-TYPE
    SYNTAX DisplayString (SIZE(0..255))
    MAX-ACCESS read-create
    STATUS current
    DESCRIPTION
        "The OID to be sent in the SNMP get request packet."
    ::= { slbNewCfgRealServerEntry 22 }

slbNewCfgRealServerCommString OBJECT-TYPE
    SYNTAX DisplayString (SIZE(0..32))
    MAX-ACCESS read-create
    STATUS current
    DESCRIPTION
        "The community string to be used in the SNMP get request packet."
    ::= { slbNewCfgRealServerEntry 23 }

slbNewCfgRealServerIdsvlan OBJECT-TYPE
    SYNTAX  INTEGER (0..4090)
    MAX-ACCESS  read-create
    STATUS  current
    DESCRIPTION
        "The VLAN to be associated with IDS server."
    ::= { slbNewCfgRealServerEntry 24 }

slbNewCfgRealServerIdsport OBJECT-TYPE
    SYNTAX  Integer32
    MAX-ACCESS  read-create
    STATUS  current
    DESCRIPTION
        "The port to be connected to IDS server."
    ::= { slbNewCfgRealServerEntry 25 }

slbNewCfgRealServerAvail OBJECT-TYPE
    SYNTAX  INTEGER (1..48)
    MAX-ACCESS  read-create
    STATUS  current
    DESCRIPTION
        "The remote real server Global SLB availability."
    ::= { slbNewCfgRealServerEntry 26 }

slbNewCfgRealServerFastHealthCheck OBJECT-TYPE
    SYNTAX  INTEGER {
        enabled(1),
        disabled(2)
        }
    MAX-ACCESS  read-create
    STATUS  current
    DESCRIPTION
        "The real server config to enable/disable Fast Health Check Operation."
    ::= { slbNewCfgRealServerEntry 27 }

slbNewCfgRealServerSubdmac OBJECT-TYPE
    SYNTAX  INTEGER {
        enabled(1),
        disabled(2)
        }
    MAX-ACCESS  read-create
    STATUS  current
    DESCRIPTION
        "The real server config to enable/disable MAC DA substitution for
         L4 traffic. If disabled, we will NOT substitute the MAC DA of
         client-to-server frames.  If enabled(default), we will substitute
         the MAC DA."
    ::= { slbNewCfgRealServerEntry 28 }

slbNewCfgRealServerOverflow OBJECT-TYPE
    SYNTAX  INTEGER {
        enabled(1),
        disabled(2)
        }
    MAX-ACCESS  read-create
    STATUS  current
    DESCRIPTION
        "The real server config to enable/disable Overflow. If enabled(default)
         allows Backup server to kick in if real server reaches maximum
         connections."
    ::= { slbNewCfgRealServerEntry 29 }
 
-- Real Server Multiple Port Table

slbRealServPortTableMaxSize OBJECT-TYPE
    SYNTAX  Integer32 
    MAX-ACCESS  read-only 
    STATUS  current 
    DESCRIPTION 
        "The maximum number of entries in SLB RealServPortTable." 
    ::= { realServerCfg 4 }

slbCurCfgRealServPortTable OBJECT-TYPE
    SYNTAX  SEQUENCE OF SlbCurCfgRealServPortEntry
    MAX-ACCESS  not-accessible
    STATUS  current
    DESCRIPTION
        "The table of real server service ports."
    ::= { realServerCfg 5 }

slbCurCfgRealServPortEntry OBJECT-TYPE
    SYNTAX  SlbCurCfgRealServPortEntry
    MAX-ACCESS  not-accessible
    STATUS  current
    DESCRIPTION
        "A row in the real server service ports table."
    INDEX   { slbCurCfgRealServIndex, slbCurCfgRealServPortIndex }
    ::= { slbCurCfgRealServPortTable 1 }

SlbCurCfgRealServPortEntry ::= SEQUENCE {
    slbCurCfgRealServIndex         Integer32,
    slbCurCfgRealServPortIndex     Integer32,
    slbCurCfgRealServRealPort      INTEGER
    }

slbCurCfgRealServIndex OBJECT-TYPE
    SYNTAX  Integer32
    MAX-ACCESS  read-only
    STATUS  current
    DESCRIPTION
        "The number of the real server." 
    ::= { slbCurCfgRealServPortEntry 1 }

slbCurCfgRealServPortIndex OBJECT-TYPE 
    SYNTAX  Integer32 
    MAX-ACCESS  read-only 
    STATUS  current 
    DESCRIPTION 
        "The port index. This has no external meaning" 
    ::= { slbCurCfgRealServPortEntry 2 }

slbCurCfgRealServRealPort OBJECT-TYPE  
    SYNTAX  INTEGER (2..65534)
    MAX-ACCESS  read-only  
    STATUS  current  
    DESCRIPTION 
        "The layer4 real service port number."  
    ::= { slbCurCfgRealServPortEntry 3 } 

slbNewCfgRealServPortTable OBJECT-TYPE
    SYNTAX  SEQUENCE OF SlbNewCfgRealServPortEntry
    MAX-ACCESS  not-accessible
    STATUS  current
    DESCRIPTION
        "The table of real server service ports."
    ::= { realServerCfg 6 }

slbNewCfgRealServPortEntry OBJECT-TYPE
    SYNTAX  SlbNewCfgRealServPortEntry
    MAX-ACCESS  not-accessible
    STATUS  current
    DESCRIPTION
        "A row in the real server service ports table."
    INDEX   { slbNewCfgRealServIndex, slbNewCfgRealServPortIndex }
    ::= { slbNewCfgRealServPortTable 1 }

SlbNewCfgRealServPortEntry ::= SEQUENCE {
    slbNewCfgRealServIndex         Integer32,
    slbNewCfgRealServPortIndex     Integer32,
    slbNewCfgRealServRealPort      INTEGER,
    slbNewCfgRealServPortDelete    INTEGER
    }

slbNewCfgRealServIndex OBJECT-TYPE
    SYNTAX  Integer32
    MAX-ACCESS  read-only
    STATUS  current
    DESCRIPTION
        "The number of the real server." 
    ::= { slbNewCfgRealServPortEntry 1 }

slbNewCfgRealServPortIndex OBJECT-TYPE 
    SYNTAX  Integer32 
    MAX-ACCESS  read-only 
    STATUS  current 
    DESCRIPTION 
        "The port index. This has no external meaning" 
    ::= { slbNewCfgRealServPortEntry 2 }

slbNewCfgRealServRealPort OBJECT-TYPE  
    SYNTAX  INTEGER (2..65534)
    MAX-ACCESS  read-create  
    STATUS  current  
    DESCRIPTION 
        "The layer4 real service port number."  
    ::= { slbNewCfgRealServPortEntry 3 } 

slbNewCfgRealServPortDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgRealServPortEntry 4 }

slbBuddyTableMaxSize OBJECT-TYPE
    SYNTAX  Integer32
    MAX-ACCESS  read-only
    STATUS  current
    DESCRIPTION
        "The maximum number of entries in SLB real buddy server table."
    ::= { realServerCfg 7 }

slbCurCfgBuddyTable OBJECT-TYPE
    SYNTAX  SEQUENCE OF SlbCurCfgBuddyEntry
    MAX-ACCESS  not-accessible
    STATUS  current
    DESCRIPTION
        "The table of buddy information."
    ::= { realServerCfg 8 }

slbCurCfgBuddyEntry OBJECT-TYPE
    SYNTAX  SlbCurCfgBuddyEntry
    MAX-ACCESS  not-accessible
    STATUS  current
    DESCRIPTION
        "A row in the buddy server table."
    INDEX   { slbCurCfgRealSerIndex, slbCurCfgBuddyIndex }
    ::= { slbCurCfgBuddyTable 1 }

SlbCurCfgBuddyEntry ::= SEQUENCE {
    slbCurCfgRealSerIndex       Integer32,
    slbCurCfgBuddyIndex         Integer32,
    slbCurCfgBuddyRealIndex     Integer32, 
    slbCurCfgBuddyGroupIndex    Integer32,
    slbCurCfgBuddyService       INTEGER 
    }

slbCurCfgRealSerIndex OBJECT-TYPE
    SYNTAX  Integer32
    MAX-ACCESS  read-only
    STATUS  current
    DESCRIPTION
        "The number of the real server."
    ::= { slbCurCfgBuddyEntry 1 }

slbCurCfgBuddyIndex OBJECT-TYPE
    SYNTAX  Integer32
    MAX-ACCESS  read-only
    STATUS  current
    DESCRIPTION
        "The buddy index. This has no external meaning"
    ::= { slbCurCfgBuddyEntry 2 }

slbCurCfgBuddyRealIndex OBJECT-TYPE
    SYNTAX  Integer32
    MAX-ACCESS  read-only
    STATUS  current
    DESCRIPTION
        "The buddy server's real server number."
    ::= { slbCurCfgBuddyEntry 3 }

slbCurCfgBuddyGroupIndex OBJECT-TYPE
    SYNTAX  Integer32
    MAX-ACCESS  read-only
    STATUS  current
    DESCRIPTION
        "The buddy server's real group number."
    ::= { slbCurCfgBuddyEntry 4 }

slbCurCfgBuddyService OBJECT-TYPE
    SYNTAX   INTEGER (9..65534)
    MAX-ACCESS  read-only
    STATUS  current
    DESCRIPTION
        "The buddy server's service."
    ::= { slbCurCfgBuddyEntry 5 }

slbNewCfgBuddyTable OBJECT-TYPE
    SYNTAX  SEQUENCE OF SlbNewCfgBuddyEntry
    MAX-ACCESS  not-accessible
    STATUS  current
    DESCRIPTION
        "The table of buddy servers."
    ::= { realServerCfg 9 }

slbNewCfgBuddyEntry OBJECT-TYPE
    SYNTAX  SlbNewCfgBuddyEntry
    MAX-ACCESS  not-accessible
    STATUS  current
    DESCRIPTION
        "A row in the real server buddy table."
    INDEX   { slbNewCfgRealSerIndex, slbNewCfgBuddyIndex }
    ::= { slbNewCfgBuddyTable 1 }

SlbNewCfgBuddyEntry      ::= SEQUENCE {
    slbNewCfgRealSerIndex         Integer32,
    slbNewCfgBuddyIndex           Integer32,
    slbNewCfgBuddyRealIndex       Integer32,
    slbNewCfgBuddyGroupIndex      Integer32,
    slbNewCfgBuddyService         INTEGER,
    slbNewCfgBuddyDelete          INTEGER
    }

slbNewCfgRealSerIndex OBJECT-TYPE
    SYNTAX  Integer32
    MAX-ACCESS  read-only
    STATUS  current
    DESCRIPTION
        "The number of the real server."
    ::= { slbNewCfgBuddyEntry 1 }

slbNewCfgBuddyIndex OBJECT-TYPE
    SYNTAX  Integer32
    MAX-ACCESS  read-only
    STATUS  current
    DESCRIPTION
        "The buddy index. This has no external meaning"
    ::= { slbNewCfgBuddyEntry 2 }

slbNewCfgBuddyRealIndex OBJECT-TYPE
    SYNTAX  Integer32 
    MAX-ACCESS  read-create
    STATUS  current
    DESCRIPTION
        "The buddy server's real server number."
    ::= { slbNewCfgBuddyEntry 3 }

slbNewCfgBuddyGroupIndex OBJECT-TYPE
    SYNTAX  Integer32
    MAX-ACCESS  read-create
    STATUS  current
    DESCRIPTION
        "The buddy server's real group number."
    ::= { slbNewCfgBuddyEntry 4 }

slbNewCfgBuddyService OBJECT-TYPE
    SYNTAX  INTEGER (9..65534) 
    MAX-ACCESS  read-create
    STATUS  current
    DESCRIPTION
        "The buddy server's service."
    ::= { slbNewCfgBuddyEntry 5 }

slbNewCfgBuddyDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { slbNewCfgBuddyEntry 6 }

-- Server load balancing - Group Table
slbGroupTableMaxSize OBJECT-TYPE
    SYNTAX  Integer32
    MAX-ACCESS  read-only
    STATUS  current
    DESCRIPTION
        "The maximum number of entries in SLB group tables."
    ::= { realServerGroupCfg 1 }

slbGroupMaxIdsSize OBJECT-TYPE
    SYNTAX  Integer32
    MAX-ACCESS  read-only
    STATUS  current
    DESCRIPTION
        "The maximum number of groups IDS can be enabled on."
    ::= { realServerGroupCfg 2 }

slbCurCfgGroupTable OBJECT-TYPE
    SYNTAX  SEQUENCE OF SlbCurCfgGroupEntry
    MAX-ACCESS  not-accessible
    STATUS  current
    DESCRIPTION
        "The table of groups"
    ::= { realServerGroupCfg 3 }

slbCurCfgGroupEntry OBJECT-TYPE
    SYNTAX  SlbCurCfgGroupEntry
    MAX-ACCESS  not-accessible
    STATUS  current
    DESCRIPTION
        "A row in the slbCurCfgGroupTable "
    INDEX   { slbCurCfgGroupIndex }
    ::= { slbCurCfgGroupTable 1 }

SlbCurCfgGroupEntry ::= SEQUENCE {
    slbCurCfgGroupIndex              Integer32,
    slbCurCfgGroupRealServers        OCTET STRING,
    slbCurCfgGroupMetric             INTEGER,
    slbCurCfgGroupBackupServer       Integer32,
    slbCurCfgGroupBackupGroup        Integer32,
    slbCurCfgGroupHealthCheckUrl     DisplayString,
    slbCurCfgGroupHealthCheckLayer   INTEGER,
    slbCurCfgGroupRealThreshold      INTEGER,
    slbCurCfgGroupVipHealthCheck     INTEGER,
    slbCurCfgGroupIdsState           INTEGER,
    slbCurCfgGroupIdsPort            INTEGER,
    slbCurCfgGroupIdsFlood           INTEGER,
    slbCurCfgGroupMinmissHash        INTEGER,
    slbCurCfgGroupPhashMask          IpAddress,
    slbCurCfgGroupRmetric            INTEGER,
    slbCurCfgGroupHealthCheckFormula DisplayString,
    slbCurCfgGroupWlm                Integer32,
    slbCurCfgGroupOperatorAccess     INTEGER,
    slbCurCfgGroupName               DisplayString
    }

slbCurCfgGroupIndex OBJECT-TYPE
    SYNTAX  Integer32
    MAX-ACCESS  read-only
    STATUS  current
    DESCRIPTION
        "The group number for which the information pertains."
    ::= { slbCurCfgGroupEntry 1 }

slbCurCfgGroupRealServers    OBJECT-TYPE
    SYNTAX  OCTET STRING
    MAX-ACCESS  read-only
    STATUS  current
    DESCRIPTION
        "The Real servers in the group. The servers are presented in 
         bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbCurCfgGroupEntry 2 }

slbCurCfgGroupMetric OBJECT-TYPE
    SYNTAX  INTEGER {
	roundRobin(1),
	leastConnections(2),
	minMisses(3),
	hash(4),
	response(5),
	bandwidth(6),
        phash(7)
	}
    MAX-ACCESS  read-only
    STATUS  current
    DESCRIPTION
        "The metric used to select next server in group."
    ::= { slbCurCfgGroupEntry 3 }

slbCurCfgGroupBackupServer OBJECT-TYPE
    SYNTAX Integer32
    MAX-ACCESS  read-only
    STATUS  current
    DESCRIPTION
        "The backup real server for this group."
    ::= { slbCurCfgGroupEntry 4 }

slbCurCfgGroupBackupGroup OBJECT-TYPE
    SYNTAX  Integer32
    MAX-ACCESS  read-only
    STATUS  current
    DESCRIPTION
        "The backup real server group for this group."
    ::= { slbCurCfgGroupEntry 5 }

slbCurCfgGroupHealthCheckUrl OBJECT-TYPE
    SYNTAX  DisplayString (SIZE(0..127))
    MAX-ACCESS  read-only
    STATUS  current
    DESCRIPTION
        "The specific content which is examined during health checks.
         The content depends on the type of health check."
    ::= { slbCurCfgGroupEntry 6 }

slbCurCfgGroupHealthCheckLayer OBJECT-TYPE
    SYNTAX  INTEGER {
	icmp(1),
	tcp(2),
	http(3),
	httphead(44),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33),
	snmp1(34),
	snmp2(35),
	snmp3(36),
	snmp4(37),
	snmp5(38),
        radiusacs(39),
        tftp(40),
        wtp(41),
        rtsp(42),
        sipping(43),
        sipoptions(45),
        wts(46),
        script17(116),
        script18(117),
        script19(118),
        script20(119),
        script21(120),
        script22(121),
        script23(122),
        script24(123),
        script25(124),
        script26(125),
        script27(126),
        script28(127),
        script29(128),
        script30(129),
        script31(130),
        script32(131),
        script33(132),
        script34(133),
        script35(134),
        script36(135),
        script37(136),
        script38(137),
        script39(138),
        script40(139),
        script41(140),
        script42(141),
        script43(142),
        script44(143),
        script45(144),
        script46(145),
        script47(146),
        script48(147),
        script49(148),
        script50(149),
        script51(150),
        script52(151),
        script53(152),
        script54(153),
        script55(154),
        script56(155),
        script57(156),
        script58(157),
        script59(158),
        script60(159),
        script61(160),
        script62(161),
        script63(162),
        script64(163)
	}
    MAX-ACCESS  read-only
    STATUS  current
    DESCRIPTION
        "The OSI layer at which servers are health checked."
    ::= { slbCurCfgGroupEntry 7 }

slbCurCfgGroupName OBJECT-TYPE 
    SYNTAX  DisplayString (SIZE(0..31))
    MAX-ACCESS  read-only 
    STATUS  current 
    DESCRIPTION 
        "The name of the real server group."  
    ::= { slbCurCfgGroupEntry 8 }

slbCurCfgGroupRealThreshold OBJECT-TYPE 
    SYNTAX  INTEGER (0..15)
    MAX-ACCESS  read-only 
    STATUS  current 
    DESCRIPTION 
        "The minimum number of real servers available. If at any time, the 
         number reaches this minimum limit, a SYSLOG ALERT message is send to 
         to the configured syslog servers stating that the real server 
         threshold has been reached for the concerned group."  
    ::= { slbCurCfgGroupEntry 9 }

slbCurCfgGroupVipHealthCheck OBJECT-TYPE
    SYNTAX  INTEGER {
	enabled(1),
	disabled(2)
	}
    MAX-ACCESS  read-only
    STATUS  current
    DESCRIPTION
        "Enable or disable VIP health checking in DSR mode." 
    ::= { slbCurCfgGroupEntry 10 }

slbCurCfgGroupIdsState OBJECT-TYPE
    SYNTAX  INTEGER {
	enabled(1),
	disabled(2)
	}
    MAX-ACCESS  read-only
    STATUS  current
    DESCRIPTION
        "Enable or disable intrusion detection."
    ::= { slbCurCfgGroupEntry 11 }

slbCurCfgGroupIdsPort OBJECT-TYPE
    SYNTAX  INTEGER (0..65534)
    MAX-ACCESS  read-only
    STATUS  current
    DESCRIPTION
        "The intrusion detection port. A value of 1 is invalid."
    ::= { slbCurCfgGroupEntry 12 }

slbCurCfgGroupIdsFlood OBJECT-TYPE
    SYNTAX  INTEGER {
	enabled(1),
	disabled(2)
	}
    MAX-ACCESS  read-only
    STATUS  current
    DESCRIPTION
        "Enable or disable intrusion detection group flood."
    ::= { slbCurCfgGroupEntry 13 }

slbCurCfgGroupMinmissHash OBJECT-TYPE
    SYNTAX  INTEGER {
        minmiss-24(1),
        minmiss-32(2)
        }
    MAX-ACCESS  read-only
    STATUS  current
    DESCRIPTION
        "24|32 number of ip bits used for minmisses hash in the
         current_configuraion block."
    ::= { slbCurCfgGroupEntry 14 }

slbCurCfgGroupPhashMask OBJECT-TYPE
    SYNTAX  IpAddress
    MAX-ACCESS  read-only
    STATUS  current
    DESCRIPTION
        "IP address mask used by the persistent hash metric."
    ::= { slbCurCfgGroupEntry 15 }

slbCurCfgGroupRmetric OBJECT-TYPE
    SYNTAX  INTEGER {
	roundRobin(1),
	hash(2)
	}
    MAX-ACCESS  read-only
    STATUS  current
    DESCRIPTION
        "The metric used to select next rport in server."
    ::= { slbCurCfgGroupEntry 16 }

slbCurCfgGroupHealthCheckFormula OBJECT-TYPE
    SYNTAX  DisplayString (SIZE(0..31))
    MAX-ACCESS  read-only
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formuala to mark the server group failed for the virtual server 
         if 1 and 2 FAILED or 3 and 4 FAILED is (1|2)&(3|4)
         This formula will mark the virtual server UP, if 1 or 2 and 3 or 4
         are health checked sucessfully."
    ::= { slbCurCfgGroupEntry 17 }

slbCurCfgGroupOperatorAccess OBJECT-TYPE
    SYNTAX  INTEGER {
	enabled(1),
	disabled(2)
	}
    MAX-ACCESS  read-only
    STATUS  current
    DESCRIPTION
        "Enable or disable access to this group for operator."
    ::= { slbCurCfgGroupEntry 18 }

slbCurCfgGroupWlm OBJECT-TYPE
    SYNTAX  Integer32
    MAX-ACCESS  read-only
    STATUS  current
    DESCRIPTION
        "The Workload Manager for this Group."
    ::= { slbCurCfgGroupEntry 19 }

-- Server load balancing - Group Table - New Configuration
slbNewCfgGroupTable OBJECT-TYPE
    SYNTAX  SEQUENCE OF SlbNewCfgGroupEntry
    MAX-ACCESS  not-accessible
    STATUS  current
    DESCRIPTION
        "The table of groups"
    ::= { realServerGroupCfg 4 }

slbNewCfgGroupEntry OBJECT-TYPE
    SYNTAX  SlbNewCfgGroupEntry
    MAX-ACCESS  not-accessible
    STATUS  current
    DESCRIPTION
        "A row in the slbNewCfgGroupTable "
    INDEX   { slbNewCfgGroupIndex }
    ::= { slbNewCfgGroupTable 1 }

SlbNewCfgGroupEntry ::= SEQUENCE {
    slbNewCfgGroupIndex              Integer32,
    slbNewCfgGroupRealServers        OCTET STRING,
    slbNewCfgGroupAddServer          Integer32,
    slbNewCfgGroupRemoveServer       Integer32,
    slbNewCfgGroupMetric             INTEGER,
    slbNewCfgGroupBackupServer       Integer32,
    slbNewCfgGroupBackupGroup	     Integer32,
    slbNewCfgGroupHealthCheckUrl     DisplayString,
    slbNewCfgGroupHealthCheckLayer   INTEGER,
    slbNewCfgGroupRealThreshold	     INTEGER,
    slbNewCfgGroupVipHealthCheck     INTEGER,
    slbNewCfgGroupIdsState           INTEGER,
    slbNewCfgGroupIdsPort            INTEGER,
    slbNewCfgGroupDelete             INTEGER,
    slbNewCfgGroupIdsFlood           INTEGER,
    slbNewCfgGroupMinmissHash        INTEGER,
    slbNewCfgGroupPhashMask          IpAddress,
    slbNewCfgGroupRmetric            INTEGER,
    slbNewCfgGroupHealthCheckFormula DisplayString,
    slbNewCfgGroupWlm                Integer32,
    slbNewCfgGroupOperatorAccess     INTEGER,
    slbNewCfgGroupName               DisplayString
    }

slbNewCfgGroupIndex OBJECT-TYPE
    SYNTAX  Integer32
    MAX-ACCESS  read-only
    STATUS  current
    DESCRIPTION
        "The group number for which the information pertains."
    ::= { slbNewCfgGroupEntry 1 }

slbNewCfgGroupRealServers    OBJECT-TYPE
    SYNTAX  OCTET STRING
    MAX-ACCESS  read-only
    STATUS  current
    DESCRIPTION
        "The Real servers in the group.  The servers are presented
         in bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbNewCfgGroupEntry 2 }

slbNewCfgGroupAddServer OBJECT-TYPE
    SYNTAX  Integer32
    MAX-ACCESS  read-create
    STATUS  current
    DESCRIPTION
        "The real server to be added to the group. When read, 0 is returned."
    ::= { slbNewCfgGroupEntry 3 }

slbNewCfgGroupRemoveServer OBJECT-TYPE 
    SYNTAX  Integer32 
    MAX-ACCESS  read-create 
    STATUS  current
    DESCRIPTION
        "The real server to be removed from the group. When read, 
         0 is returned."
    ::= { slbNewCfgGroupEntry 4 }
  
slbNewCfgGroupMetric OBJECT-TYPE
    SYNTAX  INTEGER {  
	roundRobin(1),
	leastConnections(2),
	minMisses(3),
	hash(4),
	response(5),
	bandwidth(6),
        phash(7)
        }
    MAX-ACCESS  read-create
    STATUS  current
    DESCRIPTION
        "The metric used to select next server in group."
    ::= { slbNewCfgGroupEntry 5 }

slbNewCfgGroupBackupServer OBJECT-TYPE
    SYNTAX  Integer32
    MAX-ACCESS  read-create
    STATUS  current
    DESCRIPTION
        "The backup real server for this group."
    ::= { slbNewCfgGroupEntry 6 }

slbNewCfgGroupBackupGroup OBJECT-TYPE
    SYNTAX  Integer32
    MAX-ACCESS  read-create
    STATUS  current
    DESCRIPTION
        "The backup real server group for this group."
    ::= { slbNewCfgGroupEntry 7 }

slbNewCfgGroupHealthCheckUrl OBJECT-TYPE
    SYNTAX  DisplayString (SIZE(0..127))
    MAX-ACCESS  read-create
    STATUS  current
    DESCRIPTION
        "The specific content which is examined during health checks.
         The content depends on the type of health check."
    ::= { slbNewCfgGroupEntry 8 }

slbNewCfgGroupHealthCheckLayer OBJECT-TYPE
    SYNTAX  INTEGER {
	icmp(1),
	tcp(2),
	http(3),
	httphead(44),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33),
	snmp1(34),
	snmp2(35),
	snmp3(36),
	snmp4(37),
	snmp5(38),
        radiusacs(39),
        tftp(40),
        wtp(41),
        rtsp(42),
        sipping(43),
        sipoptions(45),
        wts(46),
        script17(116),
	script18(117),
	script19(118),
	script20(119),
	script21(120),
	script22(121),
	script23(122),
	script24(123),
	script25(124),
	script26(125),
	script27(126),
	script28(127),
	script29(128),
	script30(129),
	script31(130),
	script32(131),
        script33(132),
	script34(133),
	script35(134),
	script36(135),
	script37(136),
	script38(137),
	script39(138),
	script40(139),
	script41(140),
	script42(141),
	script43(142),
	script44(143),
	script45(144),
	script46(145),
	script47(146),
	script48(147),
        script49(148),
	script50(149),
	script51(150),
	script52(151),
	script53(152),
	script54(153),
	script55(154),
	script56(155),
	script57(156),
	script58(157),
	script59(158),
	script60(159),
	script61(160),
	script62(161),
	script63(162),
	script64(163)
	}
    MAX-ACCESS  read-create
    STATUS  current
    DESCRIPTION
        "The OSI layer at which servers are health checked."
    ::= { slbNewCfgGroupEntry 9 }

slbNewCfgGroupName OBJECT-TYPE 
    SYNTAX  DisplayString (SIZE(0..31))
    MAX-ACCESS  read-create 
    STATUS  current 
    DESCRIPTION 
        "The name of the real server group."  
    ::= { slbNewCfgGroupEntry 10 }

slbNewCfgGroupRealThreshold OBJECT-TYPE 
    SYNTAX  INTEGER (0..15)
    MAX-ACCESS  read-create 
    STATUS  current 
    DESCRIPTION 
        "The minimum number of real servers available. If at any time, the 
         number reaches this minimum limit, a SYSLOG ALERT message is send to 
         to the configured syslog servers stating that the real server 
         threshold has been reached for the concerned group."  
    ::= { slbNewCfgGroupEntry 11 }

slbNewCfgGroupVipHealthCheck OBJECT-TYPE
    SYNTAX  INTEGER {
	enabled(1),
	disabled(2)
	}
    MAX-ACCESS  read-create
    STATUS  current
    DESCRIPTION
        "Enable or disable VIP health checking in DSR mode." 
    ::= { slbNewCfgGroupEntry 12 }

slbNewCfgGroupIdsState OBJECT-TYPE
    SYNTAX  INTEGER {
	enabled(1),
	disabled(2)
	}
    MAX-ACCESS  read-create
    STATUS  current
    DESCRIPTION
        "Enable or disable intrusion detection."
    ::= { slbNewCfgGroupEntry 13 }

slbNewCfgGroupIdsPort OBJECT-TYPE
    SYNTAX  INTEGER (0..65534)
    MAX-ACCESS  read-create
    STATUS  current
    DESCRIPTION
        "The intrusion detection port. A value of 1 is invalid."
    ::= { slbNewCfgGroupEntry 14 }

slbNewCfgGroupDelete OBJECT-TYPE
    SYNTAX  INTEGER {
	other(1),
	delete(2)
	}
    MAX-ACCESS  read-create
    STATUS  current
    DESCRIPTION
        "By setting the value to delete(2), the entire group is deleted."
    ::= { slbNewCfgGroupEntry 15 }

slbNewCfgGroupIdsFlood OBJECT-TYPE
    SYNTAX  INTEGER {
	enabled(1),
	disabled(2)
	}
    MAX-ACCESS  read-create
    STATUS  current
    DESCRIPTION
        "Enable or disable intrusion detection group flood."
    ::= { slbNewCfgGroupEntry 16 }

slbNewCfgGroupMinmissHash OBJECT-TYPE
    SYNTAX  INTEGER {
        minmiss-24(1),
        minmiss-32(2)
        }
    MAX-ACCESS  read-create
    STATUS  current
    DESCRIPTION
        "24|32 number of sip bits used for minmisses hash in the
         new_configuraion block."
    ::= { slbNewCfgGroupEntry 17 }

slbNewCfgGroupPhashMask OBJECT-TYPE
    SYNTAX  IpAddress
    MAX-ACCESS  read-create
    STATUS  current
    DESCRIPTION
        "IP address mask used by the persistent hash metric."
    ::= { slbNewCfgGroupEntry 18 }

slbNewCfgGroupRmetric OBJECT-TYPE
    SYNTAX  INTEGER {  
	roundRobin(1),
	hash(2)
        }
    MAX-ACCESS  read-create
    STATUS  current
    DESCRIPTION
        "The metric used to select next rport in server."
    ::= { slbNewCfgGroupEntry 19 }

slbNewCfgGroupHealthCheckFormula OBJECT-TYPE
    SYNTAX  DisplayString (SIZE(0..31))
    MAX-ACCESS  read-create 
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formuala to mark the server group failed for the virtual server 
         if 1 and 2 FAILED or 3 and 4 FAILED is (1|2)&(3|4)
         This formula will mark the virtual server UP, if 1 or 2 and 3 or 4
         are health checked sucessfully."
    ::= { slbNewCfgGroupEntry 20 }

slbNewCfgGroupOperatorAccess OBJECT-TYPE
    SYNTAX  INTEGER {
	enabled(1),
	disabled(2)
	}
    MAX-ACCESS  read-create
    STATUS  current
    DESCRIPTION
        "Enable or disable access to this group for operator."
    ::= { slbNewCfgGroupEntry 21 }

slbNewCfgGroupWlm OBJECT-TYPE
    SYNTAX  Integer32
    MAX-ACCESS  read-create
    STATUS  current
    DESCRIPTION
        "The Workload Manager for this Group."
    ::= { slbNewCfgGroupEntry 22 }

-- SLB - Group Real Server Table
slbCurCfgGroupRealServerTable OBJECT-TYPE
    SYNTAX  SEQUENCE OF SlbCurCfgGroupRealServerEntry
    MAX-ACCESS  not-accessible
    STATUS  current
    DESCRIPTION
        "The table of real servers per group."
    ::= { realServerGroupCfg 5 }

slbCurCfgGroupRealServerEntry OBJECT-TYPE
    SYNTAX  SlbCurCfgGroupRealServerEntry
    MAX-ACCESS  not-accessible
    STATUS  current
    DESCRIPTION
        "A row in the Real server group table."
    INDEX   { slbCurCfgRealServGroupIndex, slbCurCfgGroupRealServIndex }
    ::= { slbCurCfgGroupRealServerTable 1 }

SlbCurCfgGroupRealServerEntry ::= SEQUENCE {
    slbCurCfgRealServGroupIndex       Integer32,
    slbCurCfgGroupRealServIndex       Integer32,
    slbCurCfgGroupRealServerState     INTEGER
    }

slbCurCfgRealServGroupIndex OBJECT-TYPE
    SYNTAX  Integer32
    MAX-ACCESS  read-only
    STATUS  current
    DESCRIPTION
        "The real server group index." 
    ::= { slbCurCfgGroupRealServerEntry 1 }

slbCurCfgGroupRealServIndex OBJECT-TYPE
    SYNTAX  Integer32
    MAX-ACCESS  read-only
    STATUS  current
    DESCRIPTION
        "The real server index." 
    ::= { slbCurCfgGroupRealServerEntry 2 }

slbCurCfgGroupRealServerState OBJECT-TYPE
    SYNTAX  INTEGER {
	enabled(1),
	disabled(2)
	}
    MAX-ACCESS  read-only
    STATUS  current
    DESCRIPTION
        "Enable/disable a real server gracefully on a per group basis." 
    ::= { slbCurCfgGroupRealServerEntry 3 }

slbNewCfgGroupRealServerTable OBJECT-TYPE
    SYNTAX  SEQUENCE OF SlbNewCfgGroupRealServerEntry
    MAX-ACCESS  not-accessible
    STATUS  current
    DESCRIPTION
        "The table of real server per group."
    ::= { realServerGroupCfg 6 }

slbNewCfgGroupRealServerEntry OBJECT-TYPE
    SYNTAX  SlbNewCfgGroupRealServerEntry
    MAX-ACCESS  not-accessible
    STATUS  current
    DESCRIPTION
        "A row in the Real server group table."
    INDEX   { slbNewCfgRealServGroupIndex, slbNewCfgGroupRealServIndex}
    ::= { slbNewCfgGroupRealServerTable 1 }

SlbNewCfgGroupRealServerEntry ::= SEQUENCE {
    slbNewCfgRealServGroupIndex        Integer32,
    slbNewCfgGroupRealServIndex        Integer32,
    slbNewCfgGroupRealServerState      INTEGER
    }

slbNewCfgRealServGroupIndex OBJECT-TYPE
    SYNTAX  Integer32
    MAX-ACCESS  read-only
    STATUS  current
    DESCRIPTION
        "The real server group index." 
    ::= { slbNewCfgGroupRealServerEntry 1 }

slbNewCfgGroupRealServIndex OBJECT-TYPE
    SYNTAX  Integer32
    MAX-ACCESS  read-only
    STATUS  current
    DESCRIPTION
        "The real server index." 
    ::= { slbNewCfgGroupRealServerEntry 2 }

slbNewCfgGroupRealServerState OBJECT-TYPE
    SYNTAX  INTEGER {
	enabled(1),
	disabled(2)
	}
    MAX-ACCESS  read-create
    STATUS  current
    DESCRIPTION
        "Enable/disable a real server gracefully on a per group basis." 
    ::= { slbNewCfgGroupRealServerEntry 3 }

-- Server load balancing - Virtual Server Table
slbVirtServerTableMaxSize OBJECT-TYPE
    SYNTAX  Integer32
    MAX-ACCESS  read-only
    STATUS  current
    DESCRIPTION
        "The maximum number of entries in SLB VirtServerTable."
    ::= { virtualServerCfg 1 }

slbCurCfgVirtServerTable OBJECT-TYPE
    SYNTAX  SEQUENCE OF SlbCurCfgVirtualServerEntry
    MAX-ACCESS  not-accessible
    STATUS  current
    DESCRIPTION
        "The table of virtual Servers."
    ::= { virtualServerCfg 2 }
 
slbCurCfgVirtualServerEntry OBJECT-TYPE
    SYNTAX  SlbCurCfgVirtualServerEntry
    MAX-ACCESS  not-accessible
    STATUS  current
    DESCRIPTION
        "A row in the virtual server table."
    INDEX   { slbCurCfgVirtServerIndex }
    ::= { slbCurCfgVirtServerTable 1 }
 
SlbCurCfgVirtualServerEntry ::= SEQUENCE {
    slbCurCfgVirtServerIndex     	Integer32,
    slbCurCfgVirtServerIpAddress 	IpAddress,
    slbCurCfgVirtServerLayer3Only    	INTEGER,
    slbCurCfgVirtServerState     	INTEGER,
    slbCurCfgVirtServerDname     	DisplayString,
    slbCurCfgVirtServerBwmContract	Integer32,
    slbCurCfgVirtServerWeight           INTEGER,
    slbCurCfgVirtServerAvail            INTEGER,
    slbCurCfgVirtServerRule             OCTET STRING,
    slbCurCfgVirtServerIpVer            INTEGER,
    slbCurCfgVirtServerIpv6Addr         DisplayString,
    slbCurCfgVirtServerVname     	DisplayString
    }

slbCurCfgVirtServerIndex OBJECT-TYPE
    SYNTAX  Integer32
    MAX-ACCESS  read-only
    STATUS  current
    DESCRIPTION
        "Virtual Server Number" 
    ::= { slbCurCfgVirtualServerEntry 1 }

slbCurCfgVirtServerIpAddress OBJECT-TYPE
    SYNTAX  IpAddress
    MAX-ACCESS  read-only
    STATUS  current
    DESCRIPTION
        "IP address of the virtual server." 
    ::= { slbCurCfgVirtualServerEntry 2 }

slbCurCfgVirtServerLayer3Only OBJECT-TYPE 
    SYNTAX  INTEGER {
	layer3Only(1),
	disabled(2)
	}
    MAX-ACCESS  read-only 
    STATUS  current 
    DESCRIPTION 
        "Enable or disable layer3 only balancing."  
    ::= { slbCurCfgVirtualServerEntry 3 }

slbCurCfgVirtServerState OBJECT-TYPE 
    SYNTAX  INTEGER {
	enabled(2),
	disabled(3)
	}
    MAX-ACCESS  read-only 
    STATUS  current 
    DESCRIPTION 
        "Enable or disable the virtual server."  
    ::= { slbCurCfgVirtualServerEntry 4 }

slbCurCfgVirtServerDname OBJECT-TYPE 
    SYNTAX  DisplayString (SIZE(0..64))
    MAX-ACCESS  read-only 
    STATUS  current 
    DESCRIPTION 
        "The domain name of the virtual server."  
    ::= { slbCurCfgVirtualServerEntry 5 }

slbCurCfgVirtServerBwmContract OBJECT-TYPE
    SYNTAX  Integer32
    MAX-ACCESS  read-only
    STATUS  current
    DESCRIPTION
        "The default BW contract of virtual server."
    ::= { slbCurCfgVirtualServerEntry 6 }

slbCurCfgVirtServerWeight OBJECT-TYPE
    SYNTAX  INTEGER (1..48)
    MAX-ACCESS  read-only
    STATUS  current
    DESCRIPTION
        "The virtual server Global SLB weight."
    ::= { slbCurCfgVirtualServerEntry 7 }

slbCurCfgVirtServerAvail OBJECT-TYPE
    SYNTAX  INTEGER (1..48)
    MAX-ACCESS  read-only
    STATUS  current
    DESCRIPTION
        "The virtual server Global SLB availability."
    ::= { slbCurCfgVirtualServerEntry 8 }

slbCurCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbCurCfgVirtualServerEntry 9 }

slbCurCfgVirtServerVname OBJECT-TYPE 
    SYNTAX  DisplayString (SIZE(0..32))
    MAX-ACCESS  read-only 
    STATUS  current 
    DESCRIPTION 
        "The name of the virtual server."  
    ::= { slbCurCfgVirtualServerEntry 10 }


slbCurCfgVirtServerIpVer OBJECT-TYPE
    SYNTAX  INTEGER{
        ipv4(1),
        ipv6(2)
        }
    MAX-ACCESS  read-only
    STATUS  current
    DESCRIPTION
        "The type of IP address."
    ::= { slbCurCfgVirtualServerEntry 11 }

slbCurCfgVirtServerIpv6Addr OBJECT-TYPE
    SYNTAX   DisplayString (SIZE(0..40))
    MAX-ACCESS  read-only
    STATUS  current
    DESCRIPTION
        "The IPv6 address of the virtual server. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { slbCurCfgVirtualServerEntry 12 }


-- Server load balancing - Virtual Server Table

slbNewCfgVirtServerTable OBJECT-TYPE
    SYNTAX  SEQUENCE OF SlbNewCfgVirtualServerEntry
    MAX-ACCESS  not-accessible
    STATUS  current
    DESCRIPTION
        "The table of virtual Servers."
    ::= { virtualServerCfg 3 }

slbNewCfgVirtualServerEntry OBJECT-TYPE
    SYNTAX  SlbNewCfgVirtualServerEntry
    MAX-ACCESS  not-accessible
    STATUS  current
    DESCRIPTION
        "A row in the virtual server table."
    INDEX   { slbNewCfgVirtServerIndex }
    ::= { slbNewCfgVirtServerTable 1 }
 
SlbNewCfgVirtualServerEntry ::= SEQUENCE {
    slbNewCfgVirtServerIndex   		Integer32,
    slbNewCfgVirtServerIpAddress 	IpAddress,
    slbNewCfgVirtServerLayer3Only   	INTEGER,
    slbNewCfgVirtServerState     	INTEGER,
    slbNewCfgVirtServerDname     	DisplayString,
    slbNewCfgVirtServerBwmContract	Integer32,
    slbNewCfgVirtServerDelete    	INTEGER,
    slbNewCfgVirtServerWeight           INTEGER,
    slbNewCfgVirtServerAvail            INTEGER,
    slbNewCfgVirtServerRule             OCTET STRING,
    slbNewCfgVirtServerAddRule          Integer32,
    slbNewCfgVirtServerRemoveRule       Integer32,
    slbNewCfgVirtServerIpVer            INTEGER,
    slbNewCfgVirtServerIpv6Addr         DisplayString,
    slbNewCfgVirtServerVname     	DisplayString
    }

slbNewCfgVirtServerIndex OBJECT-TYPE
    SYNTAX  Integer32
    MAX-ACCESS  read-only
    STATUS  current
    DESCRIPTION
        "The Virtual Server Number" 
    ::= { slbNewCfgVirtualServerEntry 1 }

slbNewCfgVirtServerIpAddress OBJECT-TYPE
    SYNTAX  IpAddress
    MAX-ACCESS  read-create
    STATUS  current
    DESCRIPTION
        "IP address of the virtual server." 
    ::= { slbNewCfgVirtualServerEntry 2 }

slbNewCfgVirtServerLayer3Only OBJECT-TYPE 
    SYNTAX  INTEGER {
        layer3Only(1),
	disabled(2)
	}
    MAX-ACCESS  read-create 
    STATUS  current 
    DESCRIPTION 
        "Enable or disable layer3 only balancing."  
    ::= { slbNewCfgVirtualServerEntry 3 }

slbNewCfgVirtServerState OBJECT-TYPE 
    SYNTAX  INTEGER {
	enabled(2),
	disabled(3)
	}
    MAX-ACCESS  read-create 
    STATUS  current 
    DESCRIPTION 
        "Enable or disable the virtual server."  
    ::= { slbNewCfgVirtualServerEntry 4 }

slbNewCfgVirtServerDname OBJECT-TYPE 
    SYNTAX  DisplayString (SIZE(0..64))
    MAX-ACCESS  read-create 
    STATUS  current 
    DESCRIPTION 
        "The domain name of the virtual server."  
    ::= { slbNewCfgVirtualServerEntry 6 }

slbNewCfgVirtServerBwmContract OBJECT-TYPE 
    SYNTAX  Integer32
    MAX-ACCESS  read-create 
    STATUS  current 
    DESCRIPTION 
        "The default BW contract number of the virtual server."
    ::= { slbNewCfgVirtualServerEntry 7 }

slbNewCfgVirtServerDelete OBJECT-TYPE
    SYNTAX  INTEGER {
        other(1),
        delete(2)
        }
    MAX-ACCESS  read-create
    STATUS  current
    DESCRIPTION
        "By setting the value to delete(2), the entire row is deleted."
    ::= { slbNewCfgVirtualServerEntry 8 }

slbNewCfgVirtServerWeight OBJECT-TYPE
    SYNTAX  INTEGER (1..48)
    MAX-ACCESS  read-create
    STATUS  current
    DESCRIPTION
        "The virtual server Global SLB weight."
    ::= { slbNewCfgVirtualServerEntry 9 }

slbNewCfgVirtServerAvail OBJECT-TYPE
    SYNTAX  INTEGER (1..48)
    MAX-ACCESS  read-create
    STATUS  current
    DESCRIPTION
        "The virtual server Global SLB availability."
    ::= { slbNewCfgVirtualServerEntry 10 }

slbNewCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbNewCfgVirtualServerEntry 11 }

slbNewCfgVirtServerAddRule OBJECT-TYPE
    SYNTAX  Integer32
    MAX-ACCESS  read-create
    STATUS  current
    DESCRIPTION
        "The rule to be added to the domain. When read, 0 is returned."
    ::= { slbNewCfgVirtualServerEntry 12 }

slbNewCfgVirtServerRemoveRule OBJECT-TYPE
    SYNTAX  Integer32
    MAX-ACCESS  read-create
    STATUS  current
    DESCRIPTION
        "The rule to be removed from the domain. When read, 0 is returned."
    ::= { slbNewCfgVirtualServerEntry 13 }

slbNewCfgVirtServerVname OBJECT-TYPE 
    SYNTAX  DisplayString (SIZE(0..32))
    MAX-ACCESS  read-create 
    STATUS  current 
    DESCRIPTION 
        "The name of the virtual server."  
    ::= { slbNewCfgVirtualServerEntry 14 }


slbNewCfgVirtServerIpVer OBJECT-TYPE
    SYNTAX  INTEGER{
        ipv4(1),
        ipv6(2)
        }
    MAX-ACCESS read-create
    STATUS  current
    DESCRIPTION
        "The type of IP address."
    ::= { slbNewCfgVirtualServerEntry 15 }

slbNewCfgVirtServerIpv6Addr OBJECT-TYPE
    SYNTAX  DisplayString  (SIZE(0..40))
    MAX-ACCESS read-create
    STATUS  current
    DESCRIPTION
        "The IPv6 address of the virtual server. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { slbNewCfgVirtualServerEntry 16 }


-- Server load balancing - Virtual Services Table 
slbVirtServicesTableMaxSize OBJECT-TYPE
    SYNTAX  Integer32 
    MAX-ACCESS  read-only 
    STATUS  current 
    DESCRIPTION 
        "The maximum number of entries in SLB Virtual Services Table." 
    ::= { virtualServerCfg 4 }

slbCurCfgVirtServicesTable OBJECT-TYPE
    SYNTAX  SEQUENCE OF SlbCurCfgVirtServicesEntry
    MAX-ACCESS  not-accessible
    STATUS  current
    DESCRIPTION
        "The table of virtual services."
    ::= { virtualServerCfg 5 }

slbCurCfgVirtServicesEntry OBJECT-TYPE
    SYNTAX  SlbCurCfgVirtServicesEntry
    MAX-ACCESS  not-accessible
    STATUS  current
    DESCRIPTION
        "A row in the virtual services table."
    INDEX   { slbCurCfgVirtServIndex, slbCurCfgVirtServiceIndex }
    ::= { slbCurCfgVirtServicesTable 1 }

SlbCurCfgVirtServicesEntry ::= SEQUENCE {
    slbCurCfgVirtServIndex            Integer32,
    slbCurCfgVirtServiceIndex         Integer32,
    slbCurCfgVirtServiceVirtPort      INTEGER,
    slbCurCfgVirtServiceRealGroup     Integer32,
    slbCurCfgVirtServiceRealPort      INTEGER,
    slbCurCfgVirtServiceUDPBalance    INTEGER,
    slbCurCfgVirtServiceHname         DisplayString,
    slbCurCfgVirtServiceBwmContract   Integer32,
    slbCurCfgVirtServiceDirServerRtn  INTEGER,
    slbCurCfgVirtServiceRtspUrlParse  INTEGER,
    slbCurCfgVirtServiceFtpParsing    INTEGER,
    slbCurCfgVirtServiceRemapUDPFrags INTEGER,
    slbCurCfgVirtServiceDnsSlb        INTEGER,
    slbCurCfgVirtServiceResponseCount INTEGER,
    slbCurCfgVirtServicePBind         INTEGER,
    slbCurCfgVirtServiceCname         DisplayString,
    slbCurCfgVirtServiceCoffset       INTEGER,
    slbCurCfgVirtServiceClength       INTEGER,
    slbCurCfgVirtServiceUriCookie     INTEGER,
    slbCurCfgVirtServiceCExpire       DisplayString,
    slbCurCfgVirtServiceCookieMode    INTEGER,
    slbCurCfgVirtServiceDBind         INTEGER,
    slbCurCfgVirtServiceHttpSlb       INTEGER,
    slbCurCfgVirtServiceHttpSlbOption INTEGER,
    slbCurCfgVirtServiceHttpSlb2      INTEGER,
    slbCurCfgVirtServiceHttpHdrName   DisplayString,
    slbCurCfgVirtServiceUrlHashLen    INTEGER,
    slbCurCfgVirtServiceCookieDname   INTEGER,
    slbCurCfgVirtServiceDirect        INTEGER,
    slbCurCfgVirtServiceThash         INTEGER,
    slbCurCfgVirtServiceLdapreset     INTEGER,
    slbCurCfgVirtServiceLdapslb       INTEGER,
    slbCurCfgVirtServiceSip           INTEGER,
    slbCurCfgVirtServiceXForwardedFor INTEGER,
    slbCurCfgVirtServiceHttpRedir     INTEGER,
    slbCurCfgVirtServicePbindRport    INTEGER,
    slbCurCfgVirtServiceEgressPip     INTEGER,
    slbCurCfgVirtServiceWts           INTEGER,
    slbCurCfgVirtServiceTimeOut       INTEGER,
    slbCurCfgVirtServiceSoftGrid      INTEGER,
    slbCurCfgVirtServiceSessionMirror INTEGER,
    slbCurCfgVirtServiceSdpNat        INTEGER,
    slbCurCfgVirtServiceConnPooling   INTEGER,
    slbCurCfgVirtServiceUhash         INTEGER
    }

slbCurCfgVirtServIndex OBJECT-TYPE
    SYNTAX  Integer32
    MAX-ACCESS  read-only
    STATUS  current
    DESCRIPTION
        "The number of the virtual server." 
    ::= { slbCurCfgVirtServicesEntry 1 }

slbCurCfgVirtServiceIndex OBJECT-TYPE 
    SYNTAX  Integer32 
    MAX-ACCESS  read-only 
    STATUS  current 
    DESCRIPTION 
        "The service index. This has no external meaning" 
    ::= { slbCurCfgVirtServicesEntry 2 }


slbCurCfgVirtServiceVirtPort OBJECT-TYPE  
    SYNTAX  INTEGER (9..65534)
    MAX-ACCESS  read-only  
    STATUS  current  
    DESCRIPTION 
        "The layer4 virtual port number of the service."  
    ::= { slbCurCfgVirtServicesEntry 3 } 

slbCurCfgVirtServiceRealGroup OBJECT-TYPE   
    SYNTAX  Integer32   
    MAX-ACCESS  read-only   
    STATUS  current   
    DESCRIPTION 
        "The real server group number for this service."   
    ::= { slbCurCfgVirtServicesEntry 4 }

slbCurCfgVirtServiceRealPort OBJECT-TYPE   
    SYNTAX  INTEGER (0..65534)
    MAX-ACCESS  read-only   
    STATUS  current   
    DESCRIPTION 
        "The layer4 real port number of the service."   
    ::= { slbCurCfgVirtServicesEntry 5 }

slbCurCfgVirtServiceUDPBalance OBJECT-TYPE   
    SYNTAX  INTEGER    {
	enabled(2),
	disabled(3),
	stateless(4)
	}
    MAX-ACCESS  read-only   
    STATUS  current   
    DESCRIPTION 
        "Enable, disable or stateless the UDP balancing for the virtual port."
    ::= { slbCurCfgVirtServicesEntry 6 }

slbCurCfgVirtServiceHname OBJECT-TYPE 
    SYNTAX  DisplayString (SIZE(0..34))
    MAX-ACCESS  read-only 
    STATUS  current 
    DESCRIPTION 
        "The host name of the virtual service."  
    ::= { slbCurCfgVirtServicesEntry 7 }

slbCurCfgVirtServiceBwmContract OBJECT-TYPE   
    SYNTAX  Integer32   
    MAX-ACCESS  read-only   
    STATUS  current   
    DESCRIPTION 
        "The BWM contract number for this service."   
    ::= { slbCurCfgVirtServicesEntry 8 }

slbCurCfgVirtServiceDirServerRtn OBJECT-TYPE   
    SYNTAX  INTEGER {
	enabled(1),
	disabled(2)
	}
    MAX-ACCESS  read-only   
    STATUS  current   
    DESCRIPTION 
        "Enable or disable direct server return feature. To translate only 
         MAC addresses in performing server load balancing when enabled.
         This allow servers to return directly to client since IP addresses 
         have not been changed."
    ::= { slbCurCfgVirtServicesEntry 9 }

slbCurCfgVirtServiceRtspUrlParse OBJECT-TYPE   
    SYNTAX  INTEGER {
        none(1),
        l4hash(2),
        hash(3),
        patternMatch(4) 
	}
    MAX-ACCESS  read-only   
    STATUS  current   
    DESCRIPTION 
        "Select RTSP URL load balancing type."
    ::= { slbCurCfgVirtServicesEntry 10 }

slbCurCfgVirtServiceDBind OBJECT-TYPE   
    SYNTAX  INTEGER {
	enabled(1),
	disabled(2)
	}
    MAX-ACCESS  read-only   
    STATUS  current   
    DESCRIPTION 
        "Enable or disable Delayed Binding."
    ::= { slbCurCfgVirtServicesEntry 11 }

slbCurCfgVirtServiceFtpParsing OBJECT-TYPE
    SYNTAX  INTEGER {
	enabled(1),
	disabled(2)
	}
    MAX-ACCESS  read-only
    STATUS  current
    DESCRIPTION
       "Enable or Disable the ftp parsing for the virtual service."
    ::= { slbCurCfgVirtServicesEntry 12 }

slbCurCfgVirtServiceRemapUDPFrags OBJECT-TYPE   
    SYNTAX INTEGER {
        enabled(1),
        disabled(2)
        }
    MAX-ACCESS read-only   
    STATUS current   
    DESCRIPTION 
        "Enable or disable remapping UDP server fragments"   
    ::= { slbCurCfgVirtServicesEntry 13 }

slbCurCfgVirtServiceDnsSlb OBJECT-TYPE   
    SYNTAX  INTEGER {
        enabled(1),
	disabled(2)
	}
    MAX-ACCESS  read-only   
    STATUS  current   
    DESCRIPTION 
        "Enable or disable DNS query load balancing."
    ::= { slbCurCfgVirtServicesEntry 14 }

slbCurCfgVirtServiceResponseCount OBJECT-TYPE 
    SYNTAX  INTEGER (1..16)
    MAX-ACCESS  read-only
    STATUS  current 
    DESCRIPTION 
        "The number of cookie search response count."
    ::= { slbCurCfgVirtServicesEntry 15 }

slbCurCfgVirtServicePBind OBJECT-TYPE   
    SYNTAX  INTEGER {
	clientip(2),
	disabled(3),
	sslid(4),
        cookie(5)
        }
    MAX-ACCESS  read-only   
    STATUS  current   
    DESCRIPTION 
        "Enable or disable persistent bindings for the virtual port."   
    ::= { slbCurCfgVirtServicesEntry 16 }

slbCurCfgVirtServiceCname OBJECT-TYPE 
    SYNTAX  DisplayString (SIZE(0..20))
    MAX-ACCESS  read-only 
    STATUS  current 
    DESCRIPTION 
        "The cookie name of the virtual server used for cookie load balance."  
    ::= { slbCurCfgVirtServicesEntry 17 }

slbCurCfgVirtServiceCoffset OBJECT-TYPE
    SYNTAX  INTEGER (0..128)
    MAX-ACCESS  read-only
    STATUS  current
    DESCRIPTION
        "The starting byte offset of the cookie value." 
    ::= { slbCurCfgVirtServicesEntry 18 }

slbCurCfgVirtServiceClength OBJECT-TYPE
    SYNTAX  INTEGER (0..128)
    MAX-ACCESS  read-only
    STATUS  current
    DESCRIPTION
        "The number of bytes to extract from the cookie value." 
    ::= { slbCurCfgVirtServicesEntry 19 }

slbCurCfgVirtServiceUriCookie OBJECT-TYPE 
    SYNTAX  INTEGER {
	enabled(1),
	disabled(2)
	}
    MAX-ACCESS  read-only 
    STATUS  current 
    DESCRIPTION 
        "Enable or disable cookie search in URI"  
    ::= { slbCurCfgVirtServicesEntry 20 }

slbCurCfgVirtServiceCExpire OBJECT-TYPE 
    SYNTAX  DisplayString (SIZE(0..20))
    MAX-ACCESS  read-only 
    STATUS  current 
    DESCRIPTION 
        "The cookie expire of the virtual server used for insert cookie load
         balance depending on the mode it has the following format 
         <MM/dd/yy[@hh:mm]> absolute mode or <days[:hours[:minutes]]>
         for relative mode."  
    ::= { slbCurCfgVirtServicesEntry 21 }

slbCurCfgVirtServiceCookieMode OBJECT-TYPE   
    SYNTAX INTEGER {
        rewrite(1),
        passive(2),
	insert(3),
	disabled(4)
        }
    MAX-ACCESS read-only 
    STATUS current   
    DESCRIPTION 
        "Select cookie persistance mode."
    ::= { slbCurCfgVirtServicesEntry 22 }

slbCurCfgVirtServiceHttpSlb OBJECT-TYPE   
    SYNTAX  INTEGER {
	disabled(1),
	urlslb(2),
        urlhash(3),
        cookie(4),
        host(5),
        browser(6),
        others(7),
        headerhash(8) 
	}
    MAX-ACCESS  read-only   
    STATUS  current   
    DESCRIPTION 
        "Select HTTP server loadbalancing for the virtual port."   
    ::= { slbCurCfgVirtServicesEntry 23 }

slbCurCfgVirtServiceHttpSlbOption OBJECT-TYPE   
    SYNTAX  INTEGER {
	and(1),
	or(2),
        none(3)
	}
    MAX-ACCESS  read-only   
    STATUS  current   
    DESCRIPTION 
        "Select HTTP server loadbalancing option for the virtual port."   
    ::= { slbCurCfgVirtServicesEntry 24 }

slbCurCfgVirtServiceHttpSlb2 OBJECT-TYPE   
    SYNTAX  INTEGER {
	disabled(1),
	urlslb(2),
        urlhash(3),
        cookie(4),
        host(5),
        browser(6),
        others(7),
        headerhash(8) 
	}
    MAX-ACCESS  read-only   
    STATUS  current   
    DESCRIPTION 
        "Select HTTP server loadbalancing for the virtual port."   
    ::= { slbCurCfgVirtServicesEntry 25 }

slbCurCfgVirtServiceHttpHdrName OBJECT-TYPE
    SYNTAX  DisplayString (SIZE(0..32))
    MAX-ACCESS  read-only
    STATUS  current
    DESCRIPTION
        "The HTTP header name of the virtual server."
    ::= { slbCurCfgVirtServicesEntry 26 }

slbCurCfgVirtServiceUrlHashLen OBJECT-TYPE
    SYNTAX  INTEGER (0..255)
    MAX-ACCESS  read-only
    STATUS  current
    DESCRIPTION
        "The number of bytes used to hash onto server. A zero means 
         URL hashing disabled."
    ::= { slbCurCfgVirtServicesEntry 27 }

slbCurCfgVirtServiceDirect OBJECT-TYPE   
    SYNTAX  INTEGER {
        enabled(1),
	disabled(2)
	}
    MAX-ACCESS  read-only   
    STATUS  current   
    DESCRIPTION 
        "Enable or disable DAM for this service."                
    ::= { slbCurCfgVirtServicesEntry 28 }

slbCurCfgVirtServiceThash OBJECT-TYPE   
    SYNTAX  INTEGER {
        sip(1),
        sip-sport(2)
        }
    MAX-ACCESS  read-only   
    STATUS  current   
    DESCRIPTION 
        "Set hash parameter."
    ::= { slbCurCfgVirtServicesEntry 29 }

slbCurCfgVirtServiceLdapreset OBJECT-TYPE 
    SYNTAX  INTEGER {
        enabled(1),
        disabled(2)
        }
    MAX-ACCESS  read-only 
    STATUS  current 
    DESCRIPTION 
        "Enable or disable LDAP Server Reset"  
    ::= { slbCurCfgVirtServicesEntry 30 }

slbCurCfgVirtServiceLdapslb OBJECT-TYPE 
    SYNTAX  INTEGER {
        enabled(1),
        disabled(2)
        }
    MAX-ACCESS  read-only 
    STATUS  current 
    DESCRIPTION 
        "Enable or disable LDAP Server load balancing"  
    ::= { slbCurCfgVirtServicesEntry 31 }

slbCurCfgVirtServiceSip OBJECT-TYPE   
    SYNTAX  INTEGER {
        enabled(1),
	disabled(2)
	}
    MAX-ACCESS  read-only   
    STATUS  current   
    DESCRIPTION 
        "Enable/disable SIP load balancing."
    ::= { slbCurCfgVirtServicesEntry 32 }
    
slbCurCfgVirtServiceXForwardedFor OBJECT-TYPE   
    SYNTAX  INTEGER {
        enabled(1),
	disabled(2)
	}
    MAX-ACCESS  read-only   
    STATUS  current   
    DESCRIPTION 
        "Enable/disable X-Forwarded-For for proxy mode."
    ::= { slbCurCfgVirtServicesEntry 33 }

slbCurCfgVirtServiceHttpRedir OBJECT-TYPE
    SYNTAX  INTEGER {
        enabled(1),
        disabled(2)
        }
    MAX-ACCESS  read-only
    STATUS  current
    DESCRIPTION
        "Enable/disable HTTP redirect for GSLB."
    ::= { slbCurCfgVirtServicesEntry 34 }

slbCurCfgVirtServicePbindRport OBJECT-TYPE   
    SYNTAX  INTEGER {
        enabled(1),
	disabled(2)
	}
    MAX-ACCESS  read-only   
    STATUS  current   
    DESCRIPTION 
        "Enable or disable use of rport in the session lookup for a persistent
         session."
    ::= { slbCurCfgVirtServicesEntry 35 }
    
slbCurCfgVirtServiceEgressPip OBJECT-TYPE   
    SYNTAX  INTEGER {
        enabled(1),
	disabled(2)
	}
    MAX-ACCESS  read-only   
    STATUS  current   
    DESCRIPTION 
        "Enable/disable pip selection based on egress port/vlan."
    ::= { slbCurCfgVirtServicesEntry 36 }

slbCurCfgVirtServiceCookieDname OBJECT-TYPE
    SYNTAX INTEGER {
        enabled(1),
        disabled(2)
        }
    MAX-ACCESS read-only
    STATUS current
    DESCRIPTION
        "Select dname for insert cookie persistance mode."
    ::= { slbCurCfgVirtServicesEntry 37 }
    
slbCurCfgVirtServiceWts OBJECT-TYPE
    SYNTAX INTEGER {
        enabled(1),
        disabled(2)
        }
    MAX-ACCESS read-only
    STATUS current
    DESCRIPTION
        "Enable or disable WTS loadbalancing and persistance."
    ::= { slbCurCfgVirtServicesEntry 38 }

slbCurCfgVirtServiceUhash OBJECT-TYPE
    SYNTAX INTEGER {
        enabled(1),
        disabled(2)
        }
    MAX-ACCESS read-only
    STATUS current
    DESCRIPTION
        "Enable when there is no Session Directory server."
    ::= { slbCurCfgVirtServicesEntry 39 }

slbCurCfgVirtServiceTimeOut OBJECT-TYPE
    SYNTAX  INTEGER (0..32768)
    MAX-ACCESS  read-only
    STATUS  current
    DESCRIPTION
        "The maximum number of minutes an inactive connection remains open."
    ::= { slbCurCfgVirtServicesEntry 40 }
slbCurCfgVirtServiceSoftGrid OBJECT-TYPE
    SYNTAX  INTEGER  {
        enabled(1),
        disabled(2)
        }
    MAX-ACCESS  read-only
    STATUS  current
    DESCRIPTION
         "Enable/disable softgrid load balancing."
    ::= { slbCurCfgVirtServicesEntry 43 }

slbCurCfgVirtServiceSessionMirror OBJECT-TYPE
    SYNTAX  INTEGER  {
        enabled(1),
        disabled(2)
        }
    MAX-ACCESS  read-only
    STATUS  current
    DESCRIPTION
        "Enable/disable session mirroring."
    ::= { slbCurCfgVirtServicesEntry 42 }

slbCurCfgVirtServiceSdpNat OBJECT-TYPE
    SYNTAX  INTEGER {
        enabled(1),
        disabled(2)
        }
    MAX-ACCESS  read-only
    STATUS  current
    DESCRIPTION
        "Enable/disable SIP Media portal NAT."
    ::= { slbCurCfgVirtServicesEntry 41 }

slbCurCfgVirtServiceConnPooling OBJECT-TYPE
    SYNTAX  INTEGER {
        enabled(1),
        disabled(2)
        }
    MAX-ACCESS  read-only
    STATUS  current
    DESCRIPTION
        "Enable/disable connection pooling for HTTP traffic."
    ::= { slbCurCfgVirtServicesEntry 44 }

-- Server load balancing - Virtual Services Table 

slbNewCfgVirtServicesTable OBJECT-TYPE
    SYNTAX  SEQUENCE OF SlbNewCfgVirtServicesEntry
    MAX-ACCESS  not-accessible
    STATUS  current
    DESCRIPTION
        "The table of virtual Services."
    ::= { virtualServerCfg 6 }

slbNewCfgVirtServicesEntry OBJECT-TYPE
    SYNTAX  SlbNewCfgVirtServicesEntry
    MAX-ACCESS  not-accessible
    STATUS  current
    DESCRIPTION
        "A row in the virtual services table."
    INDEX   { slbNewCfgVirtServIndex, slbNewCfgVirtServiceIndex }
    ::= { slbNewCfgVirtServicesTable 1 }

SlbNewCfgVirtServicesEntry ::= SEQUENCE {
    slbNewCfgVirtServIndex            Integer32,
    slbNewCfgVirtServiceIndex         Integer32,
    slbNewCfgVirtServiceVirtPort      INTEGER,
    slbNewCfgVirtServiceRealGroup     Integer32,
    slbNewCfgVirtServiceRealPort      INTEGER,
    slbNewCfgVirtServiceUDPBalance    INTEGER,
    slbNewCfgVirtServiceHname         DisplayString,
    slbNewCfgVirtServiceBwmContract   Integer32,
    slbNewCfgVirtServiceDirServerRtn  INTEGER,
    slbNewCfgVirtServiceRtspUrlParse  INTEGER,
    slbNewCfgVirtServiceFtpParsing    INTEGER,
    slbNewCfgVirtServiceRemapUDPFrags INTEGER,
    slbNewCfgVirtServiceDnsSlb        INTEGER,
    slbNewCfgVirtServiceResponseCount INTEGER,
    slbNewCfgVirtServicePBind         INTEGER,
    slbNewCfgVirtServiceCname         DisplayString,
    slbNewCfgVirtServiceCoffset       INTEGER,
    slbNewCfgVirtServiceClength       INTEGER, 
    slbNewCfgVirtServiceUriCookie     INTEGER,
    slbNewCfgVirtServiceCExpire       DisplayString,
    slbNewCfgVirtServiceCookieMode    INTEGER,
    slbNewCfgVirtServiceDBind         INTEGER,
    slbNewCfgVirtServiceHttpSlb       INTEGER,
    slbNewCfgVirtServiceHttpSlbOption INTEGER,
    slbNewCfgVirtServiceHttpSlb2      INTEGER,
    slbNewCfgVirtServiceHttpHdrName   DisplayString,
    slbNewCfgVirtServiceUrlHashLen    INTEGER,
    slbNewCfgVirtServiceCookieDname   INTEGER,
    slbNewCfgVirtServiceDelete        INTEGER, 
    slbNewCfgVirtServiceDirect        INTEGER,
    slbNewCfgVirtServiceThash         INTEGER,
    slbNewCfgVirtServiceLdapreset     INTEGER,
    slbNewCfgVirtServiceLdapslb       INTEGER,
    slbNewCfgVirtServiceSip           INTEGER,
    slbNewCfgVirtServiceXForwardedFor INTEGER,
    slbNewCfgVirtServiceHttpRedir     INTEGER,
    slbNewCfgVirtServicePbindRport    INTEGER,
    slbNewCfgVirtServiceEgressPip     INTEGER,
    slbNewCfgVirtServiceWts           INTEGER,
    slbNewCfgVirtServiceTimeOut       INTEGER,
    slbNewCfgVirtServiceSoftGrid      INTEGER,
    slbNewCfgVirtServiceSessionMirror INTEGER,
    slbNewCfgVirtServiceSdpNat        INTEGER,
    slbNewCfgVirtServiceConnPooling   INTEGER,
    slbNewCfgVirtServiceUhash         INTEGER
    }

slbNewCfgVirtServIndex OBJECT-TYPE
    SYNTAX  Integer32
    MAX-ACCESS  read-only
    STATUS  current
    DESCRIPTION
        "The number of the virtual server." 
    ::= { slbNewCfgVirtServicesEntry 1 }

slbNewCfgVirtServiceIndex OBJECT-TYPE 
    SYNTAX  Integer32 
    MAX-ACCESS  read-only 
    STATUS  current 
    DESCRIPTION 
        "The service index. This has no external meaning" 
    ::= { slbNewCfgVirtServicesEntry 2 }


slbNewCfgVirtServiceVirtPort OBJECT-TYPE  
    SYNTAX  INTEGER (9..65534)
    MAX-ACCESS  read-create  
    STATUS  current  
    DESCRIPTION 
        "The layer4 virtual port number of the service."  
    ::= { slbNewCfgVirtServicesEntry 3 } 

slbNewCfgVirtServiceRealGroup OBJECT-TYPE   
    SYNTAX  Integer32   
    MAX-ACCESS  read-create   
    STATUS  current   
    DESCRIPTION 
        "The real server group number for this service."   
    ::= { slbNewCfgVirtServicesEntry 4 }

slbNewCfgVirtServiceRealPort OBJECT-TYPE   
    SYNTAX  INTEGER (0..65534)
    MAX-ACCESS  read-create   
    STATUS  current   
    DESCRIPTION 
        "The layer4 real port number of the service."   
    ::= { slbNewCfgVirtServicesEntry 5 }

slbNewCfgVirtServiceUDPBalance OBJECT-TYPE   
    SYNTAX  INTEGER {
	enabled(2),
	disabled(3),
	stateless(4)
	}
    MAX-ACCESS  read-create   
    STATUS  current   
    DESCRIPTION 
        "Enable, disable or stateless the UDP balancing for the virtual port."
    ::= { slbNewCfgVirtServicesEntry 6 }

slbNewCfgVirtServiceHname OBJECT-TYPE 
    SYNTAX  DisplayString (SIZE(0..34))
    MAX-ACCESS  read-create 
    STATUS  current 
    DESCRIPTION 
        "The host name of the virtual service."  
    ::= { slbNewCfgVirtServicesEntry 7 }

slbNewCfgVirtServiceBwmContract OBJECT-TYPE   
    SYNTAX  Integer32   
    MAX-ACCESS  read-create
    STATUS  current   
    DESCRIPTION 
        "The BWM contract number for this service."   
    ::= { slbNewCfgVirtServicesEntry 8 }

slbNewCfgVirtServiceDirServerRtn OBJECT-TYPE
    SYNTAX  INTEGER {
        enabled(1),
        disabled(2)
        }
    MAX-ACCESS  read-create
    STATUS  current   
    DESCRIPTION 
        "Enable or disable direct server return feature. To translate only 
         MAC addresses in performing server load balancing when enabled.  
         This allow servers to return directly to client since IP addresses 
         have not been changed."
    ::= { slbNewCfgVirtServicesEntry 9 }

slbNewCfgVirtServiceRtspUrlParse OBJECT-TYPE   
    SYNTAX  INTEGER {
        none(1),
        l4hash(2),
        hash(3),
        patternMatch(4)
	}
    MAX-ACCESS  read-create
    STATUS  current   
    DESCRIPTION 
        "Select RTSP URL load balancing type."
    ::= { slbNewCfgVirtServicesEntry 10 }

slbNewCfgVirtServiceDBind OBJECT-TYPE   
    SYNTAX  INTEGER {
	enabled(1),
	disabled(2)
	}
    MAX-ACCESS  read-create
    STATUS  current   
    DESCRIPTION 
        "Enable or disable Delayed Binding."
    ::= { slbNewCfgVirtServicesEntry 11 }

slbNewCfgVirtServiceFtpParsing OBJECT-TYPE
    SYNTAX  INTEGER {
	enabled(1),
	disabled(2)
	}
    MAX-ACCESS  read-create
    STATUS  current
    DESCRIPTION
        "Enable or Disable the ftp parsing for the virtual service."
    ::= { slbNewCfgVirtServicesEntry 12 }

slbNewCfgVirtServiceRemapUDPFrags OBJECT-TYPE   
    SYNTAX INTEGER {
        enabled(1),
        disabled(2)
        }
    MAX-ACCESS read-create   
    STATUS current   
    DESCRIPTION 
        "Enable or disable remapping UDP server fragments"   
    ::= { slbNewCfgVirtServicesEntry 13 }

slbNewCfgVirtServiceDnsSlb OBJECT-TYPE   
    SYNTAX  INTEGER {
        enabled(1),
	disabled(2)
	}
    MAX-ACCESS  read-create   
    STATUS  current   
    DESCRIPTION 
        "Enable or disable DNS query load balancing."
    ::= { slbNewCfgVirtServicesEntry 14 }

slbNewCfgVirtServiceResponseCount OBJECT-TYPE 
    SYNTAX  INTEGER (1..16)
    MAX-ACCESS  read-create 
    STATUS  current 
    DESCRIPTION 
        "The number of cookie search response count."
    ::= { slbNewCfgVirtServicesEntry 15 }

slbNewCfgVirtServicePBind OBJECT-TYPE   
    SYNTAX  INTEGER {
	clientip(2),
	disabled(3),
	sslid(4),
        cookie(5)
	}
    MAX-ACCESS  read-create   
    STATUS  current   
    DESCRIPTION 
        "Enable or disable persistent bindings for the virtual port."
    ::= { slbNewCfgVirtServicesEntry 16 }

slbNewCfgVirtServiceCname OBJECT-TYPE 
    SYNTAX  DisplayString (SIZE(0..20))
    MAX-ACCESS  read-create 
    STATUS  current 
    DESCRIPTION 
        "The cookie name of the virtual server used for cookie load balance."  
    ::= { slbNewCfgVirtServicesEntry 17 }

slbNewCfgVirtServiceCoffset OBJECT-TYPE
    SYNTAX  INTEGER (0..128)
    MAX-ACCESS  read-create 
    STATUS  current
    DESCRIPTION
        "The starting byte offset of the cookie value." 
    ::= { slbNewCfgVirtServicesEntry 18 }

slbNewCfgVirtServiceClength OBJECT-TYPE
    SYNTAX  INTEGER (0..128)
    MAX-ACCESS  read-create
    STATUS  current
    DESCRIPTION
        "The number of bytes to extract from the cookie value." 
    ::= { slbNewCfgVirtServicesEntry 19 }

slbNewCfgVirtServiceUriCookie OBJECT-TYPE 
    SYNTAX  INTEGER {
	enabled(1),
	disabled(2)
	}
    MAX-ACCESS  read-create 
    STATUS  current 
    DESCRIPTION 
        "Enable or disable cookie search in URI"  
    ::= { slbNewCfgVirtServicesEntry 20}

slbNewCfgVirtServiceCExpire OBJECT-TYPE 
    SYNTAX  DisplayString (SIZE(0..20))
    MAX-ACCESS  read-create 
    STATUS  current 
    DESCRIPTION 
        "The cookie expire of the virtual server used for insert cookie load
         balance depending on the mode it has the following format 
         <MM/dd/yy[@hh:mm]> absolute mode or <days[:hours[:minutes]]>
         for relative mode."  
    ::= { slbNewCfgVirtServicesEntry 21 }

slbNewCfgVirtServiceCookieMode OBJECT-TYPE   
    SYNTAX INTEGER {
        rewrite(1),
        passive(2),
	insert(3),
	disabled(4)
        }
    MAX-ACCESS read-create 
    STATUS current   
    DESCRIPTION 
        "Select cookie persistance mode."
    ::= { slbNewCfgVirtServicesEntry 22 }

slbNewCfgVirtServiceHttpSlb OBJECT-TYPE   
    SYNTAX  INTEGER {
	disabled(1),
        urlslb(2),
        urlhash(3),
        cookie(4),
        host(5),
        browser(6),
        others(7),
        headerhash(8) 
	}
    MAX-ACCESS  read-create   
    STATUS  current   
    DESCRIPTION 
        "Select HTTP server loadbalancing for the virtual port."   
    ::= { slbNewCfgVirtServicesEntry 23 }

slbNewCfgVirtServiceHttpSlbOption OBJECT-TYPE   
    SYNTAX  INTEGER {
	and(1),
        or(2),
        none(3)
	}
    MAX-ACCESS  read-create   
    STATUS  current   
    DESCRIPTION 
        "Select HTTP server loadbalancing for the virtual port."   
    ::= { slbNewCfgVirtServicesEntry 24 }

slbNewCfgVirtServiceHttpSlb2 OBJECT-TYPE   
    SYNTAX  INTEGER {
	disabled(1),
        urlslb(2),
        urlhash(3),
        cookie(4),
        host(5),
        browser(6),
        others(7),
        headerhash(8) 
	}
    MAX-ACCESS  read-create   
    STATUS  current   
    DESCRIPTION 
        "Select HTTP server loadbalancing for the virtual port."   
    ::= { slbNewCfgVirtServicesEntry 25 }

slbNewCfgVirtServiceHttpHdrName OBJECT-TYPE 
    SYNTAX  DisplayString  (SIZE(0..32))
    MAX-ACCESS  read-create 
    STATUS  current 
    DESCRIPTION 
        "The HTTP header name of the virtual server."
    ::= { slbNewCfgVirtServicesEntry 26 }

slbNewCfgVirtServiceUrlHashLen OBJECT-TYPE 
    SYNTAX  INTEGER (0..255)
    MAX-ACCESS  read-create 
    STATUS  current 
    DESCRIPTION 
        "The number of bytes used to hash onto server, A zero means
         URL hashing disabled."
    ::= { slbNewCfgVirtServicesEntry 27}

slbNewCfgVirtServiceDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgVirtServicesEntry 28 }

slbNewCfgVirtServiceDirect OBJECT-TYPE   
    SYNTAX  INTEGER {
        enabled(1),
	disabled(2)
	}
    MAX-ACCESS  read-create   
    STATUS  current   
    DESCRIPTION 
        "Enable or disable DAM for this service." 
    ::= { slbNewCfgVirtServicesEntry 29 }

slbNewCfgVirtServiceThash OBJECT-TYPE   
    SYNTAX  INTEGER {
        sip(1),
        sip-sport(2)
        }
    MAX-ACCESS  read-create
    STATUS  current   
    DESCRIPTION 
        "Set hash parameter."
    ::= { slbNewCfgVirtServicesEntry 30 }

slbNewCfgVirtServiceLdapreset OBJECT-TYPE 
    SYNTAX  INTEGER {
        enabled(1),
        disabled(2)
        }
    MAX-ACCESS  read-create 
    STATUS  current 
    DESCRIPTION 
        "Enable or disable LDAP Server Reset"  
    ::= { slbNewCfgVirtServicesEntry 31 }

slbNewCfgVirtServiceLdapslb OBJECT-TYPE 
    SYNTAX  INTEGER {
        enabled(1),
        disabled(2)
        }
    MAX-ACCESS  read-create 
    STATUS  current 
    DESCRIPTION 
        "Enable or disable LDAP Server load balancing"  
    ::= { slbNewCfgVirtServicesEntry 32 }

slbNewCfgVirtServiceSip OBJECT-TYPE   
    SYNTAX  INTEGER {
        enabled(1),
	disabled(2)
	}
    MAX-ACCESS  read-create   
    STATUS  current   
    DESCRIPTION 
        "Enable/disable SIP load balancing."
    ::= { slbNewCfgVirtServicesEntry 33 }

slbNewCfgVirtServiceXForwardedFor OBJECT-TYPE   
    SYNTAX  INTEGER {
        enabled(1),
	disabled(2)
	}
    MAX-ACCESS  read-create
    STATUS  current   
    DESCRIPTION 
        "Enable/disable X-Forwarded-For for proxy mode."
    ::= { slbNewCfgVirtServicesEntry 34 }

slbNewCfgVirtServiceHttpRedir OBJECT-TYPE
    SYNTAX  INTEGER {
        enabled(1),
        disabled(2)
        }
    MAX-ACCESS  read-create
    STATUS  current
    DESCRIPTION
        "Enable/disable HTTP redirect for GSLB."
    ::= { slbNewCfgVirtServicesEntry 35 }

slbNewCfgVirtServicePbindRport OBJECT-TYPE   
    SYNTAX  INTEGER {
        enabled(1),
	disabled(2)
	}
    MAX-ACCESS  read-create
    STATUS  current   
    DESCRIPTION 
        "Enable or disable use of rport in the session lookup for a persistent
         session."
    ::= { slbNewCfgVirtServicesEntry 36 }
    
slbNewCfgVirtServiceEgressPip OBJECT-TYPE   
    SYNTAX  INTEGER {
        enabled(1),
	disabled(2)
	}
    MAX-ACCESS  read-create
    STATUS  current   
    DESCRIPTION 
        "Enable/disable pip selection based on egress port/vlan."
    ::= { slbNewCfgVirtServicesEntry 37 }

slbNewCfgVirtServiceCookieDname OBJECT-TYPE
    SYNTAX INTEGER {
        enabled(1),
        disabled(2)
        }
    MAX-ACCESS read-create
    STATUS current
    DESCRIPTION
        "Select dname for insert cookie persistance mode."
    ::= { slbNewCfgVirtServicesEntry 38 }
    
slbNewCfgVirtServiceWts OBJECT-TYPE
    SYNTAX INTEGER {
        enabled(1),
        disabled(2)
        }
    MAX-ACCESS read-create
    STATUS current
    DESCRIPTION
        "Enable or disable WTS loadbalancing and persistence."
    ::= { slbNewCfgVirtServicesEntry 39 }

slbNewCfgVirtServiceUhash OBJECT-TYPE
    SYNTAX INTEGER {
        enabled(1),
        disabled(2)
        }
    MAX-ACCESS read-create
    STATUS current
    DESCRIPTION
        "Enable when there is no Session Directory server."
    ::= { slbNewCfgVirtServicesEntry 40 }

slbNewCfgVirtServiceTimeOut OBJECT-TYPE
    SYNTAX  INTEGER (0..32768)
    MAX-ACCESS  read-create
    STATUS  current
    DESCRIPTION
        "The maximum number of minutes an inactive connection remains open."
    ::= { slbNewCfgVirtServicesEntry 41 }

slbNewCfgVirtServiceSessionMirror OBJECT-TYPE
    SYNTAX  INTEGER {
        enabled(1),
        disabled(2)
        }
    MAX-ACCESS  read-create
    STATUS  current
    DESCRIPTION
        "Enable/disable session mirroring."
    ::= { slbNewCfgVirtServicesEntry 43 }

slbNewCfgVirtServiceSoftGrid OBJECT-TYPE
    SYNTAX  INTEGER {
        enabled(1),
        disabled(2)
        }
    MAX-ACCESS  read-create
    STATUS  current
    DESCRIPTION
        "Enable/disable softgrid load balancing."
    ::= { slbNewCfgVirtServicesEntry 44 }

slbNewCfgVirtServiceSdpNat OBJECT-TYPE
    SYNTAX  INTEGER {
        enabled(1),
        disabled(2)
        }
    MAX-ACCESS  read-create
    STATUS  current
    DESCRIPTION
        "Enable/disable SIP Media portal NAT."
    ::= { slbNewCfgVirtServicesEntry 42 }

slbNewCfgVirtServiceConnPooling OBJECT-TYPE
    SYNTAX  INTEGER {
        enabled(1),
        disabled(2)
        }
    MAX-ACCESS  read-create
    STATUS  current
    DESCRIPTION
        "Enable/disable connection pooling for HTTP traffic."
    ::= { slbNewCfgVirtServicesEntry 45 }

-- URL based BWM table for Virtual Services

slbUrlBwmTableMaxSize OBJECT-TYPE
    SYNTAX  Integer32 
    MAX-ACCESS  read-only 
    STATUS  current 
    DESCRIPTION 
        "The maximum number of entries in SLB URL BWM Table." 
    ::= { virtualServerCfg 7}

slbCurCfgUrlBwmTable OBJECT-TYPE
    SYNTAX  SEQUENCE OF SlbCurCfgUrlBwmEntry
    MAX-ACCESS  not-accessible
    STATUS  current
    DESCRIPTION
        "The table of URL based BWM for Virtual Services."
    ::= { virtualServerCfg 8 }

slbCurCfgUrlBwmEntry OBJECT-TYPE
    SYNTAX  SlbCurCfgUrlBwmEntry
    MAX-ACCESS  not-accessible
    STATUS  current
    DESCRIPTION
        "A row in the URL based BWM virtual services table."
    INDEX   { slbCurCfgUrlBwmVirtServIndex, 
              slbCurCfgUrlBwmVirtServiceIndex, 
              slbCurCfgUrlBwmUrlId }
    ::= { slbCurCfgUrlBwmTable 1 }

SlbCurCfgUrlBwmEntry ::= SEQUENCE {
    slbCurCfgUrlBwmVirtServIndex     Integer32,
    slbCurCfgUrlBwmVirtServiceIndex  Integer32,
    slbCurCfgUrlBwmUrlId             Integer32,
    slbCurCfgUrlBwmContract          Integer32
    }

slbCurCfgUrlBwmVirtServIndex OBJECT-TYPE
    SYNTAX  Integer32
    MAX-ACCESS  read-only
    STATUS  current
    DESCRIPTION
        "The number of the virtual server." 
    ::= { slbCurCfgUrlBwmEntry 1 }

slbCurCfgUrlBwmVirtServiceIndex OBJECT-TYPE 
    SYNTAX  Integer32 
    MAX-ACCESS  read-only 
    STATUS  current 
    DESCRIPTION 
        "The service index. This has no external meaning" 
    ::= { slbCurCfgUrlBwmEntry 2 }

slbCurCfgUrlBwmUrlId OBJECT-TYPE  
    SYNTAX  Integer32  
    MAX-ACCESS  read-only  
    STATUS  current  
    DESCRIPTION 
        "The URL Path Identifier."  
    ::= { slbCurCfgUrlBwmEntry 3 } 

slbCurCfgUrlBwmContract OBJECT-TYPE  
    SYNTAX  Integer32  
    MAX-ACCESS  read-only  
    STATUS  current  
    DESCRIPTION 
        "The BW contract number."  
    ::= { slbCurCfgUrlBwmEntry 4 } 

slbNewCfgUrlBwmTable OBJECT-TYPE
    SYNTAX  SEQUENCE OF SlbNewCfgUrlBwmEntry
    MAX-ACCESS  not-accessible
    STATUS  current
    DESCRIPTION
        "The table of URL based BWM for Virtual Services."
    ::= { virtualServerCfg 9 }

slbNewCfgUrlBwmEntry OBJECT-TYPE
    SYNTAX  SlbNewCfgUrlBwmEntry
    MAX-ACCESS  not-accessible
    STATUS  current
    DESCRIPTION
        "A row in the URL based BWM virtual services table."
    INDEX   { slbNewCfgUrlBwmVirtServIndex, 
              slbNewCfgUrlBwmVirtServiceIndex, 
              slbNewCfgUrlBwmUrlId }
    ::= { slbNewCfgUrlBwmTable 1 }

SlbNewCfgUrlBwmEntry ::= SEQUENCE {
    slbNewCfgUrlBwmVirtServIndex     Integer32,
    slbNewCfgUrlBwmVirtServiceIndex  Integer32,
    slbNewCfgUrlBwmUrlId             Integer32,
    slbNewCfgUrlBwmContract          Integer32,
    slbNewCfgUrlBwmDelete            INTEGER
    }

slbNewCfgUrlBwmVirtServIndex OBJECT-TYPE
    SYNTAX  Integer32
    MAX-ACCESS  read-only
    STATUS  current
    DESCRIPTION
        "The number of the virtual server." 
    ::= { slbNewCfgUrlBwmEntry 1 }

slbNewCfgUrlBwmVirtServiceIndex OBJECT-TYPE 
    SYNTAX  Integer32 
    MAX-ACCESS  read-only 
    STATUS  current 
    DESCRIPTION 
        "The service index. This has no external meaning" 
    ::= { slbNewCfgUrlBwmEntry 2 }

slbNewCfgUrlBwmUrlId OBJECT-TYPE  
    SYNTAX  Integer32  
    MAX-ACCESS  read-only  
    STATUS  current  
    DESCRIPTION 
        "The URL Path Identifier."  
    ::= { slbNewCfgUrlBwmEntry 3 } 

slbNewCfgUrlBwmContract OBJECT-TYPE  
    SYNTAX  Integer32  
    MAX-ACCESS  read-create  
    STATUS  current  
    DESCRIPTION 
        "The BW contract number."
    ::= { slbNewCfgUrlBwmEntry 4 } 

slbNewCfgUrlBwmDelete OBJECT-TYPE
    SYNTAX  INTEGER {
        other(1),
        delete(2)
       }
    MAX-ACCESS  read-create
    STATUS  current
    DESCRIPTION
        "When set to the value of 2 (delete), the entire row is deleted. 
         When read, other(1) is returned. Setting the value to anything 
         other than 2(delete) has no effect on the state of the row."
    ::= { slbNewCfgUrlBwmEntry 5 }

--  SLB Port table

slbPortTableMaxSize OBJECT-TYPE
    SYNTAX  Integer32 
    MAX-ACCESS  read-only 
    STATUS  current 
    DESCRIPTION 
        "The maximum number of entries in SLB Port Table." 
    ::= { portCfg 1 }

slbCurCfgPortTable OBJECT-TYPE
    SYNTAX  SEQUENCE OF SlbCurCfgPortEntry
    MAX-ACCESS  not-accessible
    STATUS  current
    DESCRIPTION
       "The table of ports and their SLB states"
    ::= { portCfg 2 }

slbCurCfgPortEntry OBJECT-TYPE
    SYNTAX  SlbCurCfgPortEntry
    MAX-ACCESS  not-accessible
    STATUS  current
    DESCRIPTION
        "A row in the slbPortTable "
    INDEX   { slbCurCfgPortIndex }
    ::= { slbCurCfgPortTable 1 }

SlbCurCfgPortEntry ::= SEQUENCE {
    slbCurCfgPortIndex              Integer32,
    slbCurCfgPortSlbHotStandby      INTEGER,
    slbCurCfgPortSlbInterSwitch     INTEGER,
    slbCurCfgPortSlbPipState        INTEGER,
    slbCurCfgPortSlbRtsState        INTEGER,
    slbCurCfgPortSlbIdslbState      INTEGER,
    slbCurCfgPortSlbState           INTEGER
    }

slbCurCfgPortIndex OBJECT-TYPE
    SYNTAX  Integer32
    MAX-ACCESS  read-only
    STATUS  current
    DESCRIPTION
        "The port number for which the SLB information pertains." 
    ::= { slbCurCfgPortEntry 1 }

slbCurCfgPortSlbState OBJECT-TYPE
    SYNTAX  INTEGER {
	none(1),
	client(2),
	server(3),
	client-server(4)
	}
    MAX-ACCESS  read-only
    STATUS  current
    DESCRIPTION
        "The SLB state of the port.
	 none(1)            - not SLB port
	 client(2)          - SLB client port
	 server(3)          - SLB server port
	 client-server(4)   - SLB client and server port"
    ::= { slbCurCfgPortEntry 2 }

slbCurCfgPortSlbHotStandby OBJECT-TYPE
    SYNTAX  INTEGER {
        enabled(1),
        disabled(2)
        }
    MAX-ACCESS  read-only
    STATUS  current
    DESCRIPTION
        "Enable or disable hot standby processing on the switch port."
    ::= { slbCurCfgPortEntry 3 }

slbCurCfgPortSlbInterSwitch OBJECT-TYPE
    SYNTAX  INTEGER {
        enabled(1),
        disabled(2)
        }
    MAX-ACCESS  read-only
    STATUS  current
    DESCRIPTION
        "Enable or disable inter-switch processing on the switch port."
    ::= { slbCurCfgPortEntry 4 }

slbCurCfgPortSlbPipState OBJECT-TYPE
    SYNTAX  INTEGER {
        enabled(1),
        disabled(2)
        }
    MAX-ACCESS  read-only
    STATUS  current
    DESCRIPTION
        "Enable or disable use of proxy IP address on the switch port."
    ::= { slbCurCfgPortEntry 5 }

slbCurCfgPortSlbRtsState OBJECT-TYPE
    SYNTAX  INTEGER   {
        enabled(1),
        disabled(2)
        }
    MAX-ACCESS  read-only
    STATUS  current
    DESCRIPTION
        "Enable or disable RTS processing on the switch port."
    ::= { slbCurCfgPortEntry 6 }

slbCurCfgPortSlbIdslbState OBJECT-TYPE
    SYNTAX  INTEGER {
        enabled(1),
        disabled(2)
        }
    MAX-ACCESS  read-only
    STATUS  current
    DESCRIPTION
        "Enable or disable Intrusion Detection server load balancing."
    ::= { slbCurCfgPortEntry 7 }


-- Server load balancing - slb port state table

slbNewCfgPortTable OBJECT-TYPE
    SYNTAX  SEQUENCE OF SlbNewCfgPortEntry
    MAX-ACCESS  not-accessible
    STATUS  current
    DESCRIPTION
        "The table of ports and their SLB states"
    ::= { portCfg 3 }

slbNewCfgPortEntry OBJECT-TYPE
    SYNTAX  SlbNewCfgPortEntry
    MAX-ACCESS  not-accessible
    STATUS  current
    DESCRIPTION
        "A row in the slbPortTable "
    INDEX   { slbNewCfgPortIndex }
    ::= { slbNewCfgPortTable 1 }

SlbNewCfgPortEntry ::= SEQUENCE {
    slbNewCfgPortIndex              Integer32,
    slbNewCfgPortSlbHotStandby      INTEGER,
    slbNewCfgPortSlbInterSwitch     INTEGER,
    slbNewCfgPortSlbPipState        INTEGER,
    slbNewCfgPortSlbRtsState        INTEGER,
    slbNewCfgPortDelete             INTEGER,
    slbNewCfgPortSlbIdslbState      INTEGER,
    slbNewCfgPortSlbState           INTEGER
    }

slbNewCfgPortIndex OBJECT-TYPE
    SYNTAX  Integer32
    MAX-ACCESS  read-only
    STATUS  current
    DESCRIPTION
        "The port number for which the SLB information pertains." 
    ::= { slbNewCfgPortEntry 1 }

slbNewCfgPortSlbState OBJECT-TYPE
    SYNTAX  INTEGER {
	none(1),
	client(2),
	server(3),
	client-server(4)
	}
    MAX-ACCESS  read-write
    STATUS  current
    DESCRIPTION
        "The SLB state of the port.
	 none(1)            - not SLB port
	 client(2)          - SLB client port
	 server(3)          - SLB server port
	 client-server(4)   - SLB client and server port"
    ::= { slbNewCfgPortEntry 2 }

slbNewCfgPortSlbHotStandby OBJECT-TYPE
    SYNTAX  INTEGER   {
        enabled(1),
        disabled(2)
        }
    MAX-ACCESS  read-write
    STATUS  current
    DESCRIPTION
        "Enable or disable hot standby processing on the switch port."
    ::= { slbNewCfgPortEntry 3 }

slbNewCfgPortSlbInterSwitch OBJECT-TYPE
    SYNTAX  INTEGER   {
        enabled(1),
        disabled(2)
        }
    MAX-ACCESS  read-write
    STATUS  current
    DESCRIPTION
        "Enable or disable inter-switch processing on the switch port."
    ::= { slbNewCfgPortEntry 4 }

slbNewCfgPortSlbPipState OBJECT-TYPE
    SYNTAX  INTEGER   {
        enabled(1),
        disabled(2)
        }
    MAX-ACCESS  read-write
    STATUS  current
    DESCRIPTION
        "Enable or disable use of proxy IP address on the switch port."
    ::= { slbNewCfgPortEntry 5 }

slbNewCfgPortSlbRtsState OBJECT-TYPE
    SYNTAX  INTEGER   {
        enabled(1),
        disabled(2)
        }
    MAX-ACCESS  read-write
    STATUS  current
    DESCRIPTION
        "Enable or disable RTS processing on the switch port."
    ::= { slbNewCfgPortEntry 6 }

slbNewCfgPortDelete OBJECT-TYPE
    SYNTAX INTEGER {
        other(1),
        delete(2)
        }
    MAX-ACCESS read-write
    STATUS current
    DESCRIPTION
        "When set to the value of 2 (delete), the entire row is deleted. 
         When read, other(1) is returned. Setting the value to anything 
         other than 2(delete) has no effect on the state of the row."
    ::= { slbNewCfgPortEntry 7 }

slbNewCfgPortSlbIdslbState OBJECT-TYPE
    SYNTAX  INTEGER {
        enabled(1),
        disabled(2)
        }
    MAX-ACCESS  read-write
    STATUS  current
    DESCRIPTION
        "Enable or disable Intrusion Detection server load balancing."
    ::= { slbNewCfgPortEntry 8 }


-- SLB General Configuration 

slbCurCfgGlobalControl OBJECT-TYPE
    SYNTAX  INTEGER { 
	enabled(2),
	disabled(3)
	}
    MAX-ACCESS  read-only
    STATUS  current
    DESCRIPTION
        "The global state of Server Load Balancing."
    ::= { slbGeneralCfg 1 }

slbNewCfgGlobalControl OBJECT-TYPE
    SYNTAX  INTEGER { 
        enabled(2),
        disabled(3)
        }
    MAX-ACCESS  read-write
    STATUS  current
    DESCRIPTION
        "The global state of Server Load Balancing."
    ::= { slbGeneralCfg 2 }

slbCurCfgImask OBJECT-TYPE
    SYNTAX  IpAddress
    MAX-ACCESS  read-only
    STATUS  current
    DESCRIPTION
        "The virtual and real IP address mask - corresponding to the
	 imask command of the slb configuration menu." 
    ::= { slbGeneralCfg 3 }

slbNewCfgImask OBJECT-TYPE
    SYNTAX  IpAddress
    MAX-ACCESS  read-write
    STATUS  current
    DESCRIPTION
        "The virtual and real IP address mask - corresponding to the
         imask command of the slb configuration menu."
    ::= { slbGeneralCfg 4 }

slbCurCfgMnet OBJECT-TYPE
    SYNTAX  IpAddress
    MAX-ACCESS  read-only
    STATUS  current
    DESCRIPTION
        "The management network - corresponding to the mnet command of 
         the slb configuration menu." 
    ::= { slbGeneralCfg 5 }

slbNewCfgMnet OBJECT-TYPE
    SYNTAX  IpAddress
    MAX-ACCESS  read-write
    STATUS  current
    DESCRIPTION
        "The management network - corresponding to the mnet command of 
         the slb configuration menu." 
    ::= { slbGeneralCfg 6 }

slbCurCfgMmask OBJECT-TYPE
    SYNTAX  IpAddress
    MAX-ACCESS  read-only
    STATUS  current
    DESCRIPTION
        "The management subnet mask - corresponding to the mmask command 
         of the slb configuration menu." 
    ::= { slbGeneralCfg 7 }

slbNewCfgMmask OBJECT-TYPE
    SYNTAX  IpAddress
    MAX-ACCESS  read-write
    STATUS  current
    DESCRIPTION
        "The management subnet mask - corresponding to the mmask command 
         of the slb configuration menu." 
    ::= { slbGeneralCfg 8 }

slbCurCfgRadiusAuthenString OBJECT-TYPE
    SYNTAX  DisplayString (SIZE(0..32))
    MAX-ACCESS  read-only
    STATUS  current
    DESCRIPTION
        "The RADIUS authentication string.  The string is used for 
	 generating encrypted authentication string for RADIUS health check."
    ::= { slbGeneralCfg 9 }

slbNewCfgRadiusAuthenString OBJECT-TYPE
    SYNTAX  DisplayString (SIZE(0..32))
    MAX-ACCESS  read-write
    STATUS  current
    DESCRIPTION
        "The RADIUS authentication string.  The string is used for 
	 generating encrypted authentication string for RADIUS health check."
    ::= { slbGeneralCfg 10 }

slbCurCfgDirectMode OBJECT-TYPE
    SYNTAX  INTEGER {
        enabled(1),
        disabled(2)
        }
    MAX-ACCESS  read-only
    STATUS  current
    DESCRIPTION
        "Enable or disable direct access mode. It allows direct access to 
         real servers and any combination of virtual and real servers 
         when set to enabled(1)."
    ::= { slbGeneralCfg 11 }

slbNewCfgDirectMode OBJECT-TYPE
    SYNTAX  INTEGER {
        enabled(1),
        disabled(2)
        }
    MAX-ACCESS  read-write
    STATUS  current
    DESCRIPTION
        "Enable or disable direct access mode. It allows direct access to 
         real servers and any combination of virtual and real servers 
         when set to enabled(1)."
    ::= { slbGeneralCfg 12 }

slbCurCfgPmask OBJECT-TYPE
    SYNTAX  IpAddress
    MAX-ACCESS  read-only
    STATUS  current
    DESCRIPTION
        "The persistent mask - corresponding to the pmask command of the 
         slb configuration menu." 
    ::= { slbGeneralCfg 13 }

slbNewCfgPmask OBJECT-TYPE
    SYNTAX  IpAddress
    MAX-ACCESS  read-write
    STATUS  current
    DESCRIPTION
        "The persistent mask - corresponding to the pmask command of the 
         slb configuration menu." 
    ::= { slbGeneralCfg 14 }

slbCurCfgGrace OBJECT-TYPE
    SYNTAX  INTEGER {
        enabled(1),
        disabled(2)
        }
    MAX-ACCESS  read-only
    STATUS  current
    DESCRIPTION
        "Enable or disable graceful server failure. It allows to keep the 
         connection to the failure real servers when set to enabled(1)."
    ::= { slbGeneralCfg 15 }

slbNewCfgGrace OBJECT-TYPE
    SYNTAX  INTEGER {
        enabled(1),
        disabled(2)
                }
    MAX-ACCESS  read-write
    STATUS  current
    DESCRIPTION
        "Enable or disable graceful server failure. It allows to keep the 
         connection to the failure real servers when set to enabled(1)."
    ::= { slbGeneralCfg 16 }

slbCurCfgVirtMatrixArch OBJECT-TYPE
    SYNTAX  INTEGER {
        enabled(1),
        disabled(2)
        }
    MAX-ACCESS  read-only
    STATUS  current
    DESCRIPTION
        "Enable or disable Virtual Matrix Architecture."
    ::= { slbGeneralCfg 17 }

slbNewCfgVirtMatrixArch OBJECT-TYPE
    SYNTAX  INTEGER {
        enabled(1),
        disabled(2)
        }
    MAX-ACCESS  read-write
    STATUS  current
    DESCRIPTION
        "Enable or disable Virtual Matrix Architecture."
    ::= { slbGeneralCfg 18 }

slbCurCfgFastage OBJECT-TYPE
    SYNTAX  INTEGER (0..7) 
    MAX-ACCESS  read-only
    STATUS  current 
    DESCRIPTION
        "Session table fast-age (1 sec) period bit shift."
    ::= { slbGeneralCfg 19 }

slbNewCfgFastage OBJECT-TYPE
    SYNTAX  INTEGER (0..7) 
    MAX-ACCESS  read-write
    STATUS  current 
    DESCRIPTION
        "Session table fast-age (1 sec) period bit shift."
    ::= { slbGeneralCfg 20 }

slbCurCfgSlowage OBJECT-TYPE
    SYNTAX  INTEGER (0..15) 
    MAX-ACCESS  read-only
    STATUS  obsolete
    DESCRIPTION
        "Session table slow-age (2 min) period bit shift."
    ::= { slbGeneralCfg 21 }

slbNewCfgSlowage OBJECT-TYPE
    SYNTAX  INTEGER (0..15) 
    MAX-ACCESS  read-write
    STATUS  obsolete
    DESCRIPTION
        "Session table slow-age (2 min) period bit shift."
    ::= { slbGeneralCfg 22 }

slbCurCfgTpcp OBJECT-TYPE
    SYNTAX  INTEGER {
        enabled(1),
        disabled(2)
        }
    MAX-ACCESS  read-only
    STATUS  current
    DESCRIPTION
        "Enable or disable Transparent Proxy Cache Protocol."
    ::= { slbGeneralCfg 23 }

slbNewCfgTpcp OBJECT-TYPE
    SYNTAX  INTEGER {
        enabled(1),
        disabled(2)
        }
    MAX-ACCESS  read-write
    STATUS  current
    DESCRIPTION
        "Enable or disable Transparent Proxy Cache Protocol."
    ::= { slbGeneralCfg 24 }

slbCurCfgMetricInterval OBJECT-TYPE
    SYNTAX  INTEGER (1..256) 
    MAX-ACCESS  read-only
    STATUS  current
    DESCRIPTION
        "The interval of response and bandwidth metric updates."
    ::= { slbGeneralCfg 25 }

slbNewCfgMetricInterval OBJECT-TYPE
    SYNTAX  INTEGER (1..256) 
    MAX-ACCESS  read-write
    STATUS  current
    DESCRIPTION
        "The interval of response and bandwidth metric updates."
    ::= { slbGeneralCfg 26 }

slbCurCfgLdapVersion OBJECT-TYPE
    SYNTAX  INTEGER {
	version2(1),
	version3(2)
    } 
    MAX-ACCESS  read-only
    STATUS  current
    DESCRIPTION
        "The version number for LDAP."
    ::= { slbGeneralCfg 27 }

slbNewCfgLdapVersion OBJECT-TYPE
    SYNTAX  INTEGER {
	version2(1),
	version3(2)
    } 
    MAX-ACCESS  read-write
    STATUS  current
    DESCRIPTION
        "The Version number of LDAP."
    ::= { slbGeneralCfg 28 }

slbCurCfgAllowHttpHc OBJECT-TYPE
    SYNTAX  INTEGER {
	enabled(1),
	disabled(2)
    } 
    MAX-ACCESS  read-only
    STATUS  current
    DESCRIPTION
        "Enable or disable allow HTTP health check on any port.
         If disabled the non-HTTP virtual services will use TCP Health Checks,
         if enabled the HTTP Content Health Check will be sent to any port 
         except HTTPS (443) if properly configured."
    ::= { slbGeneralCfg 29 }

slbNewCfgAllowHttpHc OBJECT-TYPE
    SYNTAX  INTEGER {
	enabled(1),
	disabled(2)
    } 
    MAX-ACCESS  read-write
    STATUS  current
    DESCRIPTION
        "Enable or disable allow HTTP health check on any port.
         If disabled the non-HTTP virtual services will use TCP Health Checks,
         if enabled the HTTP Content Health Check will be sent to any port 
         except HTTPS (443) if properly configured."
    ::= { slbGeneralCfg 30 }

slbCurCfgSubmac OBJECT-TYPE
    SYNTAX  INTEGER {
        enabled(1),
        disabled(2)
        }
    MAX-ACCESS  read-only
    STATUS  current
    DESCRIPTION
        "Enable or disable Source MAC Address substitution.
         Enabling this feature supercedes individual real server
         setting for Source MAC Address substitution."
    ::= { slbGeneralCfg 31 }

slbNewCfgSubmac OBJECT-TYPE
    SYNTAX  INTEGER {
        enabled(1),
        disabled(2)
        }
    MAX-ACCESS  read-write
    STATUS  current
    DESCRIPTION
        "Enable or disable Source MAC Address substitution.
         Enabling this feature supercedes individual real server
         setting for Source MAC Address substitution."
    ::= { slbGeneralCfg 32 }

slbCurCfgProxyGratArp OBJECT-TYPE
    SYNTAX  INTEGER {
        enabled(1),
        disabled(2)
        }
    MAX-ACCESS  read-only
    STATUS  obsolete
    DESCRIPTION
        "Enable or disable Proxy IP Gratuitous ARP."
    ::= { slbGeneralCfg 33 }

slbNewCfgProxyGratArp OBJECT-TYPE
    SYNTAX  INTEGER {
        enabled(1),
        disabled(2)
        }
    MAX-ACCESS  read-write
    STATUS  obsolete
    DESCRIPTION
        "Enable or disable Proxy IP Gratuitous ARP."
    ::= { slbGeneralCfg 34 }

slbCurCfgRtsVlan OBJECT-TYPE
    SYNTAX  INTEGER {
        enabled(1),
        disabled(2)
        }
    MAX-ACCESS  read-only
    STATUS  current
    DESCRIPTION
        "Enable or disable use VLAN info for real server lookup"
    ::= { slbGeneralCfg 35 }

slbNewCfgRtsVlan OBJECT-TYPE
    SYNTAX  INTEGER {
        enabled(1),
        disabled(2)
        }
    MAX-ACCESS  read-write
    STATUS  current
    DESCRIPTION
        "Enable or disable use VLAN info for real server lookup"
    ::= { slbGeneralCfg 36 }

slbCurCfgVirtualServiceStats OBJECT-TYPE
    SYNTAX  INTEGER {
        enabled(1),
        disabled(2)
        }
    MAX-ACCESS  read-only
    STATUS  current
    DESCRIPTION
        "Enable/disable Virtual Service Statistics."
    ::= { slbGeneralCfg 37 }

slbNewCfgVirtualServiceStats OBJECT-TYPE
    SYNTAX  INTEGER {
        enabled(1),
        disabled(2)
                }
    MAX-ACCESS  read-write
    STATUS  current
    DESCRIPTION
        "Enable/disable Virtual Service Statistics."
 ::= { slbGeneralCfg 38 }

slbCurCfgSlbSessAtkIntrval OBJECT-TYPE
    SYNTAX  INTEGER (0..3600)
    MAX-ACCESS  read-only
    STATUS  current
    DESCRIPTION
        "Set SLB session attack inspection interval."
    ::= { slbGeneralCfg 39 }

slbNewCfgSlbSessAtkIntrval OBJECT-TYPE
    SYNTAX  INTEGER (0..3600)
    MAX-ACCESS  read-write
    STATUS  current
    DESCRIPTION
        "Set SLB session attack inspection interval."
 ::= { slbGeneralCfg 40 }

slbCurCfgSlbSessAtkAllowlim OBJECT-TYPE
    SYNTAX  INTEGER (1..2097100)
    MAX-ACCESS  read-only
    STATUS  current
    DESCRIPTION
        "Set SLB session attack alert allowable limit."
    ::= { slbGeneralCfg 41 }

slbNewCfgSlbSessAtkAllowlim OBJECT-TYPE
    SYNTAX  INTEGER (1..2097100)
    MAX-ACCESS  read-write
    STATUS  current
    DESCRIPTION
        "Set SLB session attack alert allowable limit."
 ::= { slbGeneralCfg 42 }

slbCurCfgNewSlowage OBJECT-TYPE
    SYNTAX  INTEGER (0..14) 
    MAX-ACCESS  read-only
    STATUS  current
    DESCRIPTION
        "Session table slow-age (2 min) period bit shift."
    ::= { slbGeneralCfg 43 }

slbNewCfgNewSlowage OBJECT-TYPE
    SYNTAX  INTEGER (0..14) 
    MAX-ACCESS  read-write
    STATUS  current
    DESCRIPTION
        "Session table slow-age (2 min) period bit shift."
    ::= { slbGeneralCfg 44 }
    
slbCurCfgPortBind OBJECT-TYPE
    SYNTAX  INTEGER {
        enabled(1),
        disabled(2)
        }
    MAX-ACCESS  read-only
    STATUS  current
    DESCRIPTION
        "Enable/disable ingress port for session table Binding. SP uses
         ingress port for session lookup when set to enable."
    ::= { slbGeneralCfg 45 }

slbNewCfgPortBind OBJECT-TYPE
    SYNTAX  INTEGER {
        enabled(1),
        disabled(2)
                }
    MAX-ACCESS  read-write
    STATUS  current
    DESCRIPTION
        "Enable/disable ingress port for session table Binding. SP uses
         ingress port for session lookup when set to enable."
 ::= { slbGeneralCfg 46 }

slbCurCfgVmaSrcPort OBJECT-TYPE
    SYNTAX  INTEGER {
        enabled(1),
        disabled(2)
        }
    MAX-ACCESS  read-only
    STATUS  current
    DESCRIPTION
       "Enable/disable VMA source port."  
 ::= { slbGeneralCfg 47 }

slbNewCfgVmaSrcPort OBJECT-TYPE
    SYNTAX  INTEGER {
        enabled(1),
        disabled(2)
        }
    MAX-ACCESS  read-write
    STATUS  current
    DESCRIPTION
        "Enable/disable VMA source port." 
 ::= { slbGeneralCfg 48 }
 
slbCurCfgIpTcpCksum OBJECT-TYPE
    SYNTAX  INTEGER {
        enabled(1),
        disabled(2)
        }
    MAX-ACCESS  read-only
    STATUS  current
    DESCRIPTION
        "Enable/disable Layer 7 IP/TCP Checksum Validation."
    ::= { slbGeneralCfg 49 }

slbNewCfgIpTcpCksum OBJECT-TYPE
    SYNTAX  INTEGER {
        enabled(1),
        disabled(2)
                }
    MAX-ACCESS  read-write
    STATUS  current
    DESCRIPTION
        "Enable/disable Layer 7 IP/TCP Checksum Validation."
 ::= { slbGeneralCfg 50 }


-- WAP Health Check configuration

slbCurCfgWaphcWSPPort OBJECT-TYPE   
    SYNTAX INTEGER (0..65534)
    MAX-ACCESS read-only   
    STATUS current   
    DESCRIPTION 
        "The WSP port number to health check."   
    ::= { waphcCfg 1 }

slbNewCfgWaphcWSPPort OBJECT-TYPE   
    SYNTAX INTEGER (0..65534)
    MAX-ACCESS read-write
    STATUS current   
    DESCRIPTION 
        "The WSP port number to health check."   
    ::= { waphcCfg 2 }

slbCurCfgWaphcOffset OBJECT-TYPE   
    SYNTAX INTEGER (0..256)
    MAX-ACCESS read-only   
    STATUS current   
    DESCRIPTION 
        "The offset in received WSP packet."   
    ::= { waphcCfg 3 }

slbNewCfgWaphcOffset OBJECT-TYPE   
    SYNTAX INTEGER (0..256)
    MAX-ACCESS read-write
    STATUS current   
    DESCRIPTION 
        "The offset in received WSP packet."   
    ::= { waphcCfg 4 }

slbCurCfgWaphcSndContent OBJECT-TYPE   
    SYNTAX OCTET STRING (SIZE(0..512))
    MAX-ACCESS read-only   
    STATUS current   
    DESCRIPTION 
        "The content to be sent to the WAP gateway."   
    ::= { waphcCfg 5 }

slbNewCfgWaphcSndContent OBJECT-TYPE   
    SYNTAX OCTET STRING (SIZE(0..512))
    MAX-ACCESS read-write
    STATUS current   
    DESCRIPTION 
        "The content to be sent to the WAP gateway."   
    ::= { waphcCfg 6 }

slbCurCfgWaphcRcvContent OBJECT-TYPE   
    SYNTAX OCTET STRING (SIZE(0..512))
    MAX-ACCESS read-only   
    STATUS current   
    DESCRIPTION 
        "The content to be received from the WAP gateway."   
    ::= { waphcCfg 7 }

slbNewCfgWaphcRcvContent OBJECT-TYPE   
    SYNTAX OCTET STRING (SIZE(0..512))
    MAX-ACCESS read-write
    STATUS current   
    DESCRIPTION 
        "The content to be received from the WAP gateway."   
    ::= { waphcCfg 8 }

slbCurCfgWaphcWTLSPort OBJECT-TYPE   
    SYNTAX INTEGER (0..65534)
    MAX-ACCESS read-only   
    STATUS current   
    DESCRIPTION 
        "The WTLS port number to health check."   
    ::= { waphcCfg 9 }

slbNewCfgWaphcWTLSPort OBJECT-TYPE   
    SYNTAX INTEGER (0..65534)
    MAX-ACCESS read-write
    STATUS current   
    DESCRIPTION 
        "The WTLS port number to health check."   
    ::= { waphcCfg 10 }

slbCurCfgWaphcWTPSndContent OBJECT-TYPE   
    SYNTAX OCTET STRING (SIZE(0..512))
    MAX-ACCESS read-only   
    STATUS current   
    DESCRIPTION 
        "The WTP+WSP content to be sent to the WAP gateway."   
    ::= { waphcCfg 11 }

slbNewCfgWaphcWTPSndContent OBJECT-TYPE   
    SYNTAX OCTET STRING (SIZE(0..512))
    MAX-ACCESS read-write
    STATUS current   
    DESCRIPTION 
        "The WTP+WSP content to be sent to the WAP gateway."   
    ::= { waphcCfg 12 }

slbCurCfgWaphcWTPRcvContent OBJECT-TYPE   
    SYNTAX OCTET STRING (SIZE(0..512))
    MAX-ACCESS read-only   
    STATUS current   
    DESCRIPTION 
        "The WTP+WSP content to be received from the WAP gateway."   
    ::= { waphcCfg 13 }

slbNewCfgWaphcWTPRcvContent OBJECT-TYPE   
    SYNTAX OCTET STRING (SIZE(0..512))
    MAX-ACCESS read-write
    STATUS current   
    DESCRIPTION 
        "The WTP+WSP content to be received from the WAP gateway."   
    ::= { waphcCfg 14 }

slbCurCfgWaphcWTPConnContent OBJECT-TYPE   
    SYNTAX OCTET STRING (SIZE(0..512))
    MAX-ACCESS read-only   
    STATUS current   
    DESCRIPTION 
        "The WTP+WSP CONNECT content to be sent to the WAP gateway."   
    ::= { waphcCfg 15 }

slbNewCfgWaphcWTPConnContent OBJECT-TYPE   
    SYNTAX OCTET STRING (SIZE(0..512))
    MAX-ACCESS read-write
    STATUS current   
    DESCRIPTION 
        "The WTP+WSP CONNECT content to be sent to the WAP gateway."   
    ::= { waphcCfg 16 }

slbCurCfgWaphcWTPPort OBJECT-TYPE   
    SYNTAX INTEGER (0..65534)
    MAX-ACCESS read-only   
    STATUS current   
    DESCRIPTION 
        "The WTP port number to health check."   
    ::= { waphcCfg 17 }

slbNewCfgWaphcWTPPort OBJECT-TYPE   
    SYNTAX INTEGER (0..65534)
    MAX-ACCESS read-write
    STATUS current   
    DESCRIPTION 
        "The WTP port number to health check."   
    ::= { waphcCfg 18 }

slbCurCfgWaphcWTLSWSPPort OBJECT-TYPE   
    SYNTAX INTEGER (0..65534)
    MAX-ACCESS read-only   
    STATUS current   
    DESCRIPTION 
        "The WTLS+WSP port number to health check."   
    ::= { waphcCfg 19 }

slbNewCfgWaphcWTLSWSPPort OBJECT-TYPE   
    SYNTAX INTEGER (0..65534)
    MAX-ACCESS read-write
    STATUS current   
    DESCRIPTION 
        "The WTLS+WSP port number to health check."   
    ::= { waphcCfg 20 }

slbCurCfgWaphcWTPOffset OBJECT-TYPE   
    SYNTAX INTEGER (0..256)
    MAX-ACCESS read-only   
    STATUS current   
    DESCRIPTION 
        "The offset in received WTP packet."   
    ::= { waphcCfg 21 }

slbNewCfgWaphcWTPOffset OBJECT-TYPE   
    SYNTAX INTEGER (0..256)
    MAX-ACCESS read-write
    STATUS current   
    DESCRIPTION 
        "The offset in received WTP packet."   
    ::= { waphcCfg 22 }

slbCurCfgWaphcCouple OBJECT-TYPE
    SYNTAX INTEGER {
        enabled(1),
        disabled(2)
        }
    MAX-ACCESS  read-only
    STATUS  current
    DESCRIPTION
        "Enable or disable coupling of WAP and RADIUS Accounting 
	 health checks."
    ::= { waphcCfg 23 }

slbNewCfgWaphcCouple OBJECT-TYPE
    SYNTAX INTEGER {
        enabled(1),
        disabled(2)
        }
    MAX-ACCESS  read-write
    STATUS  current
    DESCRIPTION
        "Enable or disable coupling of WAP and RADIUS Accounting 
	 health checks."
    ::= { waphcCfg 24 }

-- WAP Load Balancing Configuration 

slbCurCfgWapTpcp OBJECT-TYPE
    SYNTAX INTEGER {
        enabled(1),
        disabled(2)
        }
    MAX-ACCESS  read-only
    STATUS  current
    DESCRIPTION
        "Enable or disable WAP load balancing. "
    ::= { wapCfg 1 }

slbNewCfgWapTpcp OBJECT-TYPE
    SYNTAX INTEGER {
        enabled(1),
        disabled(2)
        }
    MAX-ACCESS  read-write
    STATUS  current
    DESCRIPTION
        "Enable or disable WAP load balancing. "
    ::= { wapCfg 2 }

slbCurCfgWapDebug OBJECT-TYPE
    SYNTAX  INTEGER  (0..10)
    MAX-ACCESS  read-only
    STATUS  current
    DESCRIPTION
        "WAP Debug level."
    ::= { wapCfg 3 }

slbNewCfgWapDebug OBJECT-TYPE
    SYNTAX  INTEGER  (0..10)
    MAX-ACCESS  read-write
    STATUS  current
    DESCRIPTION
        "WAP Debug level."
    ::= { wapCfg 4 }


-- Synch Peer Switch Configuration
slbPeerTableMaxSize OBJECT-TYPE
    SYNTAX  Integer32 
    MAX-ACCESS  read-only 
    STATUS  current 
    DESCRIPTION 
        "The maximum number of entries in SLB Peer Table." 
    ::= { syncCfg 2 }

slbCurCfgPeerTable OBJECT-TYPE
    SYNTAX SEQUENCE OF SlbCurCfgPeerEntry
    MAX-ACCESS not-accessible
    STATUS current
    DESCRIPTION
        "The table of Synch Peer Switch configuration in the current_config."
    ::= { syncCfg 3 }

slbCurCfgPeerEntry OBJECT-TYPE
    SYNTAX SlbCurCfgPeerEntry
    MAX-ACCESS not-accessible
    STATUS current
    DESCRIPTION
        "Information about Synch Peer Switch configuration."
    INDEX { slbCurCfgPeerIndex }
    ::= { slbCurCfgPeerTable 1 }
 
SlbCurCfgPeerEntry ::= SEQUENCE {
    slbCurCfgPeerIndex          Integer32,
    slbCurCfgPeerIpAddr         IpAddress,
    slbCurCfgPeerState          INTEGER
    }
 
slbCurCfgPeerIndex OBJECT-TYPE
    SYNTAX Integer32
    MAX-ACCESS read-only
    STATUS current
    DESCRIPTION
        "The index for synch peer switchs."
    ::= { slbCurCfgPeerEntry 1 }

slbCurCfgPeerIpAddr OBJECT-TYPE
    SYNTAX IpAddress
    MAX-ACCESS read-only
    STATUS current
    DESCRIPTION
        "The IP address of the peer switch."
    ::= { slbCurCfgPeerEntry 2 }
 
slbCurCfgPeerState OBJECT-TYPE
    SYNTAX INTEGER {
        enable(1),
        disable(2)
        }
    MAX-ACCESS  read-only
    STATUS  current
    DESCRIPTION
        "Enable or disable the peer switch."
    ::= { slbCurCfgPeerEntry 3 }
 
slbNewCfgPeerTable OBJECT-TYPE
    SYNTAX SEQUENCE OF SlbNewCfgPeerEntry
    MAX-ACCESS not-accessible
    STATUS current
    DESCRIPTION
        "The table of Synch Peer Switch configuration in the new_config."
    ::= { syncCfg 4 }
 
slbNewCfgPeerEntry OBJECT-TYPE
    SYNTAX SlbNewCfgPeerEntry
    MAX-ACCESS not-accessible
    STATUS current
    DESCRIPTION
        "Information about synch peer switch  configuration."
    INDEX { slbNewCfgPeerIndex }
    ::= { slbNewCfgPeerTable 1 }
 
SlbNewCfgPeerEntry ::= SEQUENCE {
    slbNewCfgPeerIndex          Integer32,
    slbNewCfgPeerIpAddr         IpAddress,
    slbNewCfgPeerState          INTEGER,
    slbNewCfgPeerDelete         INTEGER
    }
 
slbNewCfgPeerIndex OBJECT-TYPE
    SYNTAX Integer32
    MAX-ACCESS read-only
    STATUS current
    DESCRIPTION
        "The index number for synch peer switchs."
    ::= { slbNewCfgPeerEntry 1 }
 
slbNewCfgPeerIpAddr OBJECT-TYPE
    SYNTAX IpAddress
    MAX-ACCESS read-create
    STATUS current
    DESCRIPTION
        "The IP address of the peer switch."
    ::= { slbNewCfgPeerEntry 2 }
 
slbNewCfgPeerState OBJECT-TYPE
    SYNTAX INTEGER {
        enable(1),
        disable(2)
        }
    MAX-ACCESS  read-create
    STATUS  current
    DESCRIPTION
        "Enable or disable the peer switch."
    ::= { slbNewCfgPeerEntry 3 }
 
slbNewCfgPeerDelete OBJECT-TYPE
    SYNTAX INTEGER {
        other(1),
        delete(2)
        }
    MAX-ACCESS  read-create
    STATUS  current
    DESCRIPTION
        "By setting the value to delete(2), the entire row is
         deleted."
    ::= { slbNewCfgPeerEntry 4 }

slbCurCfgSyncFilt OBJECT-TYPE
    SYNTAX  INTEGER {
        enabled(1),
        disabled(2)
        }
    MAX-ACCESS  read-only
    STATUS  current
    DESCRIPTION
        "Enable or disable synch filter configuration."
    ::= { syncGeneralCfg 1 }

slbNewCfgSyncFilt OBJECT-TYPE
    SYNTAX  INTEGER {
        enabled(1),
        disabled(2)
        }
    MAX-ACCESS  read-write
    STATUS  current
    DESCRIPTION
        "Enable or disable synch filter configuration."
    ::= { syncGeneralCfg 2 }

slbCurCfgSyncPort OBJECT-TYPE
    SYNTAX  INTEGER {
        enabled(1),
        disabled(2)
        }
    MAX-ACCESS  read-only
    STATUS  current
    DESCRIPTION
        "Enable or disable synch port configuration."
    ::= { syncGeneralCfg 3 }

slbNewCfgSyncPort OBJECT-TYPE
    SYNTAX  INTEGER {
        enabled(1),
        disabled(2)
        }
    MAX-ACCESS  read-write
    STATUS  current
    DESCRIPTION
        "Enable or disable synch port configuration."
    ::= { syncGeneralCfg 4 }

slbCurCfgSyncVrrp OBJECT-TYPE
    SYNTAX  INTEGER {
        enabled(1),
        disabled(2)
        }
    MAX-ACCESS  read-only
    STATUS  current
    DESCRIPTION
        "Enable or disable synch VRRP Priorities."
    ::= { syncGeneralCfg 5 }

slbNewCfgSyncVrrp OBJECT-TYPE
    SYNTAX  INTEGER {
        enabled(1),
        disabled(2)
        }
    MAX-ACCESS  read-write
    STATUS  current
    DESCRIPTION
        "Enable or disable synch VRRP Priorities."
    ::= { syncGeneralCfg 6 }

slbCurCfgSyncPip OBJECT-TYPE
    SYNTAX  INTEGER {
        enabled(1),
        disabled(2)
        }
    MAX-ACCESS  read-only
    STATUS  current
    DESCRIPTION
        "Enable or disable synch proxy IP addresses."
    ::= { syncGeneralCfg 7 }

slbNewCfgSyncPip OBJECT-TYPE
    SYNTAX  INTEGER {
        enabled(1),
        disabled(2)
        }
    MAX-ACCESS  read-write
    STATUS  current
    DESCRIPTION
        "Enable or disable synch proxy IP addresses."
    ::= { syncGeneralCfg 8 }

slbCurCfgSyncSfo OBJECT-TYPE
    SYNTAX  INTEGER {
        enabled(1),
        disabled(2)
        }
    MAX-ACCESS  read-only
    STATUS  current
    DESCRIPTION
        "Enable or disable synch stateful failover."
    ::= { syncGeneralCfg 9 }

slbNewCfgSyncSfo OBJECT-TYPE
    SYNTAX  INTEGER {
        enabled(1),
        disabled(2)
        }
    MAX-ACCESS  read-write
    STATUS  current
    DESCRIPTION
        "Enable or disable synch stateful failover."
    ::= { syncGeneralCfg 10 }

slbCurCfgSyncSfoUpdatePeriod OBJECT-TYPE
    SYNTAX  INTEGER (1..60)
    MAX-ACCESS  read-only
    STATUS  current
    DESCRIPTION
        "The stateful failover update period in seconds."
    ::= { syncGeneralCfg 11 }

slbNewCfgSyncSfoUpdatePeriod OBJECT-TYPE
    SYNTAX  INTEGER (1..60)
    MAX-ACCESS  read-write
    STATUS  current
    DESCRIPTION
        "The stateful failover update period in seconds."
    ::= { syncGeneralCfg 12 }

slbCurCfgSyncBwm OBJECT-TYPE
    SYNTAX  INTEGER {
        enabled(1),
        disabled(2)
        }
    MAX-ACCESS  read-only
    STATUS  current
    DESCRIPTION
        "Enable or disable syncing BWM configuration."
    ::= { syncGeneralCfg 13 }

slbNewCfgSyncBwm OBJECT-TYPE
    SYNTAX  INTEGER {
        enabled(1),
        disabled(2)
        }
    MAX-ACCESS  read-write
    STATUS  current
    DESCRIPTION
        "Enable or disable syncing BWM configuration."
    ::= { syncGeneralCfg 14 }
    
slbCurCfgSyncPeerPip OBJECT-TYPE
    SYNTAX  INTEGER {
        enabled(1),
        disabled(2)
        }
    MAX-ACCESS  read-only
    STATUS  current
    DESCRIPTION
        "Enable or disable synch peer proxy IP addresses."
    ::= { syncGeneralCfg 15 }

slbNewCfgSyncPeerPip OBJECT-TYPE
    SYNTAX  INTEGER {
        enabled(1),
        disabled(2)
        }
    MAX-ACCESS  read-write
    STATUS  current
    DESCRIPTION
        "Enable or disable synch peer proxy IP addresses."
    ::= { syncGeneralCfg 16}
    
-- SYN Attack Detection 

synAttackCurCfgInterval OBJECT-TYPE
    SYNTAX  INTEGER (2..3600)
    MAX-ACCESS  read-only
    STATUS  current
    DESCRIPTION
        "The interval specified in seconds determines how frequently the 
         switch checks for SYN attacks."
    ::= { synAttackDetCfg 1 }

synAttackNewCfgInterval OBJECT-TYPE
    SYNTAX  INTEGER (2..3600)
    MAX-ACCESS  read-write
    STATUS  current
    DESCRIPTION
        "The interval specified in seconds determines how frequently the 
         switch checks for SYN attacks."
    ::= { synAttackDetCfg 2 }

synAttackCurCfgThreshhold OBJECT-TYPE
    SYNTAX  INTEGER (1..100000)
    MAX-ACCESS  read-only
    STATUS  current
    DESCRIPTION
        "The threshhold indicating the number of new half-open sessions
         per second."
    ::= { synAttackDetCfg 3 }

synAttackNewCfgThreshhold OBJECT-TYPE
    SYNTAX  INTEGER (1..100000)
    MAX-ACCESS  read-write
    STATUS  current
    DESCRIPTION
        "The threshhold indicating the number of new half-open sessions
         per second."
    ::= { synAttackDetCfg 4 }


-- Filtering Group
 
fltCfgTableMaxSize OBJECT-TYPE
    SYNTAX  Integer32
    MAX-ACCESS  read-only
    STATUS  current
    DESCRIPTION
        "The maximum number of filtering table entries."
    ::= { filterCfg 1 }

-- Current Config Filtering Table

fltCurCfgTable OBJECT-TYPE
    SYNTAX  SEQUENCE OF FltCurCfgTableEntry
    MAX-ACCESS  not-accessible
    STATUS  current
    DESCRIPTION
        "The filtering table in the current configuration block."
    ::= { filterCfg 2 }

fltCurCfgTableEntry OBJECT-TYPE
    SYNTAX  FltCurCfgTableEntry
    MAX-ACCESS  not-accessible
    STATUS  current
    DESCRIPTION
        "A row in the filtering table."
    INDEX   { fltCurCfgIndx }
    ::= { fltCurCfgTable 1 }

FltCurCfgTableEntry ::= SEQUENCE {
    fltCurCfgIndx             Integer32,
    fltCurCfgSrcIpMac         INTEGER,
    fltCurCfgSrcIp            IpAddress,
    fltCurCfgSrcIpMask        IpAddress,
    fltCurCfgDstIpMac         INTEGER,
    fltCurCfgDstIp            IpAddress,
    fltCurCfgDstIpMask        IpAddress,
    fltCurCfgProtocol         INTEGER,
    fltCurCfgRangeLowSrcPort  INTEGER,
    fltCurCfgRangeHighSrcPort INTEGER,
    fltCurCfgRangeLowDstPort  INTEGER,
    fltCurCfgRangeHighDstPort INTEGER,
    fltCurCfgAction           INTEGER,
    fltCurCfgRedirPort        INTEGER,
    fltCurCfgRedirGroup       Integer32,
    fltCurCfgLog              INTEGER,
    fltCurCfgState            INTEGER,
    fltCurCfgNat              INTEGER,
    fltCurCfgCache            INTEGER,
    fltCurCfgInvert           INTEGER,
    fltCurCfgClientProxy      INTEGER,
    fltCurCfgTcpAck           INTEGER,
    fltCurCfgSrcMac           PhysAddress,
    fltCurCfgDstMac           PhysAddress,
    fltCurCfgFtpNatActive     INTEGER,
    fltCurCfgAclTcpUrg        INTEGER, 
    fltCurCfgAclTcpAck        INTEGER, 
    fltCurCfgAclTcpPsh        INTEGER, 
    fltCurCfgAclTcpRst        INTEGER, 
    fltCurCfgAclTcpSyn        INTEGER, 
    fltCurCfgAclTcpFin        INTEGER,
    fltCurCfgAclIcmp	      INTEGER,
    fltCurCfgAclIpOption      INTEGER,
    fltCurCfgBwmContract      Integer32,
    fltCurCfgAclIpTos         INTEGER,
    fltCurCfgAclIpTosMask     INTEGER,
    fltCurCfgAclIpTosNew      INTEGER,
    fltCurCfgFwlb	      INTEGER,
    fltCurCfgNatTimeout       INTEGER,
    fltCurCfgLinklb           INTEGER,
    fltCurCfgWapRadiusSnoop   INTEGER,
    fltCurCfgIdslbHash        INTEGER,
    fltCurCfgVlan             INTEGER,
    fltCurCfgTcpRateLimit     INTEGER,
    fltCurCfgTcpRateMaxConn   INTEGER,
    fltCurCfgHash             INTEGER,
    fltCurCfgLayer7DenyState  INTEGER,
    fltCurCfgLayer7DenyUrlBmap OCTET STRING,
    fltCurCfgGotoFilter       Integer32,
    fltCurCfgRadiusWapPersist INTEGER,
    fltCurCfgPbind            INTEGER,
    fltCurCfgTimeWindow       INTEGER,
    fltCurCfgHoldDuration     INTEGER,
    fltCurCfgProxyIp          IpAddress,
    fltCurCfgPatternMatch     INTEGER,
    fltCurCfgLayer7DenyMatchAll INTEGER,
    fltCurCfgLayer7ParseAll   INTEGER,
    fltCurCfgSecurityParseAll INTEGER,
    fltCurCfgPatternMatchGroupBmap OCTET STRING,
    fltCurCfg8021pBitsValue   INTEGER,
    fltCurCfg8021pBitsMatch   INTEGER,
    fltCurCfgAclIpLength      INTEGER,
    fltCurCfgIdsGroup         Integer32,
    fltCurCfgEgressPip        INTEGER,
    fltCurCfgDbind            INTEGER,
    fltCurCfgReverse          INTEGER,
    fltCurCfgRevBwmContract   Integer32, 
    fltCurCfgParseChn         INTEGER,
    fltCurCfgRtpBwmContract   Integer32,
    fltCurCfgSipParsing       INTEGER,
    fltCurCfgSessionMirror    INTEGER,
    fltCurCfgIpVer            INTEGER,
    fltCurCfgIpv6Sip          DisplayString,
    fltCurCfgIpv6Sprefix      INTEGER,
    fltCurCfgIpv6Dip          DisplayString,
    fltCurCfgIpv6Dprefix      INTEGER,
    fltCurCfgName             DisplayString
    }

fltCurCfgIndx OBJECT-TYPE
    SYNTAX  Integer32
    MAX-ACCESS  read-only
    STATUS  current
    DESCRIPTION
        "The filteriang table index."
    ::= { fltCurCfgTableEntry 1 }

fltCurCfgSrcIp OBJECT-TYPE
    SYNTAX  IpAddress
    MAX-ACCESS  read-only
    STATUS  current
    DESCRIPTION
        "The source IP address to be filtered."
    ::= { fltCurCfgTableEntry 2 }

fltCurCfgSrcIpMask OBJECT-TYPE
    SYNTAX  IpAddress
    MAX-ACCESS  read-only
    STATUS  current
    DESCRIPTION
        "The source IP sub-net mask for filtering."
    ::= { fltCurCfgTableEntry 3 }

fltCurCfgDstIp OBJECT-TYPE
    SYNTAX  IpAddress
    MAX-ACCESS  read-only
    STATUS  current
    DESCRIPTION
        "The destination IP address to be filtered."
    ::= { fltCurCfgTableEntry 4 }

fltCurCfgDstIpMask OBJECT-TYPE
    SYNTAX  IpAddress
    MAX-ACCESS  read-only
    STATUS  current
    DESCRIPTION
        "The destination IP sub-net mask for filtering."
    ::= { fltCurCfgTableEntry 5 }

fltCurCfgProtocol OBJECT-TYPE
    SYNTAX  INTEGER (0..255)
    MAX-ACCESS  read-only
    STATUS  current
    DESCRIPTION
        "The protocol to be filtered."
    ::= { fltCurCfgTableEntry 6 }

fltCurCfgRangeHighSrcPort OBJECT-TYPE
    SYNTAX  INTEGER (0..65534)
    MAX-ACCESS  read-only
    STATUS  current
    DESCRIPTION
        "The higher source TCP/UDP port number to be filtered. It applies 
         only when protocol defined in fltCurCfgProtocol is UDP or TCP.
         '0' means no filtering."
    ::= { fltCurCfgTableEntry 7 }

fltCurCfgRangeLowSrcPort OBJECT-TYPE
    SYNTAX  INTEGER (0..65534)
    MAX-ACCESS  read-only
    STATUS  current
    DESCRIPTION
        "The lower source TCP/UDP port number to be filtered. It applies 
         only when protocol defined in fltCurCfgProtocol is UDP or TCP.  
         '0' means no filtering."
    ::= { fltCurCfgTableEntry 8 }

fltCurCfgRangeLowDstPort OBJECT-TYPE
    SYNTAX  INTEGER (0..65534)
    MAX-ACCESS  read-only
    STATUS  current
    DESCRIPTION
        "The lower destination TCP/UDP port number to be filtered. It applies 
         only when protocol defined in fltCurCfgProtocol is UDP or TCP.
         '0' means no filtering."
    ::= { fltCurCfgTableEntry 9 }

fltCurCfgRangeHighDstPort OBJECT-TYPE
    SYNTAX  INTEGER (0..65534)
    MAX-ACCESS  read-only
    STATUS  current
    DESCRIPTION
        "The higher destination TCP/UDP port number to be filtered. It applies
         only when protocol defined in fltCurCfgProtocol is UDP or TCP.
         '0' means no filtering."
    ::= { fltCurCfgTableEntry 10 }

fltCurCfgAction OBJECT-TYPE
    SYNTAX  INTEGER {
        allow(1),
        deny(2),
        redirect(3),
        nat(4),      -- network address translation
        goto(5)
        }
    MAX-ACCESS  read-only
    STATUS  current
    DESCRIPTION
        "The action for the filtering rule."
    ::= { fltCurCfgTableEntry 11 }

fltCurCfgRedirPort OBJECT-TYPE
    SYNTAX  INTEGER (0..65534)
    MAX-ACCESS  read-only
    STATUS  current
    DESCRIPTION
        "The real server port number used for redirection."
    ::= { fltCurCfgTableEntry 12 }

fltCurCfgRedirGroup OBJECT-TYPE
    SYNTAX  Integer32
    MAX-ACCESS  read-only
    STATUS  current
    DESCRIPTION
        "The real server group to be redirected to."
    ::= { fltCurCfgTableEntry 13 }

fltCurCfgLog OBJECT-TYPE
    SYNTAX  INTEGER {
        enabled(1),
        disabled(2)
        }
    MAX-ACCESS  read-only
    STATUS  current
    DESCRIPTION
        "Enable or disable logging."
    ::= { fltCurCfgTableEntry 14 }

fltCurCfgState OBJECT-TYPE
    SYNTAX  INTEGER {
        enabled(1),
        disabled(2)
        }
    MAX-ACCESS  read-only
    STATUS  current
    DESCRIPTION
        "The state of this filtering rule."
    ::= { fltCurCfgTableEntry 15 }

fltCurCfgNat OBJECT-TYPE
    SYNTAX  INTEGER {
        destination-address(1),
        source-address(2)
        }
    MAX-ACCESS  read-only
    STATUS  current
    DESCRIPTION
        "The selection of destination or source for network address 
         translation."
    ::= { fltCurCfgTableEntry 16 }

fltCurCfgCache OBJECT-TYPE
    SYNTAX  INTEGER {
        enabled(1),
        disabled(2)
        }
    MAX-ACCESS  read-only
    STATUS  current
    DESCRIPTION
        "Enable or disable caching sessions that match filter."
    ::= { fltCurCfgTableEntry 17 }

fltCurCfgInvert OBJECT-TYPE
    SYNTAX  INTEGER {
        enabled(1),
        disabled(2)
        }
    MAX-ACCESS  read-only
    STATUS  current
    DESCRIPTION
        "Turn the invert logic on or off for the filter entry."
    ::= { fltCurCfgTableEntry 18 }

fltCurCfgClientProxy OBJECT-TYPE
    SYNTAX  INTEGER {
        enabled(1),
        disabled(2)
        }
    MAX-ACCESS  read-only
    STATUS  current
    DESCRIPTION
        "Enable or disable client proxy."
    ::= { fltCurCfgTableEntry 19 }

fltCurCfgTcpAck OBJECT-TYPE
    SYNTAX  INTEGER {
        enabled(1),
        disabled(2)
        }
    MAX-ACCESS  read-only
    STATUS  current
    DESCRIPTION
        "Enable or disable filtering on matching TCP ACK and RST flag."
    ::= { fltCurCfgTableEntry 20 }


fltCurCfgSrcMac OBJECT-TYPE
    SYNTAX  PhysAddress 
    MAX-ACCESS  read-only
    STATUS  current
    DESCRIPTION
        "The source MAC address to be filtered."
    ::= { fltCurCfgTableEntry 22 }

fltCurCfgDstMac OBJECT-TYPE
    SYNTAX  PhysAddress 
    MAX-ACCESS  read-only
    STATUS  current
    DESCRIPTION
        "The Destination MAC address to be filtered."
    ::= { fltCurCfgTableEntry 23 }

fltCurCfgFtpNatActive OBJECT-TYPE
    SYNTAX  INTEGER{
	enabled(1),
	disabled(2)
	}
    MAX-ACCESS  read-only
    STATUS  current	
    DESCRIPTION
        "Enable or disable FTP NAT for active ftp only."
    ::= { fltCurCfgTableEntry 24 }

-- Current Config for TCP ACL filtering Table 

fltCurCfgAclTcpUrg OBJECT-TYPE
    SYNTAX  INTEGER {
	enable(1),
	disable(2)
	}
    MAX-ACCESS  read-only
    STATUS  current
    DESCRIPTION
        "Enable or disable TCP URG packet."
    ::= { fltCurCfgTableEntry 25 }	

fltCurCfgAclTcpAck OBJECT-TYPE
    SYNTAX  INTEGER {
	enable(1),
	disable(2)
	}
    MAX-ACCESS  read-only
    STATUS  current
    DESCRIPTION
        "Enable or disable TCP ACK packet."
    ::= { fltCurCfgTableEntry 26 }	

fltCurCfgAclTcpPsh OBJECT-TYPE
    SYNTAX  INTEGER {
	enable(1),
	disable(2)
	}
    MAX-ACCESS  read-only
    STATUS  current
    DESCRIPTION
        "Enable or disable TCP PSH packet."
    ::= { fltCurCfgTableEntry 27 }	

fltCurCfgAclTcpRst OBJECT-TYPE
    SYNTAX  INTEGER {
	enable(1),
	disable(2)
	}
    MAX-ACCESS  read-only
    STATUS  current 
    DESCRIPTION
        "Enable or disable TCP RST packet."
    ::= { fltCurCfgTableEntry 28 }	

fltCurCfgAclTcpSyn OBJECT-TYPE
    SYNTAX  INTEGER {
	enable(1),
	disable(2)
	}
    MAX-ACCESS  read-only
    STATUS  current
    DESCRIPTION
        "Enable or disable TCP SYN packet."
    ::= { fltCurCfgTableEntry 29 }	

fltCurCfgAclTcpFin OBJECT-TYPE
    SYNTAX  INTEGER {
	enable(1),
	disable(2)
	}
    MAX-ACCESS  read-only
    STATUS  current
    DESCRIPTION
	"Enable or disable TCP FIN packet."
    ::= { fltCurCfgTableEntry 30 }	

-- Current Config for ICMP Type ACL filtering Table 

fltCurCfgAclIcmp OBJECT-TYPE
    SYNTAX  INTEGER (0..255)
    MAX-ACCESS  read-only
    STATUS  current
    DESCRIPTION
        "ICMP type to be filtered. A ICMP type of 255 indicates 'any'"
    ::= { fltCurCfgTableEntry 31 }	

-- Current Config IP Option ACL Filtering Table

fltCurCfgAclIpOption OBJECT-TYPE
    SYNTAX  INTEGER {
        enable(1),
	disable(2)
        }
    MAX-ACCESS  read-only
    STATUS  current
    DESCRIPTION
        "Enable or disable IP option matching."
    ::= { fltCurCfgTableEntry 32 }

fltCurCfgBwmContract OBJECT-TYPE
    SYNTAX  Integer32
    MAX-ACCESS  read-only
    STATUS  current
    DESCRIPTION
	"Filt default BW contract number."
    ::= { fltCurCfgTableEntry 33 }	

fltCurCfgAclIpTos OBJECT-TYPE
    SYNTAX  INTEGER (0..255)
    MAX-ACCESS  read-only
    STATUS  current
    DESCRIPTION
        "The IP TOS value to be filtered."
    ::= { fltCurCfgTableEntry 34 }	

fltCurCfgAclIpTosMask OBJECT-TYPE
    SYNTAX  INTEGER (0..255)
    MAX-ACCESS  read-only
    STATUS  current
    DESCRIPTION
        "The IP TOS mask for filtering."
    ::= { fltCurCfgTableEntry 35 }	

fltCurCfgAclIpTosNew OBJECT-TYPE
    SYNTAX  INTEGER (0..255)
    MAX-ACCESS  read-only
    STATUS  current
    DESCRIPTION
        "The new IP TOS value to over-write when filtering fired."
    ::= { fltCurCfgTableEntry 36 }	

fltCurCfgFwlb OBJECT-TYPE
    SYNTAX  INTEGER {
        enabled(1),
        disabled(2)
        }
    MAX-ACCESS  read-only
    STATUS  current
    DESCRIPTION
        "Enable or disable filtering on firewall redirect hash method."
    ::= { fltCurCfgTableEntry 37 }

fltCurCfgNatTimeout OBJECT-TYPE
    SYNTAX  INTEGER (4..32768)
    MAX-ACCESS  read-only
    STATUS  current
    DESCRIPTION
        "The NAT session timeout. The timeout value should be an even number 
         between 4 and 32768."
    ::= { fltCurCfgTableEntry 38 }	

fltCurCfgLinklb OBJECT-TYPE
    SYNTAX  INTEGER {
        enabled(1),
        disabled(2)
        }
    MAX-ACCESS  read-only
    STATUS  current
    DESCRIPTION
        "Enable or disable WAN link load balancing."
    ::= { fltCurCfgTableEntry 39 }

fltCurCfgWapRadiusSnoop OBJECT-TYPE
    SYNTAX  INTEGER {
        enabled(1),
        disabled(2)
        }
    MAX-ACCESS  read-only
    STATUS  current
    DESCRIPTION
        "Enable or disable WAP RADIUS snooping."
    ::= { fltCurCfgTableEntry 40 }

fltCurCfgSrcIpMac OBJECT-TYPE
    SYNTAX  INTEGER {
        ip(1),
        mac(2)
        }
    MAX-ACCESS  read-only
    STATUS  current
    DESCRIPTION
        "Set a flag indicating whether filtering should be based on the 
         source IP address or the source MAC address field."
    ::= { fltCurCfgTableEntry 41 }

fltCurCfgDstIpMac OBJECT-TYPE
    SYNTAX  INTEGER {
        ip(1),
        mac(2)
        }
    MAX-ACCESS  read-only
    STATUS  current
    DESCRIPTION
        "Set a flag indicating whether filtering should be based on the 
         destination IP address or the destination MAC address field."
    ::= { fltCurCfgTableEntry 42 }

fltCurCfgIdslbHash OBJECT-TYPE
    SYNTAX  INTEGER {
        sip(1),
        dip(2),
        both(3)
        }
    MAX-ACCESS  read-only
    STATUS  current
    DESCRIPTION
        "Set hash parameter for intrusion detection server load balancing."
    ::= { fltCurCfgTableEntry 43 }

fltCurCfgVlan OBJECT-TYPE
    SYNTAX  INTEGER (0..4090)
    MAX-ACCESS  read-only
    STATUS  current
    DESCRIPTION
        "Set the VLAN assoicated with the filter."
    ::= { fltCurCfgTableEntry 44 }

fltCurCfgName OBJECT-TYPE
    SYNTAX DisplayString (SIZE(0..31))
    MAX-ACCESS read-only
    STATUS current
    DESCRIPTION
        "The name of the filter."
    ::= { fltCurCfgTableEntry 45 }

fltCurCfgTcpRateLimit OBJECT-TYPE
    SYNTAX  INTEGER {
        enabled(1),
        disabled(2)
        }
    MAX-ACCESS  read-only
    STATUS  current
    DESCRIPTION
        "Enable or disable protocol rate limiting."
    ::= { fltCurCfgTableEntry 46 }

fltCurCfgTcpRateMaxConn OBJECT-TYPE
    SYNTAX  INTEGER (0..255)
    MAX-ACCESS  read-only
    STATUS  current
    DESCRIPTION
        "Set maximum connections (number of connections in units of 10)
         for TCP connection rate limiting.  In the case of ICMP and UDP,
	 this is the maximum packets (number of packets in units of 10)."
    ::= { fltCurCfgTableEntry 47 }

fltCurCfgHash OBJECT-TYPE
    SYNTAX  INTEGER {
	auto(1),
        sip(2),
        dip(3),
        both(4),
	sipsport(5)
        }
    MAX-ACCESS  read-only
    STATUS  current
    DESCRIPTION
        "Set hash parameter for the filter."
    ::= { fltCurCfgTableEntry 48 }


fltCurCfgLayer7DenyState OBJECT-TYPE
    SYNTAX  INTEGER {
        enabled(1),
        disabled(2)
        }
    MAX-ACCESS  read-only
    STATUS  current
    DESCRIPTION
        "Enable or disable layer 7 deny filtering."
    ::= { fltCurCfgTableEntry 50 }

fltCurCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltCurCfgTableEntry 51 }

fltCurCfgGotoFilter OBJECT-TYPE
    SYNTAX  Integer32
    MAX-ACCESS  read-only
    STATUS  current	
    DESCRIPTION
        "The filter ID for GOTO action in the current config."
    ::= { fltCurCfgTableEntry 52 }

fltCurCfgRadiusWapPersist OBJECT-TYPE
    SYNTAX  INTEGER {
        enabled(1),
        disabled(2)
        }
    MAX-ACCESS  read-only
    STATUS  current	
    DESCRIPTION
        "Enable or disable Radius/WAP persistence."
    ::= { fltCurCfgTableEntry 53 }

fltCurCfgPbind OBJECT-TYPE
    SYNTAX  INTEGER {
        enabled(1),
        disabled(2)
        }
    MAX-ACCESS  read-only
    STATUS  current	
    DESCRIPTION
        "Enable or disable filter persistent binding."
    ::= { fltCurCfgTableEntry 54 }
   
fltCurCfgTimeWindow OBJECT-TYPE
    SYNTAX  INTEGER (1..65535)
    MAX-ACCESS  read-only
    STATUS  current
    DESCRIPTION
        "The time window for protocol rate limiting (in seconds)."
    ::= { fltCurCfgTableEntry 55 }

fltCurCfgHoldDuration OBJECT-TYPE
    SYNTAX  INTEGER (2..65535)
    MAX-ACCESS  read-only
    STATUS  current
    DESCRIPTION
        "The hold down duration for protocol rate limiting (in minutes)."
    ::= { fltCurCfgTableEntry 56 }

fltCurCfgPatternMatch OBJECT-TYPE
    SYNTAX  INTEGER {
        enabled(1),
        disabled(2)
        }
    MAX-ACCESS  read-only
    STATUS  current	
    DESCRIPTION
        "Enable or disable binary pattern matching."
    ::= { fltCurCfgTableEntry 57 }

fltCurCfgLayer7DenyMatchAll OBJECT-TYPE
    SYNTAX  INTEGER {
        enabled(1),
        disabled(2)
        }
    MAX-ACCESS  read-only
    STATUS  current
    DESCRIPTION
        "Enable or disable match-all criteria for L7 deny string matching."
    ::= { fltCurCfgTableEntry 58 }
    
fltCurCfgProxyIp OBJECT-TYPE
    SYNTAX  IpAddress
    MAX-ACCESS  read-only
    STATUS  current
    DESCRIPTION
        "The client proxy IP address for NAT and REDIR filter."
        
    ::= { fltCurCfgTableEntry 59 }
    
fltCurCfgLayer7ParseAll OBJECT-TYPE
    SYNTAX  INTEGER {
        enabled(1),
        disabled(2)
        }
    MAX-ACCESS  read-only
    STATUS  current
    DESCRIPTION
        "Enable or disable layer 7 lookup (parsing) of all packets."
    ::= { fltCurCfgTableEntry 60 }

fltCurCfgSecurityParseAll OBJECT-TYPE
    SYNTAX  INTEGER {
        enabled(1),
        disabled(2)
        }
    MAX-ACCESS  read-only
    STATUS  current
    DESCRIPTION
        "Enable or disable pattern string lookup (parsing) of all packets."
    ::= { fltCurCfgTableEntry 61 }
    
fltCurCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltCurCfgTableEntry 62 }

fltCurCfg8021pBitsValue OBJECT-TYPE
    SYNTAX  INTEGER (0..7)
    MAX-ACCESS  read-only
    STATUS  current
    DESCRIPTION
        "The 802.1p bits value to match."
    ::= { fltCurCfgTableEntry 63 }

fltCurCfg8021pBitsMatch OBJECT-TYPE
    SYNTAX  INTEGER {
        enabled(1),
        disabled(2)
        }
    MAX-ACCESS  read-only
    STATUS  current
    DESCRIPTION
        "Enable or disable matching on 802.1p bits in the packets."
    ::= { fltCurCfgTableEntry 64 }
 
fltCurCfgAclIpLength OBJECT-TYPE
    SYNTAX  INTEGER (0..65535)
    MAX-ACCESS  read-only
    STATUS  current 
    DESCRIPTION
        "Set the IP maximum packet length in bytes. A value can be either 0 
         which indicates 'any' length or between 64 and 65535."
    ::= { fltCurCfgTableEntry 65 }	

fltCurCfgIdsGroup OBJECT-TYPE
    SYNTAX  Integer32
    MAX-ACCESS  read-only
    STATUS  current
    DESCRIPTION
        "The real server group for IDS load balancing. A value of 0 indicates
	 'none'." 
    ::= { fltCurCfgTableEntry 66 }
    
fltCurCfgEgressPip OBJECT-TYPE
    SYNTAX  INTEGER {
        enabled(1),
        disabled(2)
        }
    MAX-ACCESS  read-only
    STATUS  current
    DESCRIPTION
        "Enable or disable pip selection based on egress port/vlan."
    ::= { fltCurCfgTableEntry 67 }
    
fltCurCfgDbind OBJECT-TYPE
    SYNTAX  INTEGER {
        enabled(1),
        disabled(2)
        }
    MAX-ACCESS  read-only
    STATUS  current	
    DESCRIPTION
        "Enable or disable filter delayed binding."
    ::= { fltCurCfgTableEntry 68 }

fltCurCfgRevBwmContract OBJECT-TYPE
    SYNTAX  Integer32
    MAX-ACCESS  read-only
    STATUS  current
    DESCRIPTION
	"Filt reverse session BWM contract number."
    ::= { fltCurCfgTableEntry 69 }	

fltCurCfgReverse OBJECT-TYPE
    SYNTAX  INTEGER {
        enabled(1),
        disabled(2)
        }
    MAX-ACCESS  read-only
    STATUS  current	
    DESCRIPTION
        "Enable or disable creating session for reverse side traffic."
    ::= { fltCurCfgTableEntry 70 }

fltCurCfgParseChn OBJECT-TYPE
    SYNTAX INTEGER { 
	enabled(1),
	disabled(2)
	}
    MAX-ACCESS  read-only
    STATUS  current
    DESCRIPTION
	"Enable or disable chained pgroup match criteria for l7 filtering."
    ::= { fltCurCfgTableEntry 71 }


fltCurCfgRtpBwmContract OBJECT-TYPE
    SYNTAX  Integer32
    MAX-ACCESS  read-only
    STATUS  current
    DESCRIPTION
        "BWM contract for SIP RTP traffic."
    ::= { fltCurCfgTableEntry 72 }

fltCurCfgSipParsing OBJECT-TYPE
    SYNTAX  INTEGER {
        enabled(1),
        disabled(2)
        }
    MAX-ACCESS  read-only
    STATUS  current
    DESCRIPTION
        "Enable or disable SIP NAT."
    ::= { fltCurCfgTableEntry 73 }


fltCurCfgSessionMirror  OBJECT-TYPE
    SYNTAX  INTEGER {
        enabled(1),
        disabled(2)
        }
    MAX-ACCESS  read-only
    STATUS  current
    DESCRIPTION
        "Enable or disable session mirroring."
    ::= { fltCurCfgTableEntry 74 }


fltCurCfgIpVer OBJECT-TYPE
    SYNTAX  INTEGER{
        ipv4(1),
        ipv6(2)
        }
    MAX-ACCESS  read-only
    STATUS  current
    DESCRIPTION
        "The type of IP address."
    ::= { fltCurCfgTableEntry 75 }

fltCurCfgIpv6Sip   OBJECT-TYPE
    SYNTAX   DisplayString (SIZE(0..40))
    MAX-ACCESS  read-only
    STATUS  current
    DESCRIPTION
        "The source IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 76 }

fltCurCfgIpv6Sprefix   OBJECT-TYPE
    SYNTAX  INTEGER(0..128) 
    MAX-ACCESS  read-only
    STATUS  current
    DESCRIPTION
        "The prefix length associated with source IP address ."
    ::= { fltCurCfgTableEntry 77 }

fltCurCfgIpv6Dip     OBJECT-TYPE
    SYNTAX   DisplayString (SIZE(0..40))
    MAX-ACCESS  read-only
    STATUS  current
    DESCRIPTION
        "The destination  IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 78 }

fltCurCfgIpv6Dprefix OBJECT-TYPE
    SYNTAX   INTEGER(0..128) 
    MAX-ACCESS  read-only
    STATUS  current
    DESCRIPTION
        "The prefix length associated with destination IP address ."
    ::= { fltCurCfgTableEntry 79 }


-- New Config Filtering Table

fltNewCfgTable OBJECT-TYPE
    SYNTAX  SEQUENCE OF FltNewCfgTableEntry
    MAX-ACCESS  not-accessible
    STATUS  current
    DESCRIPTION
        "The filtering table in the new configuration block."
    ::= { filterCfg 3 }

fltNewCfgTableEntry OBJECT-TYPE
    SYNTAX  FltNewCfgTableEntry
    MAX-ACCESS  not-accessible
    STATUS  current
    DESCRIPTION
        "A row in the filtering table."
    INDEX   { fltNewCfgIndx }
    ::= { fltNewCfgTable 1 }

FltNewCfgTableEntry ::= SEQUENCE {
    fltNewCfgIndx             Integer32,
    fltNewCfgSrcIpMac         INTEGER,
    fltNewCfgSrcIp            IpAddress,
    fltNewCfgSrcIpMask        IpAddress,
    fltNewCfgDstIpMac         INTEGER,
    fltNewCfgDstIp            IpAddress,
    fltNewCfgDstIpMask        IpAddress,
    fltNewCfgProtocol         INTEGER,
    fltNewCfgRangeLowSrcPort  INTEGER,
    fltNewCfgRangeHighSrcPort INTEGER,
    fltNewCfgRangeLowDstPort  INTEGER,
    fltNewCfgRangeHighDstPort INTEGER,
    fltNewCfgAction           INTEGER,
    fltNewCfgRedirPort        INTEGER,
    fltNewCfgRedirGroup       Integer32,
    fltNewCfgLog              INTEGER,
    fltNewCfgState            INTEGER,
    fltNewCfgNat              INTEGER,
    fltNewCfgCache            INTEGER,
    fltNewCfgInvert           INTEGER,
    fltNewCfgClientProxy      INTEGER,
    fltNewCfgTcpAck           INTEGER,
    fltNewCfgSrcMac           PhysAddress,
    fltNewCfgDstMac           PhysAddress,
    fltNewCfgFtpNatActive     INTEGER,
    fltNewCfgAclTcpUrg        INTEGER,
    fltNewCfgAclTcpAck        INTEGER,
    fltNewCfgAclTcpPsh        INTEGER,
    fltNewCfgAclTcpRst        INTEGER,
    fltNewCfgAclTcpSyn        INTEGER,
    fltNewCfgAclTcpFin        INTEGER,
    fltNewCfgAclIcmp          INTEGER,
    fltNewCfgAclIpOption      INTEGER,
    fltNewCfgBwmContract      Integer32,
    fltNewCfgAclIpTos	      INTEGER,
    fltNewCfgAclIpTosMask     INTEGER,
    fltNewCfgAclIpTosNew      INTEGER,
    fltNewCfgFwlb             INTEGER,
    fltNewCfgNatTimeout	      INTEGER,
    fltNewCfgLinklb           INTEGER,
    fltNewCfgWapRadiusSnoop   INTEGER,
    fltNewCfgIdslbHash        INTEGER,
    fltNewCfgVlan             INTEGER,
    fltNewCfgName             DisplayString,
    fltNewCfgTcpRateLimit     INTEGER,
    fltNewCfgTcpRateMaxConn   INTEGER,
    fltNewCfgHash             INTEGER,
    fltNewCfgLayer7DenyState  INTEGER,
    fltNewCfgLayer7DenyUrlBmap OCTET STRING,
    fltNewCfgLayer7DenyAddUrl Integer32,
    fltNewCfgLayer7DenyRemUrl Integer32,
    fltNewCfgGotoFilter       Integer32,
    fltNewCfgRadiusWapPersist INTEGER,
    fltNewCfgPbind            INTEGER,
    fltNewCfgTimeWindow       INTEGER,
    fltNewCfgHoldDuration     INTEGER,
    fltNewCfgProxyIp          IpAddress,
    fltNewCfgPatternMatch     INTEGER,
    fltNewCfgLayer7DenyMatchAll INTEGER,
    fltNewCfgLayer7ParseAll   INTEGER,
    fltNewCfgSecurityParseAll INTEGER,
    fltNewCfgPatternMatchGroupBmap OCTET STRING,
    fltNewCfgAddPatternMatchGroup  Integer32,
    fltNewCfgRemPatternMatchGroup Integer32,
    fltNewCfg8021pBitsValue   INTEGER,
    fltNewCfg8021pBitsMatch   INTEGER,
    fltNewCfgAclIpLength      INTEGER,
    fltNewCfgIdsGroup         Integer32,
    fltNewCfgEgressPip        INTEGER,
    fltNewCfgDbind            INTEGER,
    fltNewCfgReverse          INTEGER,
    fltNewCfgRevBwmContract   Integer32,
    fltNewCfgParseChn         INTEGER,
    fltNewCfgRtpBwmContract   Integer32,
    fltNewCfgSipParsing       INTEGER,
    fltNewCfgSessionMirror    INTEGER,
    fltNewCfgIpVer            INTEGER,
    fltNewCfgIpv6Sip          DisplayString,
    fltNewCfgIpv6Sprefix      INTEGER,
    fltNewCfgIpv6Dip          DisplayString,
    fltNewCfgIpv6Dprefix      INTEGER,
    fltNewCfgDelete           INTEGER
    }

fltNewCfgIndx OBJECT-TYPE
    SYNTAX  Integer32
    MAX-ACCESS  read-only
    STATUS  current
    DESCRIPTION
        "The filtering table index."
    ::= { fltNewCfgTableEntry 1 }

fltNewCfgSrcIp OBJECT-TYPE
    SYNTAX  IpAddress
    MAX-ACCESS  read-create
    STATUS  current
    DESCRIPTION
        "The source IP address to be filtered."
    ::= { fltNewCfgTableEntry 2 }

fltNewCfgSrcIpMask OBJECT-TYPE
    SYNTAX  IpAddress
    MAX-ACCESS  read-create
    STATUS  current
    DESCRIPTION
        "The source IP sub-net mask for filtering."
    ::= { fltNewCfgTableEntry 3 }

fltNewCfgDstIp OBJECT-TYPE
    SYNTAX  IpAddress
    MAX-ACCESS  read-create
    STATUS  current
    DESCRIPTION
        "The destination IP address to be filtered."
    ::= { fltNewCfgTableEntry 4 }

fltNewCfgDstIpMask OBJECT-TYPE
    SYNTAX  IpAddress
    MAX-ACCESS  read-create
    STATUS  current
    DESCRIPTION
        "The destination IP sub-net mask for filtering."
    ::= { fltNewCfgTableEntry 5 }

fltNewCfgProtocol OBJECT-TYPE
    SYNTAX  INTEGER (0..255)
    MAX-ACCESS  read-create
    STATUS  current
    DESCRIPTION
        "The protocol to be filtered."
    ::= { fltNewCfgTableEntry 6 }

fltNewCfgRangeHighSrcPort OBJECT-TYPE
    SYNTAX  INTEGER (0..65534)
    MAX-ACCESS  read-create
    STATUS  current
    DESCRIPTION
        "The higher source TCP/UDP port number to be filtered. It applies 
         only when protocol defined in fltNewCfgProtocol is UDP or TCP. 
         '0' means no filtering."
    ::= { fltNewCfgTableEntry 7 }

fltNewCfgRangeLowSrcPort OBJECT-TYPE
    SYNTAX  INTEGER (0..65534)
    MAX-ACCESS  read-create
    STATUS  current
    DESCRIPTION
        "The lower source TCP/UDP port number to be filtered. It applies 
         only when protocol defined in fltNewCfgProtocol is UDP or TCP. 
         '0' means no filtering."
    ::= { fltNewCfgTableEntry 8 }

fltNewCfgRangeLowDstPort OBJECT-TYPE
    SYNTAX  INTEGER (0..65534)
    MAX-ACCESS  read-create
    STATUS  current
    DESCRIPTION
        "The lower destination TCP/UDP port number to be filtered.
         It applies only when protocol defined in fltNewCfgProtocol
	 is UDP or TCP.  '0' means no filtering."
    ::= { fltNewCfgTableEntry 9 }

fltNewCfgRangeHighDstPort OBJECT-TYPE
    SYNTAX  INTEGER (0..65534)
    MAX-ACCESS  read-create
    STATUS  current
    DESCRIPTION
        "The higher destination TCP/UDP port number to be filtered.
         It applies only when protocol defined in fltNewCfgProtocol
         is UDP or TCP.  '0' means no filtering."
    ::= { fltNewCfgTableEntry 10 }

fltNewCfgAction OBJECT-TYPE
    SYNTAX  INTEGER {
        allow(1),
        deny(2),
        redirect(3),
        nat(4),      -- network address translation
        goto(5)
        }
    MAX-ACCESS  read-create
    STATUS  current
    DESCRIPTION
        "The action for the filtering rule."
    ::= { fltNewCfgTableEntry 11 }

fltNewCfgRedirPort OBJECT-TYPE
    SYNTAX  INTEGER (0..65534)
    MAX-ACCESS  read-create
    STATUS  current
    DESCRIPTION
        "The real server port number used for redirection."
    ::= { fltNewCfgTableEntry 12 }

fltNewCfgRedirGroup OBJECT-TYPE
    SYNTAX  Integer32
    MAX-ACCESS  read-create
    STATUS  current
    DESCRIPTION
        "The real server group to be redirected to."
    ::= { fltNewCfgTableEntry 13 }

fltNewCfgLog OBJECT-TYPE
    SYNTAX  INTEGER {
        enabled(1),
        disabled(2)
        }
    MAX-ACCESS  read-create
    STATUS  current
    DESCRIPTION
        "Enable or disable logging."
    ::= { fltNewCfgTableEntry 14 }

fltNewCfgState OBJECT-TYPE
    SYNTAX  INTEGER {
        enabled(1),
        disabled(2)
        }
    MAX-ACCESS  read-create
    STATUS  current
    DESCRIPTION
        "The state of this filtering rule."
    ::= { fltNewCfgTableEntry 15 }

fltNewCfgDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { fltNewCfgTableEntry 16 }

fltNewCfgNat OBJECT-TYPE
    SYNTAX  INTEGER {
        destination-address(1),
        source-address(2)
        }
    MAX-ACCESS  read-create
    STATUS  current
    DESCRIPTION
        "The selection of destination or source for network address 
         translation."
    ::= { fltNewCfgTableEntry 17 }

fltNewCfgCache OBJECT-TYPE
    SYNTAX  INTEGER {
        enabled(1),
        disabled(2)
        }
    MAX-ACCESS  read-create
    STATUS  current
    DESCRIPTION
        "Enable or disable caching sessions that match filter."
    ::= { fltNewCfgTableEntry 18 }

fltNewCfgInvert OBJECT-TYPE
    SYNTAX  INTEGER {
        enabled(1),
        disabled(2)
        }
    MAX-ACCESS  read-create
    STATUS  current
    DESCRIPTION
        "Turn the invert logic on or off for the filter entry."
    ::= { fltNewCfgTableEntry 19 }

fltNewCfgClientProxy OBJECT-TYPE
    SYNTAX  INTEGER {
        enabled(1),
        disabled(2)
        }
    MAX-ACCESS  read-create
    STATUS  current
    DESCRIPTION
        "Enable or disable client proxy."
    ::= { fltNewCfgTableEntry 20 }

fltNewCfgTcpAck OBJECT-TYPE
    SYNTAX  INTEGER {
        enabled(1),
        disabled(2)
        }
    MAX-ACCESS  read-create
    STATUS  current
    DESCRIPTION
        "Enable or disable filtering on matching TCP ACK and RST flag."
    ::= { fltNewCfgTableEntry 21 }


fltNewCfgSrcMac OBJECT-TYPE
    SYNTAX  PhysAddress 
    MAX-ACCESS  read-create
    STATUS  current
    DESCRIPTION
        "The source MAC address to be filtered."
    ::= { fltNewCfgTableEntry 23 }

fltNewCfgDstMac OBJECT-TYPE
    SYNTAX  PhysAddress 
    MAX-ACCESS  read-create
    STATUS  current
    DESCRIPTION
        "The Destination MAC address to be filtered."
    ::= { fltNewCfgTableEntry 24 }

fltNewCfgFtpNatActive OBJECT-TYPE
    SYNTAX  INTEGER {
        enabled(1),	
	disabled(2)
	}	
    MAX-ACCESS  read-create
    STATUS  current
    DESCRIPTION
        "Enable or disable FTP NAT for active ftp."
    ::= { fltNewCfgTableEntry 25 }	

-- New Config TCP Flag ACL Filtering Table

fltNewCfgAclTcpUrg OBJECT-TYPE
    SYNTAX  INTEGER {
	enable(1),
	disable(2)
	}	
    MAX-ACCESS  read-create
    STATUS  current
    DESCRIPTION
	"Enable or disable TCP URG packet."
    ::= { fltNewCfgTableEntry 26 }	

fltNewCfgAclTcpAck OBJECT-TYPE
    SYNTAX  INTEGER {
	enable(1),
	disable(2)
	}	
    MAX-ACCESS  read-create
    STATUS  current
    DESCRIPTION
        "Enable or disable TCP ACK packet."
    ::= { fltNewCfgTableEntry 27 }	

fltNewCfgAclTcpPsh OBJECT-TYPE
    SYNTAX  INTEGER {
	enable(1),
	disable(2)
	}	
    MAX-ACCESS  read-create
    STATUS  current
    DESCRIPTION
        "Enable or disable TCP PSH packet."
    ::= { fltNewCfgTableEntry 28 }	

fltNewCfgAclTcpRst OBJECT-TYPE
    SYNTAX  INTEGER {
	enable(1),
	disable(2)
	}	
    MAX-ACCESS  read-create
    STATUS  current
    DESCRIPTION
        "Enable or disable TCP RST packet."
    ::= { fltNewCfgTableEntry 29 }	

fltNewCfgAclTcpSyn OBJECT-TYPE
    SYNTAX  INTEGER {
	enable(1),
	disable(2)
	}	
    MAX-ACCESS  read-create
    STATUS  current
    DESCRIPTION
        "Enable or disable TCP SYN packet."
    ::= { fltNewCfgTableEntry 30 }	

fltNewCfgAclTcpFin OBJECT-TYPE
    SYNTAX  INTEGER {
	enable(1),
	disable(2)
	}	
    MAX-ACCESS  read-create
    STATUS  current
    DESCRIPTION
        "Enable or disable TCP FIN packet."
    ::= { fltNewCfgTableEntry 31 }	

-- New Config ICMP Type ACL Filtering Table

fltNewCfgAclIcmp OBJECT-TYPE
    SYNTAX  INTEGER (0..255) 
    MAX-ACCESS  read-create
    STATUS  current
    DESCRIPTION
        "ICMP type to be filtered. A ICMP type of 255 indicates 'any'"
    ::= { fltNewCfgTableEntry 32 }	

-- New Config IP Option ACL Filtering Table

fltNewCfgAclIpOption OBJECT-TYPE
    SYNTAX  INTEGER {
        enable(1),
        disable(2)
        }
    MAX-ACCESS  read-create
    STATUS  current
    DESCRIPTION
        "Enable or disable IP option matching."
    ::= { fltNewCfgTableEntry 33 }

fltNewCfgBwmContract OBJECT-TYPE
    SYNTAX  Integer32 
    MAX-ACCESS  read-create
    STATUS  current
    DESCRIPTION
        "Filt default BW contract number."
    ::= { fltNewCfgTableEntry 34 }	

fltNewCfgAclIpTos OBJECT-TYPE
    SYNTAX  INTEGER (0..255)
    MAX-ACCESS  read-create
    STATUS  current
    DESCRIPTION
        "The IP TOS value to be filtered."
    ::= { fltNewCfgTableEntry 35 }	

fltNewCfgAclIpTosMask OBJECT-TYPE
    SYNTAX  INTEGER (0..255)
    MAX-ACCESS  read-create
    STATUS  current
    DESCRIPTION
        "The IP TOS mask for filtering."
    ::= { fltNewCfgTableEntry 36 }	

fltNewCfgAclIpTosNew OBJECT-TYPE
    SYNTAX  INTEGER (0..255)
    MAX-ACCESS  read-create
    STATUS  current
    DESCRIPTION
        "The new IP TOS value to over-write when filtering fired."
    ::= { fltNewCfgTableEntry 37 }	

fltNewCfgFwlb OBJECT-TYPE
    SYNTAX  INTEGER {
        enabled(1),
        disabled(2)
        }
    MAX-ACCESS  read-create
    STATUS  current
    DESCRIPTION
        "Enable or disable filtering on firewall redirect hash method."
    ::= { fltNewCfgTableEntry 38 }

fltNewCfgNatTimeout OBJECT-TYPE
    SYNTAX  INTEGER (4..32768)
    MAX-ACCESS  read-create
    STATUS  current
    DESCRIPTION
	"The NAT session timeout. The timeout value should be an even
         number between 4 and 32768."
    ::= { fltNewCfgTableEntry 39 }	

fltNewCfgLinklb OBJECT-TYPE
    SYNTAX  INTEGER {
        enabled(1),
        disabled(2)
        }
    MAX-ACCESS  read-create
    STATUS  current
    DESCRIPTION
        "Enable or disable WAN link load balancing."
    ::= { fltNewCfgTableEntry 40 }

fltNewCfgWapRadiusSnoop OBJECT-TYPE
    SYNTAX  INTEGER {
        enabled(1),
        disabled(2)
        }
    MAX-ACCESS  read-create
    STATUS  current
    DESCRIPTION
        "Enable or disable WAP RADIUS snooping."
    ::= { fltNewCfgTableEntry 41 }

fltNewCfgSrcIpMac OBJECT-TYPE
    SYNTAX  INTEGER {
        ip(1),
        mac(2)
        }
    MAX-ACCESS  read-create
    STATUS  current
    DESCRIPTION
        "Set a flag indicating whether filtering should be based on the 
         source IP address or the source MAC address field."
    ::= { fltNewCfgTableEntry 42 }

fltNewCfgDstIpMac OBJECT-TYPE
    SYNTAX  INTEGER {
        ip(1),
        mac(2)
        }
    MAX-ACCESS  read-create
    STATUS  current
    DESCRIPTION
        "Set a flag indicating whether filtering should be based on the 
         destination IP address or the destination MAC address field."
    ::= { fltNewCfgTableEntry 43 }

fltNewCfgIdslbHash OBJECT-TYPE
    SYNTAX  INTEGER {
        sip(1),
        dip(2),
        both(3)
        }
    MAX-ACCESS  read-create
    STATUS  current
    DESCRIPTION
        "Set hash parameter for intrusion detection server load balancing."
    ::= { fltNewCfgTableEntry 44 }

fltNewCfgVlan OBJECT-TYPE
    SYNTAX  INTEGER (0..4090)
    MAX-ACCESS  read-create
    STATUS  current
    DESCRIPTION
        "Set the VLAN assoicated with the filter."
    ::= { fltNewCfgTableEntry 45 }

fltNewCfgName OBJECT-TYPE
    SYNTAX DisplayString (SIZE(0..31))
    MAX-ACCESS read-create
    STATUS current
    DESCRIPTION
        "The name of the filter."
    ::= { fltNewCfgTableEntry 46 }

fltNewCfgTcpRateLimit OBJECT-TYPE
    SYNTAX  INTEGER {
        enabled(1),
        disabled(2)
        }
    MAX-ACCESS  read-create
    STATUS  current
    DESCRIPTION
        "Enable or disable protocol rate limiting."
    ::= { fltNewCfgTableEntry 47 }

fltNewCfgTcpRateMaxConn OBJECT-TYPE
    SYNTAX  INTEGER (0..255)
    MAX-ACCESS  read-create
    STATUS  current
    DESCRIPTION
        "Set maximum connections (number of connections in units of 10)
         for TCP connection rate limiting. In the case of ICMP and UDP,
	 this is the maximum packets (number of packets in units of 10)."
    ::= { fltNewCfgTableEntry 48 }

fltNewCfgHash OBJECT-TYPE
    SYNTAX  INTEGER {
	auto(1),
        sip(2),
        dip(3),
        both(4),
	sipsport(5)
        }
    MAX-ACCESS  read-create
    STATUS  current
    DESCRIPTION
        "Set hash parameter for the filter."
    ::= { fltNewCfgTableEntry 49 }


fltNewCfgLayer7DenyState OBJECT-TYPE
    SYNTAX  INTEGER {
        enabled(1),
        disabled(2)
        }
    MAX-ACCESS  read-create
    STATUS  current
    DESCRIPTION
        "Enable or disable layer 7 deny filtering."
    ::= { fltNewCfgTableEntry 51 }

fltNewCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgTableEntry 52 }

fltNewCfgLayer7DenyAddUrl OBJECT-TYPE
    SYNTAX  Integer32
    MAX-ACCESS  read-create
    STATUS  current
    DESCRIPTION
        "The URL Path (slbCurCfgUrlLbPathIndex) to be added to the 
         Layer 7 deny filter. A zero is returned when read."
    ::= { fltNewCfgTableEntry 53 }

fltNewCfgLayer7DenyRemUrl OBJECT-TYPE
    SYNTAX  Integer32
    MAX-ACCESS  read-create
    STATUS  current
    DESCRIPTION
        "The URL Path (slbCurCfgUrlLbPathIndex) to be removed from 
         the Layer 7 deny filter. A zero is returned when read."
    ::= { fltNewCfgTableEntry 54 }

fltNewCfgGotoFilter OBJECT-TYPE
    SYNTAX  Integer32
    MAX-ACCESS  read-create
    STATUS  current	
    DESCRIPTION
        "The filter ID for GOTO action in the new config."
    ::= { fltNewCfgTableEntry 55 }

fltNewCfgRadiusWapPersist OBJECT-TYPE
    SYNTAX  INTEGER {
        enabled(1),
        disabled(2)
        }
    MAX-ACCESS  read-create
    STATUS  current	
    DESCRIPTION
        "Enable or disable Radius/WAP persistence."
    ::= { fltNewCfgTableEntry 56 }

fltNewCfgPbind OBJECT-TYPE
    SYNTAX  INTEGER {
        enabled(1),
        disabled(2)
        }
    MAX-ACCESS  read-create
    STATUS  current	
    DESCRIPTION
        "Enable or disable filter persistent binding."
    ::= { fltNewCfgTableEntry 57 }

fltNewCfgTimeWindow OBJECT-TYPE
    SYNTAX  INTEGER (1..65535)
    MAX-ACCESS  read-create
    STATUS  current
    DESCRIPTION
        "The time window for protocol rate limiting (in seconds)."
    ::= { fltNewCfgTableEntry 58 }

fltNewCfgHoldDuration OBJECT-TYPE
    SYNTAX  INTEGER (2..65535)
    MAX-ACCESS  read-create
    STATUS  current
    DESCRIPTION
        "The hold down duration for protocol rate limiting (in minutes)."
    ::= { fltNewCfgTableEntry 59 }

fltNewCfgPatternMatch OBJECT-TYPE
    SYNTAX  INTEGER {
        enabled(1),
        disabled(2)
        }
    MAX-ACCESS  read-create
    STATUS  current	
    DESCRIPTION
        "Enable or disable binary pattern matching."
    ::= { fltNewCfgTableEntry 60 }

fltNewCfgLayer7DenyMatchAll OBJECT-TYPE
    SYNTAX  INTEGER {
        enabled(1),
        disabled(2)
        }
    MAX-ACCESS  read-create
    STATUS  current
    DESCRIPTION
        "Enable or disable match-all criteria for L7 deny string matching."
    ::= { fltNewCfgTableEntry 61 }

fltNewCfgProxyIp OBJECT-TYPE
    SYNTAX  IpAddress
    MAX-ACCESS  read-create
    STATUS  current
    DESCRIPTION
        "The client proxy IP address for NAT and REDIR filter."
        
    ::= { fltNewCfgTableEntry 62 }

fltNewCfgLayer7ParseAll OBJECT-TYPE
    SYNTAX  INTEGER {
        enabled(1),
        disabled(2)
        }
    MAX-ACCESS  read-create
    STATUS  current
    DESCRIPTION
        "Enable or disable layer 7 lookup (parsing) of all packets."
    ::= { fltNewCfgTableEntry 63 }

fltNewCfgSecurityParseAll OBJECT-TYPE
    SYNTAX  INTEGER {
        enabled(1),
        disabled(2)
        }
    MAX-ACCESS  read-create
    STATUS  current
    DESCRIPTION
        "Enable or disable pattern string lookup (parsing) of all packets."
    ::= { fltNewCfgTableEntry 64 }

fltNewCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltNewCfgTableEntry 65 }
    
fltNewCfgAddPatternMatchGroup OBJECT-TYPE
    SYNTAX  Integer32
    MAX-ACCESS  read-create
    STATUS  current
    DESCRIPTION
        "The pattern match group to be added to the 
         security filter. A zero is returned when read."
    ::= { fltNewCfgTableEntry 66 }

fltNewCfgRemPatternMatchGroup OBJECT-TYPE
    SYNTAX  Integer32
    MAX-ACCESS  read-create
    STATUS  current
    DESCRIPTION
        "The pattern match group to be to be removed from 
         the security filter. A zero is returned when read."
    ::= { fltNewCfgTableEntry 67 }

fltNewCfg8021pBitsValue OBJECT-TYPE
    SYNTAX  INTEGER (0..7)
    MAX-ACCESS  read-create
    STATUS  current
    DESCRIPTION
        "The 802.1p bits value to match."
    ::= { fltNewCfgTableEntry 68 }

fltNewCfg8021pBitsMatch OBJECT-TYPE
    SYNTAX  INTEGER {
        enabled(1),
        disabled(2)
        }
    MAX-ACCESS  read-create
    STATUS  current
    DESCRIPTION
        "Enable or disable matching on 802.1p bits in the packets."
    ::= { fltNewCfgTableEntry 69 }
 
fltNewCfgAclIpLength OBJECT-TYPE
    SYNTAX  INTEGER (0..65535)
    MAX-ACCESS  read-create
    STATUS  current 
    DESCRIPTION
        "Set the IP maximum packet length in bytes. A value can be either 0 
         which indicates 'any' length or between 64 and 65535."
    ::= { fltNewCfgTableEntry 70 }	

fltNewCfgIdsGroup OBJECT-TYPE
    SYNTAX  Integer32
    MAX-ACCESS  read-create
    STATUS  current
    DESCRIPTION
        "The real server group for IDS load balancing. A value of 0 indicates
	 'none'." 
    ::= { fltNewCfgTableEntry 71 }
    
fltNewCfgEgressPip OBJECT-TYPE
    SYNTAX  INTEGER {
        enabled(1),
        disabled(2)
        }
    MAX-ACCESS  read-create
    STATUS  current
    DESCRIPTION
        "Enable or disable pip selection based on egress port/vlan."
    ::= { fltNewCfgTableEntry 72 }
    
fltNewCfgDbind OBJECT-TYPE
    SYNTAX  INTEGER {
        enabled(1),
        disabled(2)
        }
    MAX-ACCESS  read-create
    STATUS  current	
    DESCRIPTION
        "Enable or disable filter delayed binding."
    ::= { fltNewCfgTableEntry 73 }

fltNewCfgRevBwmContract OBJECT-TYPE
    SYNTAX  Integer32
    MAX-ACCESS  read-create
    STATUS  current
    DESCRIPTION
	"Filt reverse session BWM contract number."
    ::= { fltNewCfgTableEntry 74 }	

fltNewCfgReverse OBJECT-TYPE
    SYNTAX  INTEGER {
        enabled(1),
        disabled(2)
        }
    MAX-ACCESS  read-create
    STATUS  current	
    DESCRIPTION
        "Enable or disable creating session for reverse side traffic."
    ::= { fltNewCfgTableEntry 75 }

fltNewCfgParseChn OBJECT-TYPE
    SYNTAX  INTEGER {
	enabled(1),
	disabled(2)
	}
    MAX-ACCESS  read-create
    STATUS  current 
    DESCRIPTION
        "Enable or disable chained pgroup match criteria for l7 filtering."	 
    ::= { fltNewCfgTableEntry 76}


fltNewCfgRtpBwmContract OBJECT-TYPE
    SYNTAX  Integer32
    MAX-ACCESS  read-create
    STATUS  current
    DESCRIPTION
        "BWM contract for SIP RTP traffic."
    ::= { fltNewCfgTableEntry 77 }

fltNewCfgSipParsing OBJECT-TYPE
    SYNTAX  INTEGER {
        enabled(1),
        disabled(2)
        }
    MAX-ACCESS  read-create
    STATUS  current
    DESCRIPTION
        "Enable or disable SIP NAT."
    ::= { fltNewCfgTableEntry 78 }


    fltNewCfgSessionMirror  OBJECT-TYPE
    SYNTAX  INTEGER {
        enabled(1),
        disabled(2)
        }
    MAX-ACCESS  read-create
    STATUS  current
    DESCRIPTION
        "Enable or disable session mirroring."
    ::= { fltNewCfgTableEntry 79 }


fltNewCfgIpVer OBJECT-TYPE
    SYNTAX  INTEGER{
        ipv4(1),
        ipv6(2)
        }
    MAX-ACCESS  read-create
    STATUS  current
    DESCRIPTION
        "The type of IP address."
    ::= { fltNewCfgTableEntry 80 }

fltNewCfgIpv6Sip  OBJECT-TYPE
    SYNTAX   DisplayString (SIZE(0..40))
    MAX-ACCESS  read-create
    STATUS  current
    DESCRIPTION
        "The source IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 81 }

fltNewCfgIpv6Sprefix   OBJECT-TYPE
    SYNTAX   INTEGER(0..128) 
    MAX-ACCESS  read-create
    STATUS  current
    DESCRIPTION
        "The prefix length associated with source IP address ."
    ::= { fltNewCfgTableEntry 82 }

fltNewCfgIpv6Dip   OBJECT-TYPE
    SYNTAX   DisplayString (SIZE(0..40))
    MAX-ACCESS  read-create
    STATUS  current
    DESCRIPTION
        "The destination  IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 83 }

fltNewCfgIpv6Dprefix   OBJECT-TYPE
    SYNTAX  INTEGER(0..128) 
    MAX-ACCESS  read-create
    STATUS  current
    DESCRIPTION
        "The prefix length associated with destination IP address ."
    ::= { fltNewCfgTableEntry 84 }


-- Filtering Port Table

fltCurCfgPortTable OBJECT-TYPE
    SYNTAX  SEQUENCE OF FltCurCfgPortTableEntry
    MAX-ACCESS  not-accessible
    STATUS  current
    DESCRIPTION
        "The filtering port table in the current configuration block."
    ::= { filterCfg 4 }

fltCurCfgPortTableEntry OBJECT-TYPE
    SYNTAX  FltCurCfgPortTableEntry
    MAX-ACCESS  not-accessible
    STATUS  current
    DESCRIPTION
        "A row in the filtering port table."
    INDEX   { fltCurCfgPortIndx }
    ::= { fltCurCfgPortTable 1 }

FltCurCfgPortTableEntry ::= SEQUENCE {
    fltCurCfgPortIndx         Integer32,
    fltCurCfgPortState        INTEGER,
    fltCurCfgPortFiltBmap     OCTET STRING
    }

fltCurCfgPortIndx OBJECT-TYPE
    SYNTAX  Integer32
    MAX-ACCESS  read-only
    STATUS  current
    DESCRIPTION
        "The port index."
    ::= { fltCurCfgPortTableEntry 1 }

fltCurCfgPortState OBJECT-TYPE
    SYNTAX  INTEGER {
        enabled(1),
        disabled(2)
        }
    MAX-ACCESS  read-only
    STATUS  current
    DESCRIPTION
        "Enable or disable filtering."
    ::= { fltCurCfgPortTableEntry 2 }

fltCurCfgPortFiltBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { fltCurCfgPortTableEntry 3 }

fltNewCfgPortTable OBJECT-TYPE
    SYNTAX  SEQUENCE OF FltNewCfgPortTableEntry
    MAX-ACCESS  not-accessible
    STATUS  current
    DESCRIPTION
        "The filtering port table in the new configuration block."
    ::= { filterCfg 5 }

fltNewCfgPortTableEntry OBJECT-TYPE
    SYNTAX  FltNewCfgPortTableEntry
    MAX-ACCESS  not-accessible
    STATUS  current
    DESCRIPTION
        "A row in the filtering port table."
    INDEX   { fltNewCfgPortIndx }
    ::= { fltNewCfgPortTable 1 }

FltNewCfgPortTableEntry ::= SEQUENCE {
    fltNewCfgPortIndx         Integer32,
    fltNewCfgPortState        INTEGER,
    fltNewCfgPortFiltBmap     OCTET STRING,
    fltNewCfgPortAddFiltRule  Integer32,
    fltNewCfgPortRemFiltRule  Integer32
    }

fltNewCfgPortIndx OBJECT-TYPE
    SYNTAX  Integer32
    MAX-ACCESS  read-only
    STATUS  current
    DESCRIPTION
        "The port index."
    ::= { fltNewCfgPortTableEntry 1 }

fltNewCfgPortState OBJECT-TYPE
    SYNTAX  INTEGER {
        enabled(1),
        disabled(2)
        }
    MAX-ACCESS  read-create
    STATUS  current
    DESCRIPTION
        "Enable or disable filtering."
    ::= { fltNewCfgPortTableEntry 2 }

fltNewCfgPortFiltBmap OBJECT-TYPE
    SYNTAX  OCTET STRING (SIZE(0..256))
    MAX-ACCESS  read-create
    STATUS  current
    DESCRIPTION
        "The filtering rules applied to the port.  The filtering rules
         are presented in bitmap format.

         in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltNewCfgTable)

         where x : 1 - The represented filter rule applied to the port
		   0 - The represented filter rule not applied to the port "
    ::= { fltNewCfgPortTableEntry 3 }

fltNewCfgPortAddFiltRule OBJECT-TYPE
    SYNTAX  Integer32
    MAX-ACCESS  read-create
    STATUS  current
    DESCRIPTION
        "This is an action object to add filtering rule to a port. The value 
         specified with this object is the index to the fltNewCfgTable for 
         which filtering rule to be added to the port. The range of the 
         valid index is between 1 and fltCurCfgTableMaxSize. When read, the 
         value '0' is returned always."
    ::= { fltNewCfgPortTableEntry 4 }

fltNewCfgPortRemFiltRule OBJECT-TYPE
    SYNTAX  Integer32
    MAX-ACCESS  read-create
    STATUS  current
    DESCRIPTION
        "This is an action object to remove filtering rule from a port.	The 
         value specified with this object is the index to the fltNewCfgTable 
         for which filtering rule to be removed from the port. The range of 
         the valid index is between 1 and fltCurCfgTableMaxSize.  When read, 
         the value '0' is returned always."
    ::= { fltNewCfgPortTableEntry 5 }

-- URL based BWM filtering table
fltUrlBwmTableMaxSize OBJECT-TYPE
    SYNTAX Integer32
    MAX-ACCESS read-only
    STATUS current
    DESCRIPTION
        "The maximum number of URL based BWM entries."
    ::= { filterCfg 6 }

fltCurCfgUrlBwmTable OBJECT-TYPE
    SYNTAX  SEQUENCE OF FltCurCfgUrlBwmEntry
    MAX-ACCESS  not-accessible
    STATUS  current
    DESCRIPTION
        "The table of URL based BWM for filtering."
    ::= { filterCfg 7 }

fltCurCfgUrlBwmEntry OBJECT-TYPE
    SYNTAX  FltCurCfgUrlBwmEntry
    MAX-ACCESS  not-accessible
    STATUS  current
    DESCRIPTION
        "A row in the URL based BWM filtering table."
    INDEX   { fltCurCfgUrlBwmFltIndex, fltCurCfgUrlBwmUrlId }
    ::= { fltCurCfgUrlBwmTable 1 }

FltCurCfgUrlBwmEntry ::= SEQUENCE {
    fltCurCfgUrlBwmFltIndex        Integer32,
    fltCurCfgUrlBwmUrlId           Integer32,
    fltCurCfgUrlReverseBwmContract Integer32,
    fltCurCfgUrlBwmContract        Integer32  
    }

fltCurCfgUrlBwmFltIndex OBJECT-TYPE
    SYNTAX  Integer32
    MAX-ACCESS  read-only
    STATUS  current
    DESCRIPTION
        "The number of the filter." 
    ::= { fltCurCfgUrlBwmEntry 1 }

fltCurCfgUrlBwmUrlId OBJECT-TYPE  
    SYNTAX  Integer32  
    MAX-ACCESS  read-only  
    STATUS  current  
    DESCRIPTION 
        "The URL Path Identifier."  
    ::= { fltCurCfgUrlBwmEntry 2 } 

fltCurCfgUrlBwmContract OBJECT-TYPE  
    SYNTAX  Integer32  
    MAX-ACCESS  read-only  
    STATUS  current  
    DESCRIPTION 
        "The BW contract."  
    ::= { fltCurCfgUrlBwmEntry 3 } 

fltCurCfgUrlReverseBwmContract OBJECT-TYPE  
    SYNTAX  Integer32  
    MAX-ACCESS  read-only  
    STATUS  current  
    DESCRIPTION 
        "The BWM contract for reverse traffic."  
    ::= { fltCurCfgUrlBwmEntry 4 } 

fltNewCfgUrlBwmTable OBJECT-TYPE
    SYNTAX  SEQUENCE OF FltNewCfgUrlBwmEntry
    MAX-ACCESS  not-accessible
    STATUS  current
    DESCRIPTION
        "The table of URL based BWM for filtering."
    ::= { filterCfg 8 }

fltNewCfgUrlBwmEntry OBJECT-TYPE
    SYNTAX  FltNewCfgUrlBwmEntry
    MAX-ACCESS  not-accessible
    STATUS  current
    DESCRIPTION
        "A row in the URL based BWM filtering table."
    INDEX   { fltNewCfgUrlBwmFltIndex, fltNewCfgUrlBwmUrlId }
    ::= { fltNewCfgUrlBwmTable 1 }

FltNewCfgUrlBwmEntry ::= SEQUENCE {
    fltNewCfgUrlBwmFltIndex        Integer32,
    fltNewCfgUrlBwmUrlId           Integer32,
    fltNewCfgUrlBwmContract        Integer32,
    fltNewCfgUrlReverseBwmContract Integer32,
    fltNewCfgUrlBwmDelete          INTEGER
    }

fltNewCfgUrlBwmFltIndex OBJECT-TYPE
    SYNTAX  Integer32
    MAX-ACCESS  read-only
    STATUS  current
    DESCRIPTION
        "The number of the filter." 
    ::= { fltNewCfgUrlBwmEntry 1 }

fltNewCfgUrlBwmUrlId OBJECT-TYPE  
    SYNTAX  Integer32  
    MAX-ACCESS  read-only  
    STATUS  current  
    DESCRIPTION 
        "The URL Path Identifier."  
    ::= { fltNewCfgUrlBwmEntry 2 } 

fltNewCfgUrlBwmContract OBJECT-TYPE  
    SYNTAX  Integer32  
    MAX-ACCESS  read-create  
    STATUS  current  
    DESCRIPTION 
        "The BW traffic contract."  
    ::= { fltNewCfgUrlBwmEntry 3 } 

fltNewCfgUrlBwmDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { fltNewCfgUrlBwmEntry 4 }

fltNewCfgUrlReverseBwmContract OBJECT-TYPE  
    SYNTAX  Integer32  
    MAX-ACCESS  read-create  
    STATUS  current  
    DESCRIPTION 
        "The BWM contract for reverse traffic."  
    ::= { fltNewCfgUrlBwmEntry 5 }

-- Filter HTTP Redirection Mapping Table

fltCfgHttpRedirMappingTableMaxSize OBJECT-TYPE
    SYNTAX  Integer32 
    MAX-ACCESS  read-only 
    STATUS  current 
    DESCRIPTION 
        "The maximum number of entries in HttpRedirMappingTable." 
    ::= { filterCfg 9 }

fltCurCfgHttpRedirMappingTable OBJECT-TYPE
    SYNTAX  SEQUENCE OF FltCurCfgHttpRedirMappingEntry
    MAX-ACCESS  not-accessible
    STATUS  current
    DESCRIPTION
        "The table of HTTP redirection mapping table."
    ::= { filterCfg 10 }

fltCurCfgHttpRedirMappingEntry OBJECT-TYPE
    SYNTAX  FltCurCfgHttpRedirMappingEntry
    MAX-ACCESS  not-accessible
    STATUS  current
    DESCRIPTION
        "A row in the HTTP redirect mapping table."
    INDEX   { fltCurCfgHttpRedirMappingFilter, 
              fltCurCfgHttpRedirMappingFromStr }
    ::= { fltCurCfgHttpRedirMappingTable 1 }

FltCurCfgHttpRedirMappingEntry ::= SEQUENCE {
    fltCurCfgHttpRedirMappingFilter   Integer32,
    fltCurCfgHttpRedirMappingFromStr  INTEGER,
    fltCurCfgHttpRedirMappingToStr    INTEGER
    }

fltCurCfgHttpRedirMappingFilter OBJECT-TYPE
    SYNTAX  Integer32
    MAX-ACCESS  read-only
    STATUS  current
    DESCRIPTION
        "The filter number."
    ::= { fltCurCfgHttpRedirMappingEntry 1 }

fltCurCfgHttpRedirMappingFromStr OBJECT-TYPE 
    SYNTAX  INTEGER (1..1024)
    MAX-ACCESS  read-only 
    STATUS  current 
    DESCRIPTION 
        "This index is the string ID of Layer7 string table. 
         If HTTP request matches this string, then switch issues 
         a HTTP REDIRECT to client with the 
         fltCurCfgHttpRedirMappingToStr string." 
    ::= { fltCurCfgHttpRedirMappingEntry 2 }

fltCurCfgHttpRedirMappingToStr OBJECT-TYPE  
    SYNTAX  INTEGER (2..1024)
    MAX-ACCESS  read-only  
    STATUS  current  
    DESCRIPTION 
        "The string ID of Layer7 string table. The switch sends 
         HTTP Redirect back to client with this string when HTTP
         request matches the fltCurCfgHttpRedirMappingFromStr string"
    ::= { fltCurCfgHttpRedirMappingEntry 3 } 

fltNewCfgHttpRedirMappingTable OBJECT-TYPE
    SYNTAX  SEQUENCE OF FltNewCfgHttpRedirMappingEntry
    MAX-ACCESS  not-accessible
    STATUS  current
    DESCRIPTION
        "The table of HTTP redirection mapping table."
    ::= { filterCfg 11 }

fltNewCfgHttpRedirMappingEntry OBJECT-TYPE
    SYNTAX  FltNewCfgHttpRedirMappingEntry
    MAX-ACCESS  not-accessible
    STATUS  current
    DESCRIPTION
        "A row in the HTTP redirect mapping table."
    INDEX   { fltNewCfgHttpRedirMappingFilter, 
              fltNewCfgHttpRedirMappingFromStr }
    ::= { fltNewCfgHttpRedirMappingTable 1 }

FltNewCfgHttpRedirMappingEntry ::= SEQUENCE {
    fltNewCfgHttpRedirMappingFilter    Integer32,
    fltNewCfgHttpRedirMappingFromStr   INTEGER,
    fltNewCfgHttpRedirMappingToStr     INTEGER,
    fltNewCfgHttpRedirMappingDelete    INTEGER
    }

fltNewCfgHttpRedirMappingFilter OBJECT-TYPE
    SYNTAX  Integer32
    MAX-ACCESS  read-only
    STATUS  current
    DESCRIPTION
        "The filter number."
    ::= { fltNewCfgHttpRedirMappingEntry 1 }

fltNewCfgHttpRedirMappingFromStr OBJECT-TYPE  
    SYNTAX  INTEGER (1..1024)
    MAX-ACCESS  read-only  
    STATUS  current  
    DESCRIPTION 
        "The string ID of Layer7 string table. If HTTP request 
         matches this string then switch issues a HTTP REDIRECT 
         to client with the fltNewCfgHttpRedirMappingToStr string."  
    ::= { fltNewCfgHttpRedirMappingEntry 2 } 

fltNewCfgHttpRedirMappingToStr OBJECT-TYPE  
    SYNTAX  INTEGER (2..1024)
    MAX-ACCESS  read-create  
    STATUS  current  
    DESCRIPTION 
        "The string ID of Layer7 string table. The switch sends 
         HTTP Redirect back to client with this string when the
         HTTP request matches fltNewCfgHttpRedirMappingFromStr 
         string."
    ::= { fltNewCfgHttpRedirMappingEntry 4 } 

fltNewCfgHttpRedirMappingDelete OBJECT-TYPE
    SYNTAX  INTEGER {
        other(1),
        delete(2)
        }
    MAX-ACCESS  read-create
    STATUS  current
    DESCRIPTION
        "By setting the value to delete(2), the entire row is deleted."
    ::= { fltNewCfgHttpRedirMappingEntry 6 }

-- Global SLB General Configuration

gslbCurCfgGenState OBJECT-TYPE
    SYNTAX  INTEGER {
        on(1),
        off(2)
        }
     MAX-ACCESS  read-only
     STATUS  current
     DESCRIPTION
         "Turn on or off Distributed Server Load Balance."
    ::= { gslbGeneralCfg 1 }

gslbNewCfgGenState OBJECT-TYPE
    SYNTAX  INTEGER {
        on(1),
        off(2)
        }
    MAX-ACCESS  read-write
    STATUS  current
    DESCRIPTION
        "Turn on or off Distributed Server Load Balance."
    ::= { gslbGeneralCfg 2 }


gslbCurCfgGenHttpRedirect OBJECT-TYPE
    SYNTAX  INTEGER {
        enabled(1),
        disabled(2)
        }
    MAX-ACCESS  read-only
    STATUS  current
    DESCRIPTION
        "Enable/Disable HTTP redirect based GSLB in
         the current_configuration block."
    ::= { gslbGeneralCfg 7 }

gslbNewCfgGenHttpRedirect OBJECT-TYPE
    SYNTAX  INTEGER {
        enabled(1),
        disabled(2)
        }
    MAX-ACCESS  read-write
    STATUS  current
    DESCRIPTION
        "Enable/Disable HTTP redirect based GSLB in
         the new_configuration block."
    ::= { gslbGeneralCfg 8 }


gslbCurCfgGenMinco OBJECT-TYPE
    SYNTAX  INTEGER (0..65535)
    MAX-ACCESS  read-only
    STATUS  current
    DESCRIPTION
        "Minmum number of site connections in the current_configuration block."
    ::= { gslbGeneralCfg 13 }

gslbNewCfgGenMinco OBJECT-TYPE
    SYNTAX  INTEGER (0..65535)
    MAX-ACCESS  read-write
    STATUS  current
    DESCRIPTION
        "Minmum number of site connections in the new_configuration block."
    ::= { gslbGeneralCfg 14 }


gslbCurCfgGenUsern OBJECT-TYPE
    SYNTAX  INTEGER {
        enabled(1),
        disabled(2)
        }
    MAX-ACCESS  read-only
    STATUS  current
    DESCRIPTION
        "Enable/Disable HTTP redirect to real server name."
    ::= { gslbGeneralCfg 17 }

gslbNewCfgGenUsern OBJECT-TYPE
    SYNTAX  INTEGER {
        enabled(1),
        disabled(2)
        }
    MAX-ACCESS  read-write
    STATUS  current
    DESCRIPTION
        "Enable/Disable HTTP redirect to real server name."
    ::= { gslbGeneralCfg 18 }


gslbCurCfgGenNoremote OBJECT-TYPE
    SYNTAX INTEGER {
        enabled(1),
        disabled(2)
        }
    MAX-ACCESS read-only
    STATUS current
    DESCRIPTION
        "Enable/Disable no remote real SLB. Enabling will prevent the 
         switch from load balancing incoming traffic to remote reals in
         the event that all local reals are down."
    ::= { gslbGeneralCfg 25 }

gslbNewCfgGenNoremote OBJECT-TYPE
    SYNTAX INTEGER {
        enabled(1),
        disabled(2)
        }
    MAX-ACCESS read-write
    STATUS current
    DESCRIPTION
        "Enable/Disable no remote real SLB. Enabling will prevent the 
         switch from load balancing incoming traffic to remote reals in 
         the event that all local reals are down."
    ::= { gslbGeneralCfg 26 }

gslbCurCfgGenEncrypt OBJECT-TYPE
    SYNTAX INTEGER {
        enabled(1),
        disabled(2)
        }
    MAX-ACCESS read-only
    STATUS current
    DESCRIPTION
        "Enable/Disable encrypting remote site update."
    ::= { gslbGeneralCfg 27 }

gslbNewCfgGenEncrypt OBJECT-TYPE
    SYNTAX INTEGER {
        enabled(1),
        disabled(2)
        }
    MAX-ACCESS read-write
    STATUS current
    DESCRIPTION
        "Enable/Disable encrypting remote site update."
    ::= { gslbGeneralCfg 28 }

gslbCurCfgGenRemSiteUpdatePort OBJECT-TYPE
    SYNTAX  INTEGER (1..65535)
    MAX-ACCESS  read-only
    STATUS  current
    DESCRIPTION
        "TCP port number for remote site updates in
         the current configuration block."
    ::= { gslbGeneralCfg 29 }

gslbNewCfgGenRemSiteUpdatePort OBJECT-TYPE
    SYNTAX  INTEGER (1..65535)
    MAX-ACCESS  read-write
    STATUS  current
    DESCRIPTION
        "TCP port number for remote site updates in
         the new configuration block."
    ::= { gslbGeneralCfg 30 }

gslbCurCfgGenSessUtilCap OBJECT-TYPE
    SYNTAX  INTEGER (1..100)
    MAX-ACCESS  read-only
    STATUS  current
    DESCRIPTION
        "Session utilization capacity threshold in
         the current configuration block."
    ::= { gslbGeneralCfg 31 }

gslbNewCfgGenSessUtilCap OBJECT-TYPE
    SYNTAX  INTEGER (1..100)
    MAX-ACCESS  read-write
    STATUS  current
    DESCRIPTION
        "Session utilization capacity threshold in
         the new configuration block."
    ::= { gslbGeneralCfg 32 }

gslbCurCfgGenCpuUtilCap OBJECT-TYPE
    SYNTAX  INTEGER (1..100)
    MAX-ACCESS  read-only
    STATUS  current
    DESCRIPTION
        "CPU utilization capacity threshold in
         the current configuration block."
    ::= { gslbGeneralCfg 33 }

gslbNewCfgGenCpuUtilCap OBJECT-TYPE
    SYNTAX  INTEGER (1..100)
    MAX-ACCESS  read-write
    STATUS  current
    DESCRIPTION
        "CPU utilization capacity threshold in
         the new configuration block."
    ::= { gslbGeneralCfg 34 }

gslbCurCfgGenSourceIpNetmask OBJECT-TYPE
    SYNTAX IpAddress
    MAX-ACCESS  read-only
    STATUS  current
    DESCRIPTION
        "Source IP netmask for DNS persistence cache in
         the current configuration block."
    ::= { gslbGeneralCfg 35 }

gslbNewCfgGenSourceIpNetmask OBJECT-TYPE
    SYNTAX IpAddress
    MAX-ACCESS  read-write
    STATUS  current
    DESCRIPTION
        "Source IP netmask for DNS persistence cache in
         the new configuration block."
    ::= { gslbGeneralCfg 36 }

gslbCurCfgGenTimeout OBJECT-TYPE
    SYNTAX  INTEGER (1..1440)
    MAX-ACCESS  read-only
    STATUS  current
    DESCRIPTION
        "Timeout in minutes for DNS persistence cache in
         the current configuration block."
    ::= { gslbGeneralCfg 37 }

gslbNewCfgGenTimeout OBJECT-TYPE
    SYNTAX  INTEGER (1..1440)
    MAX-ACCESS  read-write
    STATUS  current
    DESCRIPTION
        "Timeout in minutes for DNS persistence cache in
         the new configuration block."
    ::= { gslbGeneralCfg 38 }

gslbCurCfgGenDnsDirect OBJECT-TYPE
    SYNTAX  INTEGER {
        enabled(1),
        disabled(2)
        }
    MAX-ACCESS  read-only
    STATUS  current
    DESCRIPTION
        "Enable/Disable authoritative DNS direct based Global SLB in
        the current configuration block."
    ::= { gslbGeneralCfg 39 }

gslbNewCfgGenDnsDirect OBJECT-TYPE
    SYNTAX  INTEGER {
        enabled(1),
        disabled(2)
        }
    MAX-ACCESS  read-write
    STATUS  current
    DESCRIPTION
        "Enable/Disable authoritative DNS direct based Global SLB in
        the new configuration block."
    ::= { gslbGeneralCfg 40 }

gslbCurCfgGenRemSiteUpdateVersion OBJECT-TYPE
    SYNTAX  INTEGER (1..2)
    MAX-ACCESS  read-only
    STATUS  current
    DESCRIPTION
        "DSSP version 1 or 2 to send out remote site updates in
        the current configuration block."
    ::= { gslbGeneralCfg 41 }

gslbNewCfgGenRemSiteUpdateVersion OBJECT-TYPE
    SYNTAX  INTEGER (1..2)
    MAX-ACCESS  read-write
    STATUS  current
    DESCRIPTION
        "DSSP version 1 or 2 to send out remote site updates in
        the new configuration block."
    ::= { gslbGeneralCfg 42 }

gslbCurCfgGenHostname OBJECT-TYPE
    SYNTAX  INTEGER {
        enabled(1),
        disabled(2)
        }
    MAX-ACCESS  read-only
    STATUS  current
    DESCRIPTION
        "Enable/Disable virtual service hostname matching in
        the current configuration block."
    ::= { gslbGeneralCfg 43 }

gslbNewCfgGenHostname OBJECT-TYPE
    SYNTAX  INTEGER {
        enabled(1),
        disabled(2)
        }
    MAX-ACCESS  read-write
    STATUS  current
    DESCRIPTION
        "Enable/Disable virtual service hostname matching in
        the new configuration block."
    ::= { gslbGeneralCfg 44 }

gslbCurCfgGenRemSiteUpdateIntervalSeconds OBJECT-TYPE
    SYNTAX  INTEGER (10..7200)
    MAX-ACCESS  read-only
    STATUS  current
    DESCRIPTION
        "The time interval in seconds for updating remote site status
         in the current_configuration block."
    ::= { gslbGeneralCfg 45 }

gslbNewCfgGenRemSiteUpdateIntervalSeconds OBJECT-TYPE
    SYNTAX  INTEGER (10..7200)
    MAX-ACCESS  read-write
    STATUS  current
    DESCRIPTION
        "The time interval in seconds for updating remote site status
         in the new_configuration block."
    ::= { gslbGeneralCfg 46 }

gslbCurCfgGenNoResp OBJECT-TYPE
    SYNTAX  INTEGER (1..5)
    MAX-ACCESS  read-only
    STATUS  current
    DESCRIPTION
        "DNS response code when no server is returned for the current_configuration block."
    ::= { gslbGeneralCfg 47 }

gslbNewCfgGenNoResp OBJECT-TYPE
    SYNTAX  INTEGER (1..5)
    MAX-ACCESS  read-write
    STATUS  current
    DESCRIPTION
        "DNS response code when no server is returned for the new_configuration block."
    ::= { gslbGeneralCfg 48 }



-- Global SLB Remote Site Configuration

gslbRemSiteTableMaxSize OBJECT-TYPE
    SYNTAX  Integer32
    MAX-ACCESS  read-only
    STATUS  current
    DESCRIPTION
        "The maximum number of GSLB remote sites."
    ::= { gslbSitesCfg 1 }

gslbCurCfgRemSiteTable OBJECT-TYPE
    SYNTAX  SEQUENCE OF GslbCurCfgRemSiteTableEntry
    MAX-ACCESS  not-accessible
    STATUS  current
    DESCRIPTION
        "The GSLB remote site table in the current configuration block."
    ::= { gslbSitesCfg 2 }

gslbCurCfgRemSiteTableEntry OBJECT-TYPE
    SYNTAX  GslbCurCfgRemSiteTableEntry
    MAX-ACCESS  not-accessible
    STATUS  current
    DESCRIPTION
        "A row in the GSLB remote site table."
    INDEX   { gslbCurCfgRemSiteIndx }
    ::= { gslbCurCfgRemSiteTable 1 }

GslbCurCfgRemSiteTableEntry ::= SEQUENCE {
    gslbCurCfgRemSiteIndx        Integer32,
    gslbCurCfgRemSitePrimaryIp   IpAddress,
    gslbCurCfgRemSiteSecondaryIp IpAddress,
    gslbCurCfgRemSiteState       INTEGER,
    gslbCurCfgRemSiteUpdate      INTEGER,
    gslbCurCfgRemSiteName        DisplayString
    }

gslbCurCfgRemSiteIndx OBJECT-TYPE
    SYNTAX  Integer32
    MAX-ACCESS  read-only
    STATUS  current
    DESCRIPTION
        "The GSLB remote site table index."
    ::= { gslbCurCfgRemSiteTableEntry 1 }

gslbCurCfgRemSitePrimaryIp OBJECT-TYPE
    SYNTAX  IpAddress
    MAX-ACCESS  read-only
    STATUS  current
    DESCRIPTION
        "The primary IP address of the remote site in the 
         current_configuration block."
    ::= { gslbCurCfgRemSiteTableEntry 2 }

gslbCurCfgRemSiteSecondaryIp OBJECT-TYPE
    SYNTAX  IpAddress
    MAX-ACCESS  read-only
    STATUS  current
    DESCRIPTION
        "The secondary IP address of the remote site in the 
	 current_configuration block."
    ::= { gslbCurCfgRemSiteTableEntry 3 }

gslbCurCfgRemSiteState OBJECT-TYPE
    SYNTAX  INTEGER {
        enabled(1),
        disabled(2)
        }
    MAX-ACCESS  read-only
    STATUS  current
    DESCRIPTION
        "Enable/Disable GSLB for the remote site in the 
         current_configuration block."
    ::= { gslbCurCfgRemSiteTableEntry 4 }

gslbCurCfgRemSiteUpdate OBJECT-TYPE
    SYNTAX  INTEGER {
        enabled(1),
        disabled(2)
        }
    MAX-ACCESS  read-only
    STATUS  current
    DESCRIPTION
        "Enable/Disable GSLB for the remote site status update in the 
         current_configuration block."
    ::= { gslbCurCfgRemSiteTableEntry 5 }

gslbCurCfgRemSiteName OBJECT-TYPE
    SYNTAX DisplayString (SIZE(0..31))
    MAX-ACCESS read-only
    STATUS current
    DESCRIPTION
	"The name of the GSLB remote site."
    ::= { gslbCurCfgRemSiteTableEntry 6 }


gslbNewCfgRemSiteTable OBJECT-TYPE
    SYNTAX  SEQUENCE OF GslbNewCfgRemSiteTableEntry
    MAX-ACCESS  not-accessible
    STATUS  current
    DESCRIPTION
        "The GSLB remote site table in the current configuration block."
    ::= { gslbSitesCfg 3 }

gslbNewCfgRemSiteTableEntry OBJECT-TYPE
    SYNTAX  GslbNewCfgRemSiteTableEntry
    MAX-ACCESS  not-accessible
    STATUS  current
    DESCRIPTION
        "A row in the GSLB remote site table in the current configuration block."
    INDEX   { gslbNewCfgRemSiteIndx }
    ::= { gslbNewCfgRemSiteTable 1 }

GslbNewCfgRemSiteTableEntry ::= SEQUENCE {
    gslbNewCfgRemSiteIndx        Integer32,
    gslbNewCfgRemSitePrimaryIp   IpAddress,
    gslbNewCfgRemSiteSecondaryIp IpAddress,
    gslbNewCfgRemSiteState       INTEGER,
    gslbNewCfgRemSiteUpdate      INTEGER,
    gslbNewCfgRemSiteDelete      INTEGER,
    gslbNewCfgRemSiteName        DisplayString
    }

gslbNewCfgRemSiteIndx OBJECT-TYPE
    SYNTAX  Integer32
    MAX-ACCESS  read-only
    STATUS  current
    DESCRIPTION
        "The GSLB remote site table index."
    ::= { gslbNewCfgRemSiteTableEntry 1 }

gslbNewCfgRemSitePrimaryIp OBJECT-TYPE
    SYNTAX  IpAddress
    MAX-ACCESS  read-create
    STATUS  current
    DESCRIPTION
        "The primary IP address of the remote site in the new_configuration 
         block."
    ::= { gslbNewCfgRemSiteTableEntry 2 }

gslbNewCfgRemSiteSecondaryIp OBJECT-TYPE
    SYNTAX  IpAddress
    MAX-ACCESS  read-create
    STATUS  current
    DESCRIPTION
        "The secondary IP address of the remote site in the new_configuration 
         block."
    ::= { gslbNewCfgRemSiteTableEntry 3 }

gslbNewCfgRemSiteState OBJECT-TYPE
    SYNTAX  INTEGER {
        enabled(1),
        disabled(2)
        }
    MAX-ACCESS  read-create
    STATUS  current
    DESCRIPTION
        "Enable/Disable GSLB for the remote site in the new_configuration 
         block."
    ::= { gslbNewCfgRemSiteTableEntry 4 }

gslbNewCfgRemSiteUpdate OBJECT-TYPE
    SYNTAX  INTEGER {
        enabled(1),
        disabled(2)
        }
    MAX-ACCESS  read-create
    STATUS  current
    DESCRIPTION
        "Enable/Disable GSLB for the remote site status update in the 
         new_configuration block."
    ::= { gslbNewCfgRemSiteTableEntry 5 }

gslbNewCfgRemSiteDelete OBJECT-TYPE
    SYNTAX INTEGER {
        other(1),
        delete(2)
        }
    MAX-ACCESS read-create
    STATUS current
    DESCRIPTION
        "By setting the value to delete(2), the entire row is deleted."
    ::= { gslbNewCfgRemSiteTableEntry 6 }

gslbNewCfgRemSiteName OBJECT-TYPE
    SYNTAX DisplayString (SIZE(0..31))
    MAX-ACCESS read-create
    STATUS current
    DESCRIPTION
	"The name of the GSLB remote site."
    ::= { gslbNewCfgRemSiteTableEntry 7 }


-- Global SLB Enhanced Network Configuration

gslbEnhNetworkTableMaxSize OBJECT-TYPE
    SYNTAX  Integer32
    MAX-ACCESS  read-only
    STATUS  current
    DESCRIPTION
        "The maximum number of Global SLB networks."
    ::= { gslbEnhNetworkCfg 1 }

gslbCurCfgEnhNetworkTable OBJECT-TYPE
    SYNTAX SEQUENCE OF GslbCurCfgEnhNetworkTableEntry
    MAX-ACCESS not-accessible
    STATUS current
    DESCRIPTION
        "The table of network preference in the current_config."
    ::= { gslbEnhNetworkCfg 2 }

gslbCurCfgEnhNetworkTableEntry OBJECT-TYPE
    SYNTAX GslbCurCfgEnhNetworkTableEntry
    MAX-ACCESS not-accessible
    STATUS current
    DESCRIPTION
        "The table about a network preference entry configuration."
    INDEX { gslbCurCfgEnhNetworkIndx }
    ::= { gslbCurCfgEnhNetworkTable 1 }

GslbCurCfgEnhNetworkTableEntry ::= SEQUENCE {
    gslbCurCfgEnhNetworkIndx       Integer32,
    gslbCurCfgEnhNetworkState      INTEGER,
    gslbCurCfgEnhNetworkSourceIp   IpAddress,
    gslbCurCfgEnhNetworkNetMask    IpAddress,
    gslbCurCfgEnhNetworkVirtServer OCTET STRING,
    gslbCurCfgEnhNetworkRemRealServer OCTET STRING
    }

gslbCurCfgEnhNetworkIndx  OBJECT-TYPE
    SYNTAX Integer32
    MAX-ACCESS read-only
    STATUS current
    DESCRIPTION
        "The current network preference table index."
    ::= { gslbCurCfgEnhNetworkTableEntry 1 }

gslbCurCfgEnhNetworkState OBJECT-TYPE
    SYNTAX  INTEGER {
        enabled(1),
        disabled(2)
        }
    MAX-ACCESS  read-only
    STATUS  current
    DESCRIPTION
        "Enable/Disable Global SLB for the network in the
         current_configuration block."
    ::= { gslbCurCfgEnhNetworkTableEntry 2 }

gslbCurCfgEnhNetworkSourceIp OBJECT-TYPE
    SYNTAX IpAddress
    MAX-ACCESS read-only
    STATUS current
    DESCRIPTION
        "The Source IP address of the network preference table."
    ::= { gslbCurCfgEnhNetworkTableEntry 3 }

gslbCurCfgEnhNetworkNetMask OBJECT-TYPE
    SYNTAX IpAddress
    MAX-ACCESS read-only
    STATUS current
    DESCRIPTION
        "The Net mask of the network preference table."
    ::= { gslbCurCfgEnhNetworkTableEntry 4 }

gslbCurCfgEnhNetworkVirtServer OBJECT-TYPE
    SYNTAX OCTET STRING
    MAX-ACCESS read-only
    STATUS current
    DESCRIPTION
        "The virtual servers in the network.
         The virtual servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented virtual server belongs to the network
                   0 - The represented virtual server does not belong to the network"
    ::= { gslbCurCfgEnhNetworkTableEntry 5 }

gslbCurCfgEnhNetworkRemRealServer OBJECT-TYPE
    SYNTAX OCTET STRING
    MAX-ACCESS read-only
    STATUS current
    DESCRIPTION
        "The remote real servers in the network.
         The remote real servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented remote real server belongs to the network
                   0 - The represented remote real server does not belong to the network"
    ::= { gslbCurCfgEnhNetworkTableEntry 6 }

gslbNewCfgEnhNetworkTable OBJECT-TYPE
    SYNTAX SEQUENCE OF GslbNewCfgEnhNetworkTableEntry
    MAX-ACCESS not-accessible
    STATUS current
    DESCRIPTION
        "The table of network preference in the new_config."
    ::= { gslbEnhNetworkCfg 3 }

gslbNewCfgEnhNetworkTableEntry OBJECT-TYPE
    SYNTAX GslbNewCfgEnhNetworkTableEntry
    MAX-ACCESS not-accessible
    STATUS current
    DESCRIPTION
        "The table about a network preference entry configuration."
    INDEX { gslbNewCfgEnhNetworkIndx }
    ::= { gslbNewCfgEnhNetworkTable 1 }

GslbNewCfgEnhNetworkTableEntry ::= SEQUENCE {
    gslbNewCfgEnhNetworkIndx       Integer32,
    gslbNewCfgEnhNetworkState      INTEGER,
    gslbNewCfgEnhNetworkSourceIp   IpAddress,
    gslbNewCfgEnhNetworkNetMask    IpAddress,
    gslbNewCfgEnhNetworkDelete     INTEGER,
    gslbNewCfgEnhNetworkVirtServer           OCTET STRING,
    gslbNewCfgEnhNetworkRemRealServer        OCTET STRING,
    gslbNewCfgEnhNetworkAddVirtServer        Integer32,
    gslbNewCfgEnhNetworkRemoveVirtServer     Integer32,
    gslbNewCfgEnhNetworkAddRemRealServer     Integer32,
    gslbNewCfgEnhNetworkRemoveRemRealServer  Integer32
    }

gslbNewCfgEnhNetworkIndx  OBJECT-TYPE
    SYNTAX Integer32
    MAX-ACCESS read-only
    STATUS current
    DESCRIPTION
        "The new network preference table index."
    ::= { gslbNewCfgEnhNetworkTableEntry 1 }

gslbNewCfgEnhNetworkState OBJECT-TYPE
    SYNTAX  INTEGER {
        enabled(1),
        disabled(2)
        }
    MAX-ACCESS  read-create
    STATUS  current
    DESCRIPTION
        "Enable/Disable Global SLB for the network in
        the new_configuration block."
    ::= { gslbNewCfgEnhNetworkTableEntry 2 }

gslbNewCfgEnhNetworkSourceIp OBJECT-TYPE
    SYNTAX IpAddress
    MAX-ACCESS read-create
    STATUS current
    DESCRIPTION
        "The Source IP address of the network table."
    ::= { gslbNewCfgEnhNetworkTableEntry 3 }

gslbNewCfgEnhNetworkNetMask OBJECT-TYPE
    SYNTAX IpAddress
    MAX-ACCESS read-create
    STATUS current
    DESCRIPTION
        "The Net mask of the network preference table."
    ::= { gslbNewCfgEnhNetworkTableEntry 4 }

gslbNewCfgEnhNetworkDelete OBJECT-TYPE
    SYNTAX INTEGER {
        other(1),
        delete(2)
        }
    MAX-ACCESS read-create
    STATUS current
    DESCRIPTION
        "By setting the value to delete(2), the entire row is deleted."
    ::= { gslbNewCfgEnhNetworkTableEntry 5}

gslbNewCfgEnhNetworkVirtServer OBJECT-TYPE
    SYNTAX OCTET STRING
    MAX-ACCESS read-only
    STATUS current
    DESCRIPTION
        "The virtual servers in the network.
         The virtual servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented virtual server belongs to the network
                   0 - The represented virtual server does not belong to the network"
    ::= { gslbNewCfgEnhNetworkTableEntry 6 }

gslbNewCfgEnhNetworkRemRealServer OBJECT-TYPE
    SYNTAX OCTET STRING
    MAX-ACCESS read-only
    STATUS current
    DESCRIPTION
        "The remote real servers in the network.
         The remote real servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented remote real server belongs to the network
                   0 - The represented remote real server does not belong to the network"
    ::= { gslbNewCfgEnhNetworkTableEntry 7 }

gslbNewCfgEnhNetworkAddVirtServer OBJECT-TYPE
    SYNTAX  Integer32
    MAX-ACCESS  read-create
    STATUS  current
    DESCRIPTION
        "The virtual server to be added to the network. When read, 0 is returned."
    ::= { gslbNewCfgEnhNetworkTableEntry 8 }

gslbNewCfgEnhNetworkRemoveVirtServer OBJECT-TYPE
    SYNTAX  Integer32
    MAX-ACCESS  read-create
    STATUS  current
    DESCRIPTION
        "The virtual server to be removed from the network. When read, 0 is returned."
    ::= { gslbNewCfgEnhNetworkTableEntry 9 }

gslbNewCfgEnhNetworkAddRemRealServer OBJECT-TYPE
    SYNTAX  Integer32
    MAX-ACCESS  read-create
    STATUS  current
    DESCRIPTION
        "The remote real server to be added to the network. When read, 0 is returned."
    ::= { gslbNewCfgEnhNetworkTableEntry 10 }

gslbNewCfgEnhNetworkRemoveRemRealServer OBJECT-TYPE
    SYNTAX  Integer32
    MAX-ACCESS  read-create
    STATUS  current
    DESCRIPTION
        "The remote real server to be removed from the network. When read, 0 is returned."
    ::= { gslbNewCfgEnhNetworkTableEntry 11 }

-- Global SLB Rule Configuration

gslbRuleTableMaxSize OBJECT-TYPE
    SYNTAX  Integer32
    MAX-ACCESS  read-only
    STATUS  current
    DESCRIPTION
        "The maximum number of Global SLB rules."
    ::= { gslbRuleCfg 1 }

gslbCurCfgRuleTable OBJECT-TYPE
    SYNTAX SEQUENCE OF GslbCurCfgRuleTableEntry
    MAX-ACCESS not-accessible
    STATUS current
    DESCRIPTION
        "The rule table in the current configuration block."
    ::= { gslbRuleCfg 2 }

gslbCurCfgRuleTableEntry OBJECT-TYPE
    SYNTAX GslbCurCfgRuleTableEntry
    MAX-ACCESS not-accessible
    STATUS current
    DESCRIPTION
        "An entry in the rule table in the current configuration block."
    INDEX { gslbCurCfgRuleIndx }
    ::= { gslbCurCfgRuleTable 1 }

GslbCurCfgRuleTableEntry ::= SEQUENCE {
    gslbCurCfgRuleIndx         Integer32,
    gslbCurCfgRuleState        INTEGER,
    gslbCurCfgRuleStartHour    INTEGER,
    gslbCurCfgRuleStartMin     INTEGER,
    gslbCurCfgRuleEndHour      INTEGER,
    gslbCurCfgRuleEndMin       INTEGER,
    gslbCurCfgRuleTTL          INTEGER,
    gslbCurCfgRuleRR           INTEGER
    }

gslbCurCfgRuleIndx  OBJECT-TYPE
    SYNTAX Integer32
    MAX-ACCESS read-only
    STATUS current
    DESCRIPTION
        "The rule table index in the current configuration block."
    ::= { gslbCurCfgRuleTableEntry 1 }

gslbCurCfgRuleState OBJECT-TYPE
    SYNTAX  INTEGER {
        enabled(1),
        disabled(2)
        }
    MAX-ACCESS  read-only
    STATUS  current
    DESCRIPTION
        "Enable/Disable the rule in
         the current configuration block."
    ::= { gslbCurCfgRuleTableEntry 2 }

gslbCurCfgRuleStartHour OBJECT-TYPE
    SYNTAX  INTEGER (0..23)
    MAX-ACCESS  read-only
    STATUS  current
    DESCRIPTION
        "Start hour in 24-hour format for the rule in
         the current configuration block."
    ::= { gslbCurCfgRuleTableEntry 3 }

gslbCurCfgRuleStartMin OBJECT-TYPE
    SYNTAX  INTEGER (0..59)
    MAX-ACCESS  read-only
    STATUS  current
    DESCRIPTION
        "Start minutes for the rule in
         the current configuration block."
    ::= { gslbCurCfgRuleTableEntry 4 }

gslbCurCfgRuleEndHour OBJECT-TYPE
    SYNTAX  INTEGER (0..23)
    MAX-ACCESS  read-only
    STATUS  current
    DESCRIPTION
        "End hour in 24-hour format for the rule in
         the current configuration block."
    ::= { gslbCurCfgRuleTableEntry 5 }

gslbCurCfgRuleEndMin OBJECT-TYPE
    SYNTAX  INTEGER (0..59)
    MAX-ACCESS  read-only
    STATUS  current
    DESCRIPTION
        "End minutes for the rule in
         the current configuration block."
    ::= { gslbCurCfgRuleTableEntry 6 }

gslbCurCfgRuleTTL OBJECT-TYPE
    SYNTAX  INTEGER (0..65535)
    MAX-ACCESS  read-only
    STATUS  current
    DESCRIPTION
        "Time to live in seconds of DNS resource records for the rule in
         the current configuration block."
    ::= { gslbCurCfgRuleTableEntry 7 }

gslbCurCfgRuleRR OBJECT-TYPE
    SYNTAX  INTEGER (1..10)
    MAX-ACCESS  read-only
    STATUS  current
    DESCRIPTION
        "DNS resource records in DNS response for the rule in
         the current configuration block."
    ::= { gslbCurCfgRuleTableEntry 8 }


gslbNewCfgRuleTable OBJECT-TYPE
    SYNTAX SEQUENCE OF GslbNewCfgRuleTableEntry
    MAX-ACCESS not-accessible
    STATUS current
    DESCRIPTION
        "The rule table in the new configuration block."
    ::= { gslbRuleCfg 3 }

gslbNewCfgRuleTableEntry OBJECT-TYPE
    SYNTAX GslbNewCfgRuleTableEntry
    MAX-ACCESS not-accessible
    STATUS current
    DESCRIPTION
        "An entry in the rule table in the new configuration block."
    INDEX { gslbNewCfgRuleIndx }
    ::= { gslbNewCfgRuleTable 1 }

GslbNewCfgRuleTableEntry ::= SEQUENCE {
    gslbNewCfgRuleIndx         Integer32,
    gslbNewCfgRuleState        INTEGER,
    gslbNewCfgRuleStartHour    INTEGER,
    gslbNewCfgRuleStartMin     INTEGER,
    gslbNewCfgRuleEndHour      INTEGER,
    gslbNewCfgRuleEndMin       INTEGER,
    gslbNewCfgRuleTTL          INTEGER,
    gslbNewCfgRuleRR           INTEGER,
    gslbNewCfgRuleDelete       INTEGER
    }

gslbNewCfgRuleIndx  OBJECT-TYPE
    SYNTAX Integer32
    MAX-ACCESS read-only
    STATUS current
    DESCRIPTION
        "The rule table index in the new configuration block."
    ::= { gslbNewCfgRuleTableEntry 1 }

gslbNewCfgRuleState OBJECT-TYPE
    SYNTAX  INTEGER {
        enabled(1),
        disabled(2)
        }
    MAX-ACCESS  read-create
    STATUS  current
    DESCRIPTION
        "Enable/Disable the rule in
         the new configuration block."
    ::= { gslbNewCfgRuleTableEntry 2 }

gslbNewCfgRuleStartHour OBJECT-TYPE
    SYNTAX  INTEGER (0..23)
    MAX-ACCESS  read-write
    STATUS  current
    DESCRIPTION
        "Start hour in 24-hour format for the rule in
         the new configuration block."
    ::= { gslbNewCfgRuleTableEntry 3 }

gslbNewCfgRuleStartMin OBJECT-TYPE
    SYNTAX  INTEGER (0..59)
    MAX-ACCESS  read-write
    STATUS  current
    DESCRIPTION
        "Start minutes for the rule in
         the new configuration block."
    ::= { gslbNewCfgRuleTableEntry 4 }

gslbNewCfgRuleEndHour OBJECT-TYPE
    SYNTAX  INTEGER (0..23)
    MAX-ACCESS  read-write
    STATUS  current
    DESCRIPTION
        "End hour in 24-hour format for the rule in
         the new configuration block."
    ::= { gslbNewCfgRuleTableEntry 5 }

gslbNewCfgRuleEndMin OBJECT-TYPE
    SYNTAX  INTEGER (0..59)
    MAX-ACCESS  read-write
    STATUS  current
    DESCRIPTION
        "End minutes for the rule in
         the new configuration block."
    ::= { gslbNewCfgRuleTableEntry 6 }

gslbNewCfgRuleTTL OBJECT-TYPE
    SYNTAX  INTEGER (0..65535)
    MAX-ACCESS  read-write
    STATUS  current
    DESCRIPTION
        "Time to live in seconds of DNS resource records for the rule in
         the new configuration block."
    ::= { gslbNewCfgRuleTableEntry 7 }

gslbNewCfgRuleRR OBJECT-TYPE
    SYNTAX  INTEGER (1..10)
    MAX-ACCESS  read-write
    STATUS  current
    DESCRIPTION
        "DNS resource records in DNS response for the rule in
         the new configuration block."
    ::= { gslbNewCfgRuleTableEntry 8 }


gslbNewCfgRuleDelete OBJECT-TYPE
    SYNTAX INTEGER {
        other(1),
        delete(2)
        }
    MAX-ACCESS read-create
    STATUS current
    DESCRIPTION
        "By setting the value to delete(2), the entire row is deleted."
    ::= { gslbNewCfgRuleTableEntry 9 }

-- Global SLB Metric Configuration

gslbMetricTableMaxSize OBJECT-TYPE
    SYNTAX Integer32
    MAX-ACCESS read-only
    STATUS current
    DESCRIPTION
        "The maximum number of Global SLB metrics for each Global SLB rule."
    ::= { gslbRuleCfg 4 }

gslbCurCfgMetricTable OBJECT-TYPE
    SYNTAX SEQUENCE OF GslbCurCfgMetricTableEntry
    MAX-ACCESS not-accessible
    STATUS current
    DESCRIPTION
        "The metric table in the current configuration block."
    ::= { gslbRuleCfg 5 }

gslbCurCfgMetricTableEntry OBJECT-TYPE
    SYNTAX GslbCurCfgMetricTableEntry
    MAX-ACCESS not-accessible
    STATUS current
    DESCRIPTION
        "An entry in the metric table in the current configuration block."
    INDEX { gslbCurCfgRuleMetricIndx, gslbCurCfgMetricIndx }
    ::= { gslbCurCfgMetricTable 1 }

GslbCurCfgMetricTableEntry ::= SEQUENCE {
    gslbCurCfgRuleMetricIndx        Integer32,
    gslbCurCfgMetricIndx            Integer32,
    gslbCurCfgMetricMetric          INTEGER,
    gslbCurCfgMetricNetworkBmap     OCTET STRING
    }

gslbCurCfgRuleMetricIndx  OBJECT-TYPE
    SYNTAX Integer32
    MAX-ACCESS read-only
    STATUS current
    DESCRIPTION
        "The rule table index in the current configuration block."
    ::= { gslbCurCfgMetricTableEntry 1 }

gslbCurCfgMetricIndx  OBJECT-TYPE
    SYNTAX Integer32
    MAX-ACCESS read-only
    STATUS current
    DESCRIPTION
        "The metric table index in the current configuration block."
    ::= { gslbCurCfgMetricTableEntry 2 }

gslbCurCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15)
        }
    MAX-ACCESS read-only
    STATUS current
    DESCRIPTION
        "The metric to use to select next server in
         the current configuration block."
    ::= { gslbCurCfgMetricTableEntry 3 }

gslbCurCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbCurCfgMetricTableEntry 4 }

gslbNewCfgMetricTable OBJECT-TYPE
    SYNTAX SEQUENCE OF GslbNewCfgMetricTableEntry
    MAX-ACCESS not-accessible
    STATUS current
    DESCRIPTION
        "The metric table in the current configuration block."
    ::= { gslbRuleCfg 6 }

gslbNewCfgMetricTableEntry OBJECT-TYPE
    SYNTAX GslbNewCfgMetricTableEntry
    MAX-ACCESS not-accessible
    STATUS current
    DESCRIPTION
        "An entry in the metric table in the current configuration block."
    INDEX { gslbNewCfgRuleMetricIndx, gslbNewCfgMetricIndx }
    ::= { gslbNewCfgMetricTable 1 }

GslbNewCfgMetricTableEntry ::= SEQUENCE {
    gslbNewCfgRuleMetricIndx        Integer32,
    gslbNewCfgMetricIndx            Integer32,
    gslbNewCfgMetricMetric          INTEGER,
    gslbNewCfgMetricNetworkBmap     OCTET STRING,
    gslbNewCfgMetricAddNetwork      Integer32,
    gslbNewCfgMetricRemNetwork      Integer32
    }

gslbNewCfgRuleMetricIndx  OBJECT-TYPE
    SYNTAX Integer32
    MAX-ACCESS read-only
    STATUS current
    DESCRIPTION
        "The rule table index in the new configuration block."
    ::= { gslbNewCfgMetricTableEntry 1 }

gslbNewCfgMetricIndx  OBJECT-TYPE
    SYNTAX Integer32
    MAX-ACCESS read-only
    STATUS current
    DESCRIPTION
        "The metric table index in the new configuration block."
    ::= { gslbNewCfgMetricTableEntry 2 }

gslbNewCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15)
        }
    MAX-ACCESS read-write
    STATUS current
    DESCRIPTION
        "The metric to use to select next server in
         the new configuration block."
    ::= { gslbNewCfgMetricTableEntry 3 }

gslbNewCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbNewCfgMetricTableEntry 4 }

gslbNewCfgMetricAddNetwork OBJECT-TYPE
    SYNTAX  Integer32
    MAX-ACCESS read-write
    STATUS  current
    DESCRIPTION
        "This is an action object to add network to a metric. The range of the
         valid index is between 1 and gslbEnhNetworkTableMaxSize. When read, the
         value '0' is returned always."
    ::= { gslbNewCfgMetricTableEntry 5 }

gslbNewCfgMetricRemNetwork OBJECT-TYPE
    SYNTAX  Integer32
    MAX-ACCESS read-write
    STATUS  current
    DESCRIPTION
        "This is an action object to remove network to a metric. The range of the
         valid index is between 1 and gslbEnhNetworkTableMaxSize. When read, the
         value '0' is returned always."
    ::= { gslbNewCfgMetricTableEntry 6 }

-- Health Script Configuration
 
hcsTableMaxSize OBJECT-TYPE
    SYNTAX  Integer32
    MAX-ACCESS  read-only
    STATUS  current
    DESCRIPTION
        "The maximum number of scriptable health check entries."
    ::= { hcsCfg 1 }

hcsCurCfgTable OBJECT-TYPE
    SYNTAX  SEQUENCE OF HcsCurCfgTableEntry
    MAX-ACCESS  not-accessible
    STATUS  current
    DESCRIPTION
        "The scriptable health check table in the current configuration block."
    ::= { hcsCfg 2 }

hcsCurCfgTableEntry OBJECT-TYPE
    SYNTAX  HcsCurCfgTableEntry
    MAX-ACCESS  not-accessible
    STATUS  current
    DESCRIPTION
        "A row in the scriptable health check table."
    INDEX   { hcsCurCfgScriptIndex }
    ::= { hcsCurCfgTable 1 }

HcsCurCfgTableEntry ::= SEQUENCE {
    hcsCurCfgScriptIndex     Integer32,
    hcsCurCfgScriptString    OCTET STRING
    }

hcsCurCfgScriptIndex OBJECT-TYPE
    SYNTAX Integer32
    MAX-ACCESS read-only
    STATUS current
    DESCRIPTION
        "The index in the scriptable health check table."
    ::= { hcsCurCfgTableEntry 1 }

hcsCurCfgScriptString OBJECT-TYPE
    SYNTAX OCTET STRING 
    MAX-ACCESS read-only
    STATUS current
    DESCRIPTION
        "The scriptable health check string."
    ::= { hcsCurCfgTableEntry 2 }

hcsNewCfgTable OBJECT-TYPE
    SYNTAX  SEQUENCE OF HcsNewCfgTableEntry
    MAX-ACCESS  not-accessible
    STATUS  current
    DESCRIPTION
        "The scriptable health check table in the new configuration block."
    ::= { hcsCfg 3 }

hcsNewCfgTableEntry OBJECT-TYPE
    SYNTAX  HcsNewCfgTableEntry
    MAX-ACCESS  not-accessible
    STATUS  current
    DESCRIPTION
        "A row in the scriptable health check table."
    INDEX   { hcsNewCfgScriptIndex }
    ::= { hcsNewCfgTable 1 }

HcsNewCfgTableEntry ::= SEQUENCE {
    hcsNewCfgScriptIndex       Integer32,
    hcsNewCfgScriptString      OCTET STRING,
    hcsNewCfgAddSendCmd        DisplayString,     -- obsolete
    hcsNewCfgAddExpectCmd      DisplayString,     -- obsolete
    hcsNewCfgAddCloseCmd       INTEGER,
    hcsNewCfgRemLastCmd        INTEGER,
    hcsNewCfgAddWaitCmd        INTEGER,
    hcsNewCfgAddOffsetCmd      INTEGER,
    hcsNewCfgAddOpenProtCmd    DisplayString,
    hcsNewCfgAddDepthCmd       INTEGER,
    hcsNewCfgAddLongNsendCmd   OCTET STRING,
    hcsNewCfgAddLongNexpectCmd OCTET STRING,
    hcsNewCfgAddNsendCmd       DisplayString,     -- obsolete
    hcsNewCfgAddNexpectCmd     DisplayString,     -- obsolete
    hcsNewCfgAddLongBsendCmd   OCTET STRING,
    hcsNewCfgAddLongBexpectCmd OCTET STRING,
    hcsNewCfgAddLongSendCmd    OCTET STRING,
    hcsNewCfgAddLongExpectCmd  OCTET STRING,
    hcsNewCfgDeleteScript      INTEGER
    }

hcsNewCfgScriptIndex OBJECT-TYPE
    SYNTAX Integer32
    MAX-ACCESS read-only
    STATUS current
    DESCRIPTION
        "The index the scriptable health check."
    ::= { hcsNewCfgTableEntry 1 }

hcsNewCfgScriptString OBJECT-TYPE
    SYNTAX OCTET STRING
    MAX-ACCESS read-only
    STATUS current
    DESCRIPTION
        "The scriptable health check string."
    ::= { hcsNewCfgTableEntry 2 }


hcsNewCfgAddSendCmd OBJECT-TYPE
    SYNTAX DisplayString (SIZE(0..255))
    MAX-ACCESS read-create
    STATUS obsolete
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 4 }

hcsNewCfgAddExpectCmd OBJECT-TYPE
    SYNTAX DisplayString (SIZE(0..255))
    MAX-ACCESS read-create
    STATUS obsolete
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 5 }

hcsNewCfgAddCloseCmd OBJECT-TYPE
    SYNTAX INTEGER {
        other(1),
        close(2)
        }
    MAX-ACCESS read-create
    STATUS current
    DESCRIPTION
        "Add close command to end of the script. When set to the value of 2
         (add), 'close' will be appended to the script. Also, a 
         'null terminator'(\0) will be automatically appended. The null 
         terminator and the 'close' characters will be counted as characters 
         in the script.  This command is only valid for TCP."
    ::= { hcsNewCfgTableEntry 6 }

hcsNewCfgRemLastCmd OBJECT-TYPE
    SYNTAX INTEGER {
        other(1),
        remove(2)
        }
    MAX-ACCESS read-create
    STATUS current
    DESCRIPTION
        "Remove the last command from the script. When set to the value of 2
         (remove), last command will be removed from the script. When read,
         other(1) is returned."
    ::= { hcsNewCfgTableEntry 7 }

hcsNewCfgDeleteScript OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { hcsNewCfgTableEntry 8 }

hcsNewCfgAddOffsetCmd OBJECT-TYPE
    SYNTAX INTEGER (1..1464)
    MAX-ACCESS read-create
    STATUS current
    DESCRIPTION
        "Append an 'offset' command to the script. The set value of this
	 object should be the offset from the beginning of the data area
	 of the TCP/UDP packet to start matching the string configured
	 in the last bexpect command. The 'offset ' characters will be
         automatically appended. Also a 'null terminator'(\0) will be 
         automatically appended. The null terminator and the 'offset '
         characters will be counted as characters in the script.  When 
	 read, the return value has no significant meaning, but a 1 is
	 always returned."
    ::= { hcsNewCfgTableEntry 9 }

hcsNewCfgAddWaitCmd OBJECT-TYPE
    SYNTAX INTEGER (1..65535)
    MAX-ACCESS read-create
    STATUS current
    DESCRIPTION
        "Append a 'wait' command to the script. The set value of this
	 object should be the maximum waiting time for the packet
	 containing the content configured in the last expect command.
	 Wait time is in units of milliseconds, and the maximum
	 supported is 65535 ms.  The 'wait ' characters will be 
	 automatically appended. Also a 'null terminator'(\0) will be
         automatically appended. The null terminator and the 'wait ' 
         characters will be counted as characters in the script. When 
	 read, the return value has no significant meaning, but a 1 is
	 always returned. "
    ::= { hcsNewCfgTableEntry 10 }

hcsNewCfgAddOpenProtCmd OBJECT-TYPE
    SYNTAX DisplayString (SIZE(0..31))
    MAX-ACCESS read-create
    STATUS current
    DESCRIPTION
        "Append an 'open' command to the script. The value of this object
         should be real server port number or name, followed by a comma,
	 and then the protocol (either tcp or udp), e.g. '80,tcp'.  Only
	 the port number or name, and tcp or udp should be set. The 'open ' 
	 characters will be automatically appended. Also a 'null terminator'
         (\0) will be automatically appended. The null terminator and the
         'open ' characters will be counted as characters in the script."
    ::= { hcsNewCfgTableEntry 11 }

hcsNewCfgAddNsendCmd OBJECT-TYPE
    SYNTAX DisplayString (SIZE(0..255))
    MAX-ACCESS read-create
    STATUS obsolete
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 12 }

hcsNewCfgAddNexpectCmd OBJECT-TYPE
    SYNTAX DisplayString (SIZE(0..255))
    MAX-ACCESS read-create
    STATUS obsolete
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 13 }

hcsNewCfgAddDepthCmd OBJECT-TYPE
    SYNTAX INTEGER (1..1464)
    MAX-ACCESS read-create
    STATUS current
    DESCRIPTION
        "Append a 'depth' command to the script. The set value of this
	 object should be the depth (search window) within the data
	 area of the TCP/UDP packet for matching the string configured
	 in the last bexpect command. The 'depth ' characters will be
         automatically appended. Also a 'null terminator'(\0) will be 
         automatically appended. The null terminator and the 'depth '
         characters will be counted as characters in the script. When 
	 read, the return value has no significant meaning, but a 1 is
	 always returned."
    ::= { hcsNewCfgTableEntry 14 }

hcsNewCfgAddLongBsendCmd OBJECT-TYPE
    SYNTAX OCTET STRING (SIZE(0..506))
    MAX-ACCESS read-create
    STATUS current
    DESCRIPTION
        "Append a 'bsend' command to the script. The set value of this
	 object should be the exact binary data in hex format to be sent 
         on the port opened with the 'open' command. The 'bsend ' characters 
         will be automatically appended. Also a 'null terminator' (\0)
	 will be automatically appended. The null terminator and the 'bsend '
	 characters will be counted as characters in the script."
    ::= { hcsNewCfgTableEntry 15 }

hcsNewCfgAddLongBexpectCmd OBJECT-TYPE
    SYNTAX OCTET STRING (SIZE(0..504))
    MAX-ACCESS read-create
    STATUS current
    DESCRIPTION
        "Append a 'bexpect' command to the script. The set value of this 
	 object should be the exact binary data in hex format expected to
	 be received on the port opened with the 'open' command. The value 
         could also be a single wildcard character '*' which means any 
         received content will be accepted.  The 'bexpect ' characters 
	 will be automatically appended.  Also a 'null terminator'(\0)
	 will be automatically appended.  The null terminator and the 
	 'bexpect ' characters will be counted as characters in the script."
    ::= { hcsNewCfgTableEntry 16 }

hcsNewCfgAddLongSendCmd OBJECT-TYPE
    SYNTAX OCTET STRING (SIZE(0..507))
    MAX-ACCESS read-create
    STATUS current
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 17 }

hcsNewCfgAddLongExpectCmd OBJECT-TYPE
    SYNTAX OCTET STRING (SIZE(0..505))
    MAX-ACCESS read-create
    STATUS current
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 18 }

hcsNewCfgAddLongNsendCmd OBJECT-TYPE
    SYNTAX OCTET STRING (SIZE(0..506))
    MAX-ACCESS read-create
    STATUS current
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 19 }

hcsNewCfgAddLongNexpectCmd OBJECT-TYPE
    SYNTAX OCTET STRING (SIZE(0..504))
    MAX-ACCESS read-create
    STATUS current
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 20 }

-- SNMP health check configuration 
 
snmphcTableMaxSize OBJECT-TYPE
    SYNTAX  Integer32
    MAX-ACCESS  read-only
    STATUS  current
    DESCRIPTION
        "The maximum number of SNMP health check entries."
    ::= { snmphcCfg 1 }

snmphcCurCfgTable OBJECT-TYPE
    SYNTAX  SEQUENCE OF SnmphcCurCfgTableEntry
    MAX-ACCESS  not-accessible
    STATUS  current
    DESCRIPTION
        "The SNMP health check table in the current configuration block."
    ::= { snmphcCfg 2 }

snmphcCurCfgTableEntry OBJECT-TYPE
    SYNTAX  SnmphcCurCfgTableEntry
    MAX-ACCESS  not-accessible
    STATUS  current
    DESCRIPTION
        "A row in the SNMP health check table."
    INDEX   { snmphcCurCfgIndex }
    ::= { snmphcCurCfgTable 1 }

SnmphcCurCfgTableEntry ::= SEQUENCE {
    snmphcCurCfgIndex          Integer32,
    snmphcCurCfgOid            DisplayString,
    snmphcCurCfgCommString     DisplayString,
    snmphcCurCfgRcvContent     DisplayString,
    snmphcCurCfgInvert         INTEGER,
    snmphcCurCfgUseWeight      INTEGER
    }

snmphcCurCfgIndex OBJECT-TYPE
    SYNTAX Integer32
    MAX-ACCESS read-only
    STATUS current
    DESCRIPTION
        "The index of the SNMP health check."
    ::= { snmphcCurCfgTableEntry 1 }

snmphcCurCfgOid OBJECT-TYPE
    SYNTAX DisplayString (SIZE(0..255))
    MAX-ACCESS read-only
    STATUS current
    DESCRIPTION
        "The OID to be sent in the SNMP get request packet."
    ::= { snmphcCurCfgTableEntry 2 }

snmphcCurCfgCommString OBJECT-TYPE
    SYNTAX DisplayString (SIZE(0..32))
    MAX-ACCESS read-only
    STATUS current
    DESCRIPTION
        "The community string to be used in the SNMP get request packet."
    ::= { snmphcCurCfgTableEntry 3 }

snmphcCurCfgRcvContent OBJECT-TYPE
    SYNTAX DisplayString (SIZE(0..64))
    MAX-ACCESS read-only
    STATUS current
    DESCRIPTION
        "The content expected in the SNMP response packet. The content  
        specified can be either a string or an integer value."
    ::= { snmphcCurCfgTableEntry 4 }

snmphcCurCfgInvert OBJECT-TYPE
    SYNTAX INTEGER {
        enabled(1),
        disabled(2)
        }
    MAX-ACCESS read-only
    STATUS current
    DESCRIPTION
        "When the invert option is enabled the health check will fail if
         the response packet contains the value specified in the 
         receive content field."
    ::= { snmphcCurCfgTableEntry 5 }

snmphcCurCfgUseWeight OBJECT-TYPE
    SYNTAX INTEGER {
        enabled(1),
        disabled(2)
        }
    MAX-ACCESS read-only
    STATUS current
    DESCRIPTION
        "When the weight option is enabled the real server weights are 
         adjusted dynamically based on the SNMP health check response."
    ::= { snmphcCurCfgTableEntry 6 }

snmphcNewCfgTable OBJECT-TYPE
    SYNTAX  SEQUENCE OF SnmphcNewCfgTableEntry
    MAX-ACCESS  not-accessible
    STATUS  current
    DESCRIPTION
        "The SNMP health check table in the new configuration block."
    ::= { snmphcCfg 3 }

snmphcNewCfgTableEntry OBJECT-TYPE
    SYNTAX  SnmphcNewCfgTableEntry
    MAX-ACCESS  not-accessible
    STATUS  current
    DESCRIPTION
        "A row in the SNMP health check table."
    INDEX   { snmphcNewCfgIndex }
    ::= { snmphcNewCfgTable 1 }

SnmphcNewCfgTableEntry ::= SEQUENCE {
    snmphcNewCfgIndex          Integer32,
    snmphcNewCfgOid            DisplayString,
    snmphcNewCfgCommString     DisplayString,
    snmphcNewCfgRcvContent     DisplayString,
    snmphcNewCfgInvert         INTEGER,
    snmphcNewCfgDeleteHc       INTEGER,
    snmphcNewCfgUseWeight      INTEGER
    }

snmphcNewCfgIndex OBJECT-TYPE
    SYNTAX Integer32
    MAX-ACCESS read-only
    STATUS current
    DESCRIPTION
        "The index of the SNMP health check."
    ::= { snmphcNewCfgTableEntry 1 }

snmphcNewCfgOid OBJECT-TYPE
    SYNTAX DisplayString (SIZE(0..255))
    MAX-ACCESS read-create
    STATUS current
    DESCRIPTION
        "The OID to be sent in the SNMP get request packet."
    ::= { snmphcNewCfgTableEntry 2 }

snmphcNewCfgCommString OBJECT-TYPE
    SYNTAX DisplayString (SIZE(0..32))
    MAX-ACCESS read-create
    STATUS current
    DESCRIPTION
        "The community string to be used in the SNMP get request packet."
    ::= { snmphcNewCfgTableEntry 3 }

snmphcNewCfgRcvContent OBJECT-TYPE
    SYNTAX DisplayString (SIZE(0..64))
    MAX-ACCESS read-create
    STATUS current
    DESCRIPTION
        "The content expected in the SNMP response packet. The content  
        specified can be either a string or an integer value."
    ::= { snmphcNewCfgTableEntry 4 }

snmphcNewCfgInvert OBJECT-TYPE
    SYNTAX INTEGER {
        enabled(1),
        disabled(2)
        }
    MAX-ACCESS read-create
    STATUS current
    DESCRIPTION
        "When the invert option is enabled the health check will fail if
         the response packet contains the value specified in the 
         receive content field."
    ::= { snmphcNewCfgTableEntry 5 }

snmphcNewCfgDeleteHc OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { snmphcNewCfgTableEntry 6 }

snmphcNewCfgUseWeight OBJECT-TYPE
    SYNTAX INTEGER {
        enabled(1),
        disabled(2)
        }
    MAX-ACCESS read-create
    STATUS current
    DESCRIPTION
        "When the weight option is enabled the real server weights are 
         adjusted dynamically based on the SNMP health check response."
    ::= { snmphcNewCfgTableEntry 7 }

-- Table sizes in current/new configuration of various tables

curCfgFilterTableSize OBJECT-TYPE
    SYNTAX Integer32 
    MAX-ACCESS read-only 
    STATUS current 
    DESCRIPTION 
        "Indicates the number of entries in the filter table current 
         configuration." 
    ::= { layer4TableSize 1 }

newCfgFilterTableSize OBJECT-TYPE
    SYNTAX Integer32 
    MAX-ACCESS read-only 
    STATUS current 
    DESCRIPTION 
        "Indicates the number of entries in the filter table new 
         configuration." 
    ::= { layer4TableSize 2 }

curCfgRealServerTableSize OBJECT-TYPE
    SYNTAX Integer32 
    MAX-ACCESS read-only 
    STATUS current 
    DESCRIPTION 
        "Indicates the number of entries in the SLB real server table 
         current configuration." 
    ::= { layer4TableSize 3 }

newCfgRealServerTableSize OBJECT-TYPE
    SYNTAX Integer32 
    MAX-ACCESS read-only 
    STATUS current 
    DESCRIPTION 
        "Indicates the number of entries in the SLB real server table 
         new configuration." 
    ::= { layer4TableSize 4 }

curCfgRealServerGroupTableSize OBJECT-TYPE
    SYNTAX Integer32 
    MAX-ACCESS read-only 
    STATUS current 
    DESCRIPTION 
        "Indicates the number of entries in the SLB real server group table 
         current configuration." 
    ::= { layer4TableSize 5 }

newCfgRealServerGroupTableSize OBJECT-TYPE
    SYNTAX Integer32 
    MAX-ACCESS read-only 
    STATUS current 
    DESCRIPTION 
        "Indicates the number of entries in the SLB real server group table 
         new configuration." 
    ::= { layer4TableSize 6 }

curCfgVirtServerTableSize OBJECT-TYPE
    SYNTAX Integer32 
    MAX-ACCESS read-only 
    STATUS current 
    DESCRIPTION 
        "Indicates the number of entries in the SLB virtual server table 
         current configuration." 
    ::= { layer4TableSize 7 }

newCfgVirtServerTableSize OBJECT-TYPE
    SYNTAX Integer32 
    MAX-ACCESS read-only 
    STATUS current 
    DESCRIPTION 
        "Indicates the number of entries in the SLB virtual server table 
         new configuration." 
    ::= { layer4TableSize 8 }

-- PIP Table configuration 
 
pipTableMaxSize OBJECT-TYPE
    SYNTAX  Integer32
    MAX-ACCESS  read-only
    STATUS  current
    DESCRIPTION
        "The maximum number of PIP entries."
    ::= { pipTblCfg 1 }
    
pipCurCfgBaseType OBJECT-TYPE
    SYNTAX INTEGER {
        port(1),
        vlan(2)
        }
    MAX-ACCESS  read-only
    STATUS  current
    DESCRIPTION
        "The PIP base. 1 = port based, 2 = VLAN based"
    ::= { pipTblCfg 2 }
    
pipCurCfgTable OBJECT-TYPE
    SYNTAX  SEQUENCE OF PipCurCfgTableEntry
    MAX-ACCESS  not-accessible
    STATUS  current
    DESCRIPTION
        "The PIP table in the current configuration block."
    ::= { pipTblCfg 3 }

pipCurCfgTableEntry OBJECT-TYPE
    SYNTAX  PipCurCfgTableEntry
    MAX-ACCESS  not-accessible
    STATUS  current
    DESCRIPTION
        "A row in the PIP table."
    INDEX   { pipCurCfgPip }
    ::= { pipCurCfgTable 1 }

PipCurCfgTableEntry ::= SEQUENCE {
    pipCurCfgPip            IpAddress,
    pipCurCfgPortMap	    OCTET STRING,
    pipCurCfgVlanMap        OCTET STRING
    }

pipCurCfgPip OBJECT-TYPE
    SYNTAX  IpAddress
    MAX-ACCESS  read-only
    STATUS  current
    DESCRIPTION
        "Proxy IP address by the instance of the pipCurCfgIndex." 
    ::= { pipCurCfgTableEntry 1 }
    
pipCurCfgPortMap    OBJECT-TYPE
    SYNTAX  OCTET STRING (SIZE(0..8))
    MAX-ACCESS  read-only
    STATUS  current
    DESCRIPTION
        "This is a bit map of port. 
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port."
         
    ::= { pipCurCfgTableEntry 2 }
    
pipCurCfgVlanMap    OBJECT-TYPE
    SYNTAX  OCTET STRING (SIZE(0..512))
    MAX-ACCESS  read-only
    STATUS  current
    DESCRIPTION
        "This is a bit map of VLAN. 

         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN."
         
    ::= { pipCurCfgTableEntry 3 }
    
pipNewCfgBaseType OBJECT-TYPE
    SYNTAX INTEGER {
        port(1),
        vlan(2)
        }
    MAX-ACCESS  read-write
    STATUS  current
    DESCRIPTION
        "The PIP base. 1 = port based, 2 = VLAN based"
    ::= { pipTblCfg 4 }
    
pipNewCfgTable OBJECT-TYPE
    SYNTAX  SEQUENCE OF PipNewCfgTableEntry
    MAX-ACCESS  not-accessible
    STATUS  current
    DESCRIPTION
        "The PIP table in the New configuration block."
    ::= { pipTblCfg 5 }

pipNewCfgTableEntry OBJECT-TYPE
    SYNTAX  PipNewCfgTableEntry
    MAX-ACCESS  not-accessible
    STATUS  current
    DESCRIPTION
        "A row in the PIP table."
    INDEX   { pipNewCfgPip }
    ::= { pipNewCfgTable 1 }

PipNewCfgTableEntry ::= SEQUENCE {
    pipNewCfgPip                IpAddress,
    pipNewCfgPortMap            OCTET STRING,
    pipNewCfgVlanMap            OCTET STRING,
    pipNewCfgDelete		INTEGER,
    pipNewCfgAddPortVlan	Integer32,
    pipNewCfgRemovePortVlan	Integer32
    }

pipNewCfgPip OBJECT-TYPE
    SYNTAX  IpAddress
    MAX-ACCESS  read-only
    STATUS  current
    DESCRIPTION
        "PIP address by the instance of the pipCurCfgIndex." 
    ::= { pipNewCfgTableEntry 1 }
    
pipNewCfgPortMap    OBJECT-TYPE
    SYNTAX  OCTET STRING (SIZE(0..8))
    MAX-ACCESS  read-only
    STATUS  current
    DESCRIPTION
        "The bit map of port for PIP.
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port."
 
    ::= { pipNewCfgTableEntry 2 }
    
pipNewCfgVlanMap    OBJECT-TYPE
    SYNTAX  OCTET STRING (SIZE(0..512))
    MAX-ACCESS  read-only
    STATUS  current
    DESCRIPTION
        "The bit map of VLAN for PIP.
         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN."
 
    ::= { pipNewCfgTableEntry 3 }

pipNewCfgDelete OBJECT-TYPE
    SYNTAX  INTEGER {
        other(1),
        delete(2)
        }
    MAX-ACCESS  read-create
    STATUS  current
    DESCRIPTION
        "By setting the value to delete(2), the entire row is deleted."
    ::= { pipNewCfgTableEntry 4 }

pipNewCfgAddPortVlan OBJECT-TYPE
    SYNTAX  Integer32
    MAX-ACCESS  read-create
    STATUS  current
    DESCRIPTION
        "The Port or VLAN to be associated with the PIP. When read, 0 is returned."
    ::= { pipNewCfgTableEntry 5 }

pipNewCfgRemovePortVlan OBJECT-TYPE 
    SYNTAX  Integer32 
    MAX-ACCESS  read-create 
    STATUS  current
    DESCRIPTION
        "The Port or VLAN to be disassociated from the PIP. When read, 
         0 is returned."
    ::= { pipNewCfgTableEntry 6 }

-- SLB Statistics Group

-- SLB SP Real Servers Statistics Table

slbStatSpRealServerTable OBJECT-TYPE
    SYNTAX  SEQUENCE OF SlbStatSpRealServerEntry
    MAX-ACCESS  not-accessible
    STATUS  current
    DESCRIPTION
        "The sp-server statistics table.  This table shows the statistics 
         of real servers for a particular SP."
    ::= { slbSpStats 1 }

slbStatSpRealServerEntry OBJECT-TYPE
    SYNTAX  SlbStatSpRealServerEntry
    MAX-ACCESS  not-accessible
    STATUS  current
    DESCRIPTION
        "A row in the sp-server statistics table."
    INDEX  { slbStatSpRealServerSpIndex, slbStatSpRealServerServerIndex }
    ::= { slbStatSpRealServerTable 1 }

SlbStatSpRealServerEntry ::= SEQUENCE {
    slbStatSpRealServerSpIndex               Integer32,
    slbStatSpRealServerServerIndex           Integer32,
    slbStatSpRealServerCurrSessions          Gauge32,
    slbStatSpRealServerTotalSessions         Counter32,
    slbStatSpRealServerHCOctetsLow32         Counter32,
    slbStatSpRealServerHCOctetsHigh32        Counter32,
    slbStatSpRealServerHCOctets              Counter64
    }

slbStatSpRealServerSpIndex OBJECT-TYPE
    SYNTAX  Integer32
    MAX-ACCESS  read-only
    STATUS  current
    DESCRIPTION
        "The SP index."
    ::= { slbStatSpRealServerEntry 1 }

slbStatSpRealServerServerIndex OBJECT-TYPE 
    SYNTAX  Integer32 
    MAX-ACCESS  read-only
    STATUS  current 
    DESCRIPTION 
        "The real server number that identifies the server." 
    ::= { slbStatSpRealServerEntry 2 }

slbStatSpRealServerCurrSessions OBJECT-TYPE 
    SYNTAX  Gauge32
    MAX-ACCESS  read-only
    STATUS  current 
    DESCRIPTION 
        "The current sessions for the real server."
    ::= { slbStatSpRealServerEntry 3 }

slbStatSpRealServerTotalSessions OBJECT-TYPE 
    SYNTAX  Counter32 
    MAX-ACCESS  read-only
    STATUS  current 
    DESCRIPTION 
        "The total number of sessions for the real server."
    ::= { slbStatSpRealServerEntry 4 }

slbStatSpRealServerHCOctetsLow32 OBJECT-TYPE
    SYNTAX  Counter32
    MAX-ACCESS  read-only
    STATUS  current
    DESCRIPTION
        "The lower 32 bit value of the total octets received and transmitted 
         out of the real server on a particular SP."
    ::= { slbStatSpRealServerEntry 5 }

slbStatSpRealServerHCOctetsHigh32 OBJECT-TYPE
    SYNTAX  Counter32
    MAX-ACCESS  read-only
    STATUS  current
    DESCRIPTION
        "The higher 32 bit value of the total octets received and transmitted 
         out of the real server on a particular SP."
    ::= { slbStatSpRealServerEntry 6 }

slbStatSpRealServerHCOctets OBJECT-TYPE
    SYNTAX  Counter64
    MAX-ACCESS  read-only
    STATUS  current
    DESCRIPTION
        "The total octets received and transmitted by the real server on a 
         particular SP."
    ::= { slbStatSpRealServerEntry 7 }

slbStatSpFltTable OBJECT-TYPE
    SYNTAX  SEQUENCE OF SlbStatSpFltEntry
    MAX-ACCESS  not-accessible
    STATUS  current
    DESCRIPTION
        "The filter statistics table.  This table shows the statistics 
         of filters for a particular SP."
    ::= { slbSpStats 4 }

slbStatSpFltEntry OBJECT-TYPE
    SYNTAX  SlbStatSpFltEntry
    MAX-ACCESS  not-accessible
    STATUS  current
    DESCRIPTION
        "A row in the filter statistics table."
    INDEX  { slbStatSpFltSpIndex, slbStatSpFltIndex }
    ::= { slbStatSpFltTable 1 }

SlbStatSpFltEntry ::= SEQUENCE {
    slbStatSpFltSpIndex               Integer32,
    slbStatSpFltIndex                 Integer32,
    slbStatSpFltFirings               Counter32
    }

slbStatSpFltSpIndex OBJECT-TYPE
    SYNTAX  Integer32
    MAX-ACCESS  read-only
    STATUS  current
    DESCRIPTION
        "The SP index."
    ::= { slbStatSpFltEntry 1 }

slbStatSpFltIndex OBJECT-TYPE 
    SYNTAX  Integer32 
    MAX-ACCESS  read-only
    STATUS  current 
    DESCRIPTION 
        "The filter number." 
    ::= { slbStatSpFltEntry 2 }

slbStatSpFltFirings OBJECT-TYPE 
    SYNTAX  Counter32 
    MAX-ACCESS  read-only
    STATUS  current 
    DESCRIPTION 
        "The number of instances that the received packet matches the 
         filter rule on this SP."
    ::= { slbStatSpFltEntry 3 }

-- SLB Port Maintenance Statistics Table

slbStatSpMaintTable OBJECT-TYPE
    SYNTAX  SEQUENCE OF SlbStatSpMaintEntry
    MAX-ACCESS  not-accessible
    STATUS  current
    DESCRIPTION
        "The table of SLB SP maintenance statistics." 
    ::= { slbSpStats 5 }

slbStatSpMaintEntry OBJECT-TYPE
    SYNTAX  SlbStatSpMaintEntry
    MAX-ACCESS  not-accessible
    STATUS  current
    DESCRIPTION
        "A row in the SLB SP maintenance statistics table."
    INDEX   { slbStatSpMaintSpIndex }
    ::= { slbStatSpMaintTable 1 }
 
SlbStatSpMaintEntry ::= SEQUENCE {
    slbStatSpMaintSpIndex                   Integer32,
    slbStatSpMaintMaximumSessions           Integer32,
    slbStatSpMaintCurBindings               Gauge32,
    slbStatSpMaintCurBindings4Seconds       Gauge32,
    slbStatSpMaintCurBindings64Seconds      Gauge32,
    slbStatSpMaintTerminatedSessions        Counter32,
    slbStatSpMaintBindingFails              Counter32,
    slbStatSpMaintNonTcpFrames              Counter32,
    slbStatSpMaintTcpFragments              Counter32,
    slbStatSpMaintUdpDatagrams              Counter32,
    slbStatSpMaintIncorrectVIPs             Counter32,
    slbStatSpMaintIncorrectVports           Counter32,
    slbStatSpMaintRealServerNoAvails        Counter32,
    slbStatSpMaintFilteredDeniedFrames      Counter32,
    slbStatSpMaintLandAttacks		    Counter32,
    slbStatSpMaintIpFragTotalSessions	    Counter32,
    slbStatSpMaintIpFragCurSessions         Gauge32,
    slbStatSpMaintIpFragDiscards            Counter32,
    slbStatSpMaintIpFragTableFull           Counter32,
    slbStatSpMaintClear                     INTEGER,
    slbStatSpMaintOOSFinPktDrops            Counter32,
    slbStatSpMaintSymSessions		    Counter32,
    slbStatSpMaintSymValidSegments	    Counter32,
    slbStatSpMaintSymFragSessions	    Counter32,
    slbStatSpMaintSymSegAllocFails	    Counter32,
    slbStatSpMaintSymBufferAllocFails	    Counter32,	
    slbStatSpMaintSymConnAllocFails	    Counter32,
    slbStatSpMaintSymInvalidBuffers	    Counter32,
    slbStatSpMaintSymSegReallocFails	    Counter32,
    slbStatSpMaintSymPacketsIn		    Counter32,
    slbStatSpMaintSymPacketsWithNoData	    Counter32,
    slbStatSpMaintSymTcpPackets		    Counter32,
    slbStatSpMaintSymUdpPackets	            Counter32,
    slbStatSpMaintSymIcmpPackets	    Counter32,
    slbStatSpMaintSymOtherPackets	    Counter32,
    slbStatSpMaintSymMatchCount		    Counter32,
    slbStatSpMaintSymFetchErrors	    Counter32,
    slbStatSpMaintSymTruncPayloadToMp	    Counter32,
    slbStatSpMaintSymPacketsInFastPath	    Counter32
    }

slbStatSpMaintSpIndex OBJECT-TYPE
    SYNTAX  Integer32
    MAX-ACCESS  read-only
    STATUS  current
    DESCRIPTION
        "The SP number for which the statistics apply."
    ::= { slbStatSpMaintEntry 1 }

slbStatSpMaintMaximumSessions OBJECT-TYPE
    SYNTAX  Integer32
    MAX-ACCESS  read-only
    STATUS  current
    DESCRIPTION
        "The maximun number of entries per SP in the session table."
    ::= { slbStatSpMaintEntry 2 }

slbStatSpMaintCurBindings OBJECT-TYPE
    SYNTAX  Gauge32 
    MAX-ACCESS  read-only
    STATUS  current
    DESCRIPTION
        "The current number of sessions on the SP."
    ::= { slbStatSpMaintEntry 3 }

slbStatSpMaintCurBindings4Seconds OBJECT-TYPE
    SYNTAX  Gauge32 
    MAX-ACCESS  read-only
    STATUS  current
    DESCRIPTION
        "The 4 second average current number of sessions on the SP."
    ::= { slbStatSpMaintEntry 4 }

slbStatSpMaintCurBindings64Seconds OBJECT-TYPE
    SYNTAX  Gauge32 
    MAX-ACCESS  read-only
    STATUS  current
    DESCRIPTION
        "The 64 second average current number of sessions on the SP."
    ::= { slbStatSpMaintEntry 5 }

slbStatSpMaintTerminatedSessions OBJECT-TYPE
    SYNTAX  Counter32
    MAX-ACCESS  read-only
    STATUS  current
    DESCRIPTION
        "The count of the number of sessions closed because the server failed."
    ::= { slbStatSpMaintEntry 6 }

slbStatSpMaintBindingFails OBJECT-TYPE
    SYNTAX  Counter32
    MAX-ACCESS  read-only
    STATUS  current
    DESCRIPTION
        "The total number of binding failures on the SP. A binding failure 
         occurs when a SP runs out of session table entries."
    ::= { slbStatSpMaintEntry 7 }

slbStatSpMaintNonTcpFrames OBJECT-TYPE
    SYNTAX  Counter32
    MAX-ACCESS  read-only
    STATUS  current
    DESCRIPTION
        "The total number of non-TCP/IP frames dropped on the SP."
    ::= { slbStatSpMaintEntry 8 }

slbStatSpMaintTcpFragments OBJECT-TYPE
    SYNTAX  Counter32
    MAX-ACCESS  read-only
    STATUS  obsolete
    DESCRIPTION
        "The total number of TCP fragments dropped on the SP."
    ::= { slbStatSpMaintEntry 9 }

slbStatSpMaintUdpDatagrams OBJECT-TYPE
    SYNTAX  Counter32
    MAX-ACCESS  read-only
    STATUS  current
    DESCRIPTION
        "The total number of UDP datagrams dropped on the SP."
    ::= { slbStatSpMaintEntry 10 }

slbStatSpMaintIncorrectVIPs OBJECT-TYPE
    SYNTAX  Counter32
    MAX-ACCESS  read-only
    STATUS  current
    DESCRIPTION
        "The total number of frames with incorrect VIPs that are dropped on 
         the SP."
    ::= { slbStatSpMaintEntry 11 }

slbStatSpMaintIncorrectVports OBJECT-TYPE
    SYNTAX  Counter32
    MAX-ACCESS  read-only
    STATUS  current
    DESCRIPTION
        "The total number of frames with incorrect Virtual Port that are 
         dropped on the SP."
    ::= { slbStatSpMaintEntry 12 }

slbStatSpMaintRealServerNoAvails OBJECT-TYPE
    SYNTAX  Counter32
    MAX-ACCESS  read-only
    STATUS  current
    DESCRIPTION
        "The total number of frames that are dropped on the SP
	 because no real server is available."
    ::= { slbStatSpMaintEntry 13 }

slbStatSpMaintFilteredDeniedFrames OBJECT-TYPE
    SYNTAX  Counter32
    MAX-ACCESS  read-only
    STATUS  current
    DESCRIPTION
        "The total number of frames that are denied on the SP by the filter."
    ::= { slbStatSpMaintEntry 14 }

slbStatSpMaintLandAttacks OBJECT-TYPE
    SYNTAX  Counter32
    MAX-ACCESS  read-only
    STATUS  current
    DESCRIPTION
        "The total number of attacks that frames contain the same source
	 and destination IP addresses."
    ::= { slbStatSpMaintEntry 15 }

slbStatSpMaintIpFragTotalSessions OBJECT-TYPE
    SYNTAX  Counter32
    MAX-ACCESS  read-only
    STATUS  current
    DESCRIPTION
        "The total number of fragment sessions processed on the SP."
    ::= { slbStatSpMaintEntry 16 }

slbStatSpMaintIpFragCurSessions OBJECT-TYPE
    SYNTAX  Gauge32
    MAX-ACCESS  read-only
    STATUS  current
    DESCRIPTION
        "The number of sessions in the IP fragment binding table on the SP."
    ::= { slbStatSpMaintEntry 17 }

slbStatSpMaintIpFragDiscards OBJECT-TYPE
    SYNTAX  Counter32
    MAX-ACCESS  read-only
    STATUS  current
    DESCRIPTION
        "The total number of fragments discarded on the SP because there
         is no entry in the IP fragment binding table. "
    ::= { slbStatSpMaintEntry 18 }

slbStatSpMaintIpFragTableFull OBJECT-TYPE
    SYNTAX  Counter32
    MAX-ACCESS  read-only
    STATUS  current
    DESCRIPTION
        "The total number of times IP fragment binding table is full on the 
         SP."
    ::= { slbStatSpMaintEntry 19 }

slbStatSpMaintClear OBJECT-TYPE
    SYNTAX INTEGER {
	ok(1),
	clear(2)
	}
    MAX-ACCESS read-write
    STATUS current
    DESCRIPTION
        "This is an action object to clear the non-operational SLB statistics
         on the particular SP. 
         ok(1) is returned when read."
    ::= { slbStatSpMaintEntry 20 }

slbStatSpMaintOOSFinPktDrops OBJECT-TYPE
    SYNTAX  Counter32
    MAX-ACCESS  read-only
    STATUS  current
    DESCRIPTION
        "The total number of Out of state FIN Packets received on the SP."
    ::= { slbStatSpMaintEntry 21 }

-- START of Symantec SLB SP Maintenance Stats 
slbStatSpMaintSymSessions OBJECT-TYPE
    SYNTAX  Counter32
    MAX-ACCESS  read-only
    STATUS  current
    DESCRIPTION
        "Number of Symantec sessions."
    ::= { slbStatSpMaintEntry 22 }

slbStatSpMaintSymValidSegments OBJECT-TYPE
    SYNTAX  Counter32
    MAX-ACCESS  read-only
    STATUS  current
    DESCRIPTION
        "Number of Symantec valid segments."
    ::= { slbStatSpMaintEntry 23 }

slbStatSpMaintSymFragSessions OBJECT-TYPE
    SYNTAX  Counter32
    MAX-ACCESS  read-only
    STATUS  current
    DESCRIPTION
        "Number of Symantec fragment sessions."
    ::= { slbStatSpMaintEntry 24 }

slbStatSpMaintSymSegAllocFails OBJECT-TYPE
    SYNTAX  Counter32
    MAX-ACCESS  read-only
    STATUS  current
    DESCRIPTION
        "Number of Symantec segment allocation fails."
    ::= { slbStatSpMaintEntry 25 }

slbStatSpMaintSymBufferAllocFails OBJECT-TYPE
    SYNTAX  Counter32
    MAX-ACCESS  read-only
    STATUS  current
    DESCRIPTION
        "Number of Symantec buffers allocation fails."
    ::= { slbStatSpMaintEntry 26 }

slbStatSpMaintSymConnAllocFails OBJECT-TYPE
    SYNTAX  Counter32
    MAX-ACCESS  read-only
    STATUS  current
    DESCRIPTION
        "Number of Symantec Connection allocation fails."
    ::= { slbStatSpMaintEntry 27 }

slbStatSpMaintSymInvalidBuffers OBJECT-TYPE
    SYNTAX  Counter32
    MAX-ACCESS  read-only
    STATUS  current
    DESCRIPTION
        "Number of Symantec Invalid buffers."
    ::= { slbStatSpMaintEntry 28 }

slbStatSpMaintSymSegReallocFails OBJECT-TYPE
    SYNTAX  Counter32
    MAX-ACCESS  read-only
    STATUS  current
    DESCRIPTION
        "Number of Symantec Segment reallocation fails."
    ::= { slbStatSpMaintEntry 29 }

slbStatSpMaintSymPacketsIn OBJECT-TYPE
    SYNTAX  Counter32
    MAX-ACCESS  read-only
    STATUS  current
    DESCRIPTION
        "Symantec Deuce Inspection Stats - No. of packets in."
    ::= { slbStatSpMaintEntry 30 }

slbStatSpMaintSymPacketsWithNoData OBJECT-TYPE
    SYNTAX  Counter32
    MAX-ACCESS  read-only
    STATUS  current
    DESCRIPTION
        "Symantec Deuce Inspection Stats - No. of packets with no data."
    ::= { slbStatSpMaintEntry 31 }

slbStatSpMaintSymTcpPackets OBJECT-TYPE
    SYNTAX  Counter32
    MAX-ACCESS  read-only
    STATUS  current
    DESCRIPTION
        "Symantec Deuce Inspection Stats - No. of TCP packets"
    ::= { slbStatSpMaintEntry 32 }

slbStatSpMaintSymUdpPackets OBJECT-TYPE
    SYNTAX  Counter32
    MAX-ACCESS  read-only
    STATUS  current
    DESCRIPTION
        "Symantec Deuce Inspection Stats - No. of  UDP Packets"
    ::= { slbStatSpMaintEntry 33 }

slbStatSpMaintSymIcmpPackets OBJECT-TYPE
    SYNTAX  Counter32
    MAX-ACCESS  read-only
    STATUS  current
    DESCRIPTION
        "Symantec Deuce Inspection Stats - No. of  ICMP Packets"
    ::= { slbStatSpMaintEntry 34 }

slbStatSpMaintSymOtherPackets OBJECT-TYPE
    SYNTAX  Counter32
    MAX-ACCESS  read-only
    STATUS  current
    DESCRIPTION
        "Symantec Deuce Inspection Stats - No. of  Packets other than 
	 TCP UDP or ICMP"
    ::= { slbStatSpMaintEntry 35 }

slbStatSpMaintSymMatchCount OBJECT-TYPE
    SYNTAX  Counter32
    MAX-ACCESS  read-only
    STATUS  current
    DESCRIPTION
        "Symantec Deuce Inspection Stats - Match Count"
    ::= { slbStatSpMaintEntry 36 }

slbStatSpMaintSymFetchErrors OBJECT-TYPE
    SYNTAX  Counter32
    MAX-ACCESS  read-only
    STATUS  current
    DESCRIPTION
        "Symantec Deuce Inspection Stats - No. of Fetch Errors"
    ::= { slbStatSpMaintEntry 37 }

slbStatSpMaintSymTruncPayloadToMp OBJECT-TYPE
    SYNTAX  Counter32
    MAX-ACCESS  read-only
    STATUS  current
    DESCRIPTION
        "Symantec Deuce Inspection Stats - No. of Truncated payload to MP"
    ::= { slbStatSpMaintEntry 38 }

slbStatSpMaintSymPacketsInFastPath OBJECT-TYPE
    SYNTAX  Counter32
    MAX-ACCESS  read-only
    STATUS  current
    DESCRIPTION
        "Symantec Deuce Inspection Stats - No. of Packets in fast path"
    ::= { slbStatSpMaintEntry 39 }

-- END of Symantec SLB SP Maintenance Stats 

slbStatSpAuxSessTable OBJECT-TYPE
    SYNTAX  SEQUENCE OF SlbStatSpAuxSessEntry
    MAX-ACCESS  not-accessible
    STATUS  current
    DESCRIPTION
        "The auxiliary session table statistics for a particular SP."
    ::= { slbSpStats 6 }

slbStatSpAuxSessEntry OBJECT-TYPE
    SYNTAX  SlbStatSpAuxSessEntry
    MAX-ACCESS  not-accessible
    STATUS  current
    DESCRIPTION
        "The statistics of a particular auxiliary session table entry."
    INDEX   { slbStatSpAuxSessSpIndex, slbStatSpAuxSessIndex }
    ::= { slbStatSpAuxSessTable 1 }

SlbStatSpAuxSessEntry ::= SEQUENCE {
    slbStatSpAuxSessSpIndex             Integer32,
    slbStatSpAuxSessIndex               Integer32,
    slbStatSpAuxSessCurConn             Gauge32,
    slbStatSpAuxSessMaxConn             Integer32,
    slbStatSpAuxSessAllocFails          Counter32
    }

slbStatSpAuxSessSpIndex OBJECT-TYPE
    SYNTAX  Integer32
    MAX-ACCESS  read-only
    STATUS  current
    DESCRIPTION
        "The SP number." 
    ::= { slbStatSpAuxSessEntry 1 }

slbStatSpAuxSessIndex OBJECT-TYPE
    SYNTAX  Integer32
    MAX-ACCESS  read-only
    STATUS  current
    DESCRIPTION
        "The auxiliary session table number." 
    ::= { slbStatSpAuxSessEntry 2 }

slbStatSpAuxSessCurConn OBJECT-TYPE 
    SYNTAX  Gauge32
    MAX-ACCESS  read-only
    STATUS  current 
    DESCRIPTION 
        "The number of connections in this auxiliary sessions table."
    ::= { slbStatSpAuxSessEntry 3 }

slbStatSpAuxSessMaxConn OBJECT-TYPE 
    SYNTAX  Integer32 
    MAX-ACCESS  read-only
    STATUS  current 
    DESCRIPTION 
        "The maximum number of connections handled by this auxiliary session 
         table."
    ::= { slbStatSpAuxSessEntry 4 }

slbStatSpAuxSessAllocFails OBJECT-TYPE 
    SYNTAX  Counter32 
    MAX-ACCESS  read-only
    STATUS  current 
    DESCRIPTION 
        "The total number of allocation failures for this auxiliary session 
         table."
    ::= { slbStatSpAuxSessEntry 5 }

-- SLB Real Servers Statistics Table

slbStatRServerTable OBJECT-TYPE
    SYNTAX  SEQUENCE OF SlbStatRServerEntry
    MAX-ACCESS  not-accessible
    STATUS  current
    DESCRIPTION
        "The real server statistics table."
    ::= { layer4Stats 2 }

slbStatRServerEntry OBJECT-TYPE
    SYNTAX  SlbStatRServerEntry
    MAX-ACCESS  not-accessible
    STATUS  current
    DESCRIPTION
        "The statistics of a particular real server."
    INDEX   { slbStatRServerIndex }
    ::= { slbStatRServerTable 1 }

SlbStatRServerEntry ::= SEQUENCE {
    slbStatRServerIndex               Integer32,
    slbStatRServerCurrSessions        Gauge32,
    slbStatRServerTotalSessions       Counter32,
    slbStatRServerFailures            Counter32,
    slbStatRServerHighestSessions     Counter32,
    slbStatRServerHCOctetsLow32       Counter32,
    slbStatRServerHCOctetsHigh32      Counter32,
    slbStatRServerHCOctets            Counter64
    }

slbStatRServerIndex OBJECT-TYPE
    SYNTAX  Integer32
    MAX-ACCESS  read-only
    STATUS  current
    DESCRIPTION
        "The real server number that identifies the server." 
    ::= { slbStatRServerEntry 1 }

slbStatRServerCurrSessions OBJECT-TYPE 
    SYNTAX  Gauge32
    MAX-ACCESS  read-only
    STATUS  current 
    DESCRIPTION 
        "The number of sessions that are currently handled by the real server."
    ::= { slbStatRServerEntry 2 }

slbStatRServerTotalSessions OBJECT-TYPE 
    SYNTAX  Counter32 
    MAX-ACCESS  read-only
    STATUS  current 
    DESCRIPTION 
        "The total number of sessions that are handled by the real server."
    ::= { slbStatRServerEntry 3 }

slbStatRServerFailures OBJECT-TYPE 
    SYNTAX  Counter32 
    MAX-ACCESS  read-only
    STATUS  current 
    DESCRIPTION 
        "The total number of times that the real server is claimed down."
    ::= { slbStatRServerEntry 4 }

slbStatRServerHighestSessions OBJECT-TYPE 
    SYNTAX  Counter32 
    MAX-ACCESS  read-only
    STATUS  current 
    DESCRIPTION 
        "The highest sessions that have been handled by the real server."
    ::= { slbStatRServerEntry 5 }

slbStatRServerHCOctetsLow32 OBJECT-TYPE
    SYNTAX  Counter32
    MAX-ACCESS  read-only
    STATUS  current
    DESCRIPTION
        "The lower 32 bit value of octets received and transmitted out of the 
         real server."
    ::= { slbStatRServerEntry 6 }

slbStatRServerHCOctetsHigh32 OBJECT-TYPE
    SYNTAX  Counter32
    MAX-ACCESS  read-only
    STATUS  current
    DESCRIPTION
        "The higher 32 bit value of octets received and transmitted out
         of the real server."
    ::= { slbStatRServerEntry 7 }

slbStatRServerHCOctets OBJECT-TYPE
    SYNTAX  Counter64
    MAX-ACCESS  read-only
    STATUS  current
    DESCRIPTION
        "The total number of octets received and transmitted by the real 
         server."
    ::= { slbStatRServerEntry 8 }

-- SLB Real Server Groups Statistics Table

slbStatGroupTable OBJECT-TYPE
    SYNTAX  SEQUENCE OF SlbStatGroupEntry
    MAX-ACCESS  not-accessible
    STATUS  current
    DESCRIPTION
        "The real server group statistics table."
    ::= { layer4Stats 3 }

slbStatGroupEntry OBJECT-TYPE
    SYNTAX  SlbStatGroupEntry
    MAX-ACCESS  not-accessible
    STATUS  current
    DESCRIPTION
        "The statistics of a particular real server group."
    INDEX   { slbStatGroupIndex }
    ::= { slbStatGroupTable 1 }

SlbStatGroupEntry ::= SEQUENCE {
    slbStatGroupIndex               Integer32,
    slbStatGroupCurrSessions        Gauge32,
    slbStatGroupTotalSessions       Counter32,
    slbStatGroupHighestSessions     Counter32,
    slbStatGroupHCOctetsLow32       Counter32,
    slbStatGroupHCOctetsHigh32      Counter32,
    slbStatGroupWlmUpdates          Counter32, 
    slbStatGroupHCOctets            Counter64
    }

slbStatGroupIndex OBJECT-TYPE
    SYNTAX  Integer32
    MAX-ACCESS  read-only
    STATUS  current
    DESCRIPTION
        "The real server group number that identifies the group." 
    ::= { slbStatGroupEntry 1 }

slbStatGroupCurrSessions OBJECT-TYPE 
    SYNTAX  Gauge32
    MAX-ACCESS  read-only
    STATUS  current 
    DESCRIPTION 
        "The number of sessions that are currently handled by the real server 
         group."
    ::= { slbStatGroupEntry 2 }

slbStatGroupTotalSessions OBJECT-TYPE 
    SYNTAX  Counter32 
    MAX-ACCESS  read-only
    STATUS  current 
    DESCRIPTION 
        "The total number of sessions that are handled by the real 
         server group."
    ::= { slbStatGroupEntry 3 }

slbStatGroupHighestSessions OBJECT-TYPE 
    SYNTAX  Counter32 
    MAX-ACCESS  read-only
    STATUS  current 
    DESCRIPTION 
        "The highest sessions that have been handled by the real server group."
    ::= { slbStatGroupEntry 4 }

slbStatGroupHCOctetsLow32 OBJECT-TYPE
    SYNTAX  Counter32
    MAX-ACCESS  read-only
    STATUS  current
    DESCRIPTION
        "The lower 32 bit value of octets received and transmitted out of the 
         real server group."
    ::= { slbStatGroupEntry 5 }

slbStatGroupHCOctetsHigh32 OBJECT-TYPE
    SYNTAX  Counter32
    MAX-ACCESS  read-only
    STATUS  current
    DESCRIPTION
        "The higher 32 bit value of octets received and transmitted out
         of the real server group."
    ::= { slbStatGroupEntry 6 }

slbStatGroupHCOctets OBJECT-TYPE
    SYNTAX  Counter64
    MAX-ACCESS  read-only
    STATUS  current
    DESCRIPTION
        "The total octets received and transmitted by the real server group."
    ::= { slbStatGroupEntry 7 }

slbStatGroupWlmUpdates OBJECT-TYPE
    SYNTAX  Counter32
    MAX-ACCESS  read-only
    STATUS  current
    DESCRIPTION
        "Total weight updates from work load manager."
    ::= { slbStatGroupEntry 8 } 

-- SLB Virtual Server Statistics Table

slbStatVServerTable OBJECT-TYPE
    SYNTAX  SEQUENCE OF SlbStatVServerEntry
    MAX-ACCESS  not-accessible
    STATUS  current
    DESCRIPTION
        "The virtual server statistics table."
    ::= { layer4Stats 4 }

slbStatVServerEntry OBJECT-TYPE
    SYNTAX  SlbStatVServerEntry
    MAX-ACCESS  not-accessible
    STATUS  current
    DESCRIPTION
        "The statistics of a particular virtual server group."
    INDEX   { slbStatVServerIndex }
    ::= { slbStatVServerTable 1 }

SlbStatVServerEntry ::= SEQUENCE {
    slbStatVServerIndex                   Integer32,
    slbStatVServerCurrSessions            Gauge32,
    slbStatVServerTotalSessions           Counter32,
    slbStatVServerHighestSessions         Counter32,
    slbStatVServerHCOctetsLow32           Counter32,
    slbStatVServerHCOctetsHigh32          Counter32,
    slbStatVServerHeaderHits              Counter32,
    slbStatVServerHeaderMisses            Counter32,
    slbStatVServerHeaderTotalSessions     Counter32,
    slbStatVServerCookieRewrites          Counter32,
    slbStatVServerCookieInserts           Counter32,
    slbStatVServerHCOctets                Counter64,
    slbStatVServerIpAddress               DisplayString 
    }

slbStatVServerIndex OBJECT-TYPE
    SYNTAX  Integer32
    MAX-ACCESS  read-only
    STATUS  current
    DESCRIPTION
        "The virtual server number that identifies the server." 
    ::= { slbStatVServerEntry 1 }

slbStatVServerCurrSessions OBJECT-TYPE 
    SYNTAX  Gauge32
    MAX-ACCESS  read-only
    STATUS  current 
    DESCRIPTION 
        "The number of sessions that are currently handled by the 
         virtual server."
    ::= { slbStatVServerEntry 2 }

slbStatVServerTotalSessions OBJECT-TYPE 
    SYNTAX  Counter32 
    MAX-ACCESS  read-only
    STATUS  current 
    DESCRIPTION 
        "The total number of sessions that are handled by the virtual server."
    ::= { slbStatVServerEntry 3 }

slbStatVServerHighestSessions OBJECT-TYPE 
    SYNTAX  Counter32 
    MAX-ACCESS  read-only
    STATUS  current 
    DESCRIPTION 
        "The highest sessions that have been handled by the virtual server."
    ::= { slbStatVServerEntry 4 }

slbStatVServerHCOctetsLow32 OBJECT-TYPE
    SYNTAX  Counter32
    MAX-ACCESS  read-only
    STATUS  current
    DESCRIPTION
        "The lower 32 bit value of octets received and transmitted out
         of the virtual server."
    ::= { slbStatVServerEntry 5 }

slbStatVServerHCOctetsHigh32 OBJECT-TYPE
    SYNTAX  Counter32
    MAX-ACCESS  read-only
    STATUS  current
    DESCRIPTION
        "The higher 32 bit value of octets received and transmitted out
         of the virtual server."
    ::= { slbStatVServerEntry 6 }


--  HTTP Header LB stats 
slbStatVServerHeaderHits OBJECT-TYPE 
    SYNTAX  Counter32 
    MAX-ACCESS  read-only
    STATUS  current 
    DESCRIPTION 
        "The current HTTP header hits." 
    ::= { slbStatVServerEntry 8 }

slbStatVServerHeaderMisses OBJECT-TYPE 
    SYNTAX  Counter32 
    MAX-ACCESS  read-only
    STATUS  current 
    DESCRIPTION 
        "The current HTTP header misses."  
    ::= { slbStatVServerEntry 9 }

slbStatVServerHeaderTotalSessions OBJECT-TYPE 
    SYNTAX  Counter32 
    MAX-ACCESS  read-only
    STATUS  current 
    DESCRIPTION 
        "The total HTTP header sessions."
    ::= { slbStatVServerEntry 10 }

-- Cookie Statistics 
slbStatVServerCookieRewrites OBJECT-TYPE 
    SYNTAX  Counter32 
    MAX-ACCESS  read-only
    STATUS  current 
    DESCRIPTION 
        "The total Cookie Rewrites."
    ::= { slbStatVServerEntry 11 }

slbStatVServerCookieInserts OBJECT-TYPE 
    SYNTAX  Counter32 
    MAX-ACCESS  read-only
    STATUS  current 
    DESCRIPTION 
        "The total Cookie Inserts."
    ::= { slbStatVServerEntry 12 }

slbStatVServerHCOctets OBJECT-TYPE
    SYNTAX  Counter64
    MAX-ACCESS  read-only
    STATUS  current
    DESCRIPTION
        "The total octets received and transmitted by the virtual server."
    ::= { slbStatVServerEntry 13 }

slbStatVServerIpAddress   OBJECT-TYPE
    SYNTAX  DisplayString 
    MAX-ACCESS  read-only 
    STATUS  current
    DESCRIPTION
        "IP address of the virtual server." 
    ::= { slbStatVServerEntry  14 }

-- SLB Maintenance Statistics 

slbStatMaintMaximumSessions OBJECT-TYPE
    SYNTAX  Integer32
    MAX-ACCESS  read-only
    STATUS  current
    DESCRIPTION
        "The maximun number entries in the session table."
    ::= { slbMaintStats 1 }

slbStatMaintCurBindings OBJECT-TYPE
    SYNTAX  Gauge32 
    MAX-ACCESS  read-only
    STATUS  current
    DESCRIPTION
        "The current number of bindings on the port."
    ::= { slbMaintStats 2 }

slbStatMaintCurBindings4Seconds OBJECT-TYPE
    SYNTAX  Gauge32 
    MAX-ACCESS  read-only
    STATUS  current
    DESCRIPTION
        "The 4 second average current number of bindings on the port."
    ::= { slbMaintStats 3 }

slbStatMaintCurBindings64Seconds OBJECT-TYPE
    SYNTAX  Gauge32 
    MAX-ACCESS  read-only
    STATUS  current
    DESCRIPTION
        "The 64 second average current number of bindings on the port."
    ::= { slbMaintStats 4 }

slbStatMaintTerminatedSessions OBJECT-TYPE
    SYNTAX  Counter32
    MAX-ACCESS  read-only
    STATUS  current
    DESCRIPTION
        "The count of the number of sessions closed because the server failed."
    ::= { slbMaintStats 5 }

slbStatMaintAllocFailures OBJECT-TYPE
    SYNTAX  Counter32
    MAX-ACCESS  read-only
    STATUS  current
    DESCRIPTION
        "The total number of Binding failures on the port. A Binding Failure 
         occurs when a port runs out of binding table entries."
    ::= { slbMaintStats 6 }

slbStatMaintNonTcpFrames OBJECT-TYPE
    SYNTAX  Counter32
    MAX-ACCESS  read-only
    STATUS  current
    DESCRIPTION
        "The total number of non-TCP/IP frames dropped on the port."
    ::= { slbMaintStats 7 }

slbStatMaintTcpFragments OBJECT-TYPE
    SYNTAX  Counter32
    MAX-ACCESS  read-only
    STATUS  current
    DESCRIPTION
        "The total number of TCP fragments dropped on the port."
    ::= { slbMaintStats 8 }

slbStatMaintUdpDatagrams OBJECT-TYPE
    SYNTAX  Counter32
    MAX-ACCESS  read-only
    STATUS  current
    DESCRIPTION
        "The total number of UDP datagrams dropped on the port."
    ::= { slbMaintStats 9 }

slbIncorrectVirtServs OBJECT-TYPE 
    SYNTAX  Counter32 
    MAX-ACCESS  read-only
    STATUS  current 
    DESCRIPTION 
        "Incorrect Virtual Servers specified for Server Load Balancing."
    ::= { slbMaintStats  10}

slbIncorrectVports OBJECT-TYPE 
    SYNTAX  Counter32  
    MAX-ACCESS  read-only
    STATUS  current 
    DESCRIPTION 
        "Incorrect Virtual ports specified for Server Load Balancing."
    ::= { slbMaintStats 11 }

slbNoRealServs OBJECT-TYPE 
    SYNTAX  Counter32  
    MAX-ACCESS  read-only
    STATUS  current 
    DESCRIPTION 
        "No Real Servers available for Server Load Balancing."
    ::= { slbMaintStats 12 }

slbStatMaintBackupServActs OBJECT-TYPE
    SYNTAX  Counter32
    MAX-ACCESS  read-only
    STATUS  current
    DESCRIPTION
        "The total number of times that backup servers become active due 
         to failure of primary servers."
    ::= { slbMaintStats 13 }

slbStatMaintOverflowServActs OBJECT-TYPE
    SYNTAX  Counter32
    MAX-ACCESS  read-only
    STATUS  current
    DESCRIPTION
        "The total number of times that backup servers become
	 active due to primary servers reach overflow situation."
    ::= { slbMaintStats 14 }

slbStatMaintFilteredDeniedFrames OBJECT-TYPE
    SYNTAX  Counter32
    MAX-ACCESS  read-only
    STATUS  current
    DESCRIPTION
        "The total number of frames that are denied on the port by the filter."
    ::= { slbMaintStats 15 }

slbStatMaintLandAttacks OBJECT-TYPE
    SYNTAX  Counter32
    MAX-ACCESS  read-only
    STATUS  current
    DESCRIPTION
        "The total number of attacks that frames contain the same source
	 and destination IP addresses."
    ::= { slbMaintStats 16 }

slbStatMaintIpFragTotalSessions OBJECT-TYPE
    SYNTAX  Counter32
    MAX-ACCESS  read-only
    STATUS  current
    DESCRIPTION
        "The total number of fragment sessions processed."
    ::= { slbMaintStats 17 }

slbStatMaintIpFragCurSessions OBJECT-TYPE
    SYNTAX  Gauge32
    MAX-ACCESS  read-only
    STATUS  current
    DESCRIPTION
        "The number of sessions in the IP fragment binding table."
    ::= { slbMaintStats 18 }

slbStatMaintIpFragDiscards OBJECT-TYPE
    SYNTAX  Counter32
    MAX-ACCESS  read-only
    STATUS  current
    DESCRIPTION
        "The total number of fragmemts discarded on the SP because there
         is no entry in the IP fragment binding table. "
    ::= { slbMaintStats 19 }

slbStatMaintIpFragTableFull OBJECT-TYPE
    SYNTAX  Counter32
    MAX-ACCESS  read-only
    STATUS  current
    DESCRIPTION
        "The total number times IP fragment binding table is full on the SP."
    ::= { slbMaintStats 20 }

slbStatMaintIp6CurrSessions OBJECT-TYPE
    SYNTAX  Counter32
    MAX-ACCESS  read-only
    STATUS  current
    DESCRIPTION
        "The number of sessions  for ipv6."
    ::= { slbMaintStats 21 }

slbIncorrectIp6Vip  OBJECT-TYPE 
    SYNTAX  Counter32 
    MAX-ACCESS  read-only
    STATUS  current 
    DESCRIPTION 
        "Incorrect Ip6 VIPs specified for server load balancing."
    ::= { slbMaintStats  22}

slbIncorrectIp6Vports OBJECT-TYPE 
    SYNTAX  Counter32  
    MAX-ACCESS  read-only
    STATUS  current 
    DESCRIPTION 
        "Incorrect Ip6 virtual ports specified for server load balancing."
    ::= { slbMaintStats 23 }

slbStatMaintIp6PktDropped OBJECT-TYPE
    SYNTAX  Counter32
    MAX-ACCESS  read-only
    STATUS  current
    DESCRIPTION
        "The total number of Ip6 pacekets dropped."
    ::= { slbMaintStats 24 }


slbStatMaintOOSFinPktDrops OBJECT-TYPE
    SYNTAX  Counter32
    MAX-ACCESS  read-only
    STATUS  current
    DESCRIPTION
        "The total number Out of state FIN Packet drops."
    ::= { slbMaintStats 25 }

-- START of Symantec SLB Maintenance Stats
slbStatMaintSymSessions OBJECT-TYPE
    SYNTAX  Counter32
    MAX-ACCESS  read-only
    STATUS  current
    DESCRIPTION
        "Total number of Symantec sessions."
    ::= { slbMaintStats 26 }

slbStatMaintSymValidSegments OBJECT-TYPE
    SYNTAX  Counter32
    MAX-ACCESS  read-only
    STATUS  current
    DESCRIPTION
        "Total number of Symantec valid segments."
    ::= { slbMaintStats 27 }

slbStatMaintSymFragSessions OBJECT-TYPE
    SYNTAX  Counter32
    MAX-ACCESS  read-only
    STATUS  current
    DESCRIPTION
        "Total number of Symantec fragment sessions."
    ::= { slbMaintStats 28 }

slbStatMaintSymSegAllocFails OBJECT-TYPE
    SYNTAX  Counter32
    MAX-ACCESS  read-only
    STATUS  current
    DESCRIPTION
        "Total number of Symantec segment allocation fails."
    ::= { slbMaintStats 29 }

slbStatMaintSymBufferAllocFails OBJECT-TYPE
    SYNTAX  Counter32
    MAX-ACCESS  read-only
    STATUS  current
    DESCRIPTION
        "Total number of Symantec buffers allocation fails."
    ::= { slbMaintStats 30 }

slbStatMaintSymConnAllocFails OBJECT-TYPE
    SYNTAX  Counter32
    MAX-ACCESS  read-only
    STATUS  current
    DESCRIPTION
        "Total number of Symantec Connection allocation fails."
    ::= { slbMaintStats 31 }

slbStatMaintSymInvalidBuffers OBJECT-TYPE
    SYNTAX  Counter32
    MAX-ACCESS  read-only
    STATUS  current
    DESCRIPTION
        "Total number of Symantec Invalid buffers."
    ::= { slbMaintStats 32 }

slbStatMaintSymSegReallocFails OBJECT-TYPE
    SYNTAX  Counter32
    MAX-ACCESS  read-only
    STATUS  current
    DESCRIPTION
        "Total number of Symantec Segment reallocation fails."
    ::= { slbMaintStats 33 }

slbStatMaintSymPacketsIn OBJECT-TYPE
    SYNTAX  Counter32
    MAX-ACCESS  read-only
    STATUS  current
    DESCRIPTION
        "Symantec Deuce Inspection Stats - Total no. of Packets in."
    ::= { slbMaintStats 34 }

slbStatMaintSymPacketsWithNoData OBJECT-TYPE
    SYNTAX  Counter32
    MAX-ACCESS  read-only
    STATUS  current
    DESCRIPTION
        "Symantec Deuce Inspection Stats - Total no. of Packets with no data."
    ::= { slbMaintStats 35 }

slbStatMaintSymTcpPackets OBJECT-TYPE
    SYNTAX  Counter32
    MAX-ACCESS  read-only
    STATUS  current
    DESCRIPTION
        "Symantec Deuce Inspection Stats - Total no. of TCP packets"
    ::= { slbMaintStats 36 }

slbStatMaintSymUdpPackets OBJECT-TYPE
    SYNTAX  Counter32
    MAX-ACCESS  read-only
    STATUS  current
    DESCRIPTION
        "Symantec Deuce Inspection Stats - Total no. of UDP Packets"
    ::= { slbMaintStats 37 }

slbStatMaintSymIcmpPackets OBJECT-TYPE
    SYNTAX  Counter32
    MAX-ACCESS  read-only
    STATUS  current
    DESCRIPTION
        "Symantec Deuce Inspection Stats - Total no. of ICMP Packets"
    ::= { slbMaintStats 38 }

slbStatMaintSymOtherPackets OBJECT-TYPE
    SYNTAX  Counter32
    MAX-ACCESS  read-only
    STATUS  current
    DESCRIPTION
        "Symantec Deuce Inspection Stats - Total no. of Packets 
	 other than TCP UDP or ICMP"
    ::= { slbMaintStats 39 }

slbStatMaintSymMatchCount OBJECT-TYPE
    SYNTAX  Counter32
    MAX-ACCESS  read-only
    STATUS  current
    DESCRIPTION
        "Symantec Deuce Inspection Stats - Total Match Count"
    ::= { slbMaintStats 40 }

slbStatMaintSymFetchErrors OBJECT-TYPE
    SYNTAX  Counter32
    MAX-ACCESS  read-only
    STATUS  current
    DESCRIPTION
        "Symantec Deuce Inspection Stats - Total no. of Fetch Errors"
    ::= { slbMaintStats 41 }

slbStatMaintSymTruncPayloadToMp OBJECT-TYPE
    SYNTAX  Counter32
    MAX-ACCESS  read-only
    STATUS  current
    DESCRIPTION
        "Symantec Deuce Inspection Stats - Total no. of Truncated 
	 payload to MP"
    ::= { slbMaintStats 42 }

slbStatMaintSymPacketsInFastPath OBJECT-TYPE
    SYNTAX  Counter32
    MAX-ACCESS  read-only
    STATUS  current
    DESCRIPTION
        "Symantec Deuce Inspection Stats - Total no. of Packets in 
	 fast path"
    ::= { slbMaintStats 43 }

-- END of Symantec SLB Maintenance Stats 

-- Filter Statistics

fltStatTable OBJECT-TYPE
    SYNTAX  SEQUENCE OF FltStatTableEntry
    MAX-ACCESS  not-accessible
    STATUS  current
    DESCRIPTION
        "The filter statistics table."
    ::= { filterStats 1 }

fltStatTableEntry OBJECT-TYPE
    SYNTAX  FltStatTableEntry
    MAX-ACCESS  not-accessible
    STATUS  current
    DESCRIPTION
        "A row in filter statistics table."
    INDEX   { fltStatFltIndex }
    ::= { fltStatTable 1 }

FltStatTableEntry ::= SEQUENCE {
    fltStatFltIndex     Integer32,
    fltStatFltFirings	Counter32
    }

fltStatFltIndex OBJECT-TYPE 
    SYNTAX  Integer32 
    MAX-ACCESS  read-only
    STATUS  current 
    DESCRIPTION 
        "The number that identifies the filter." 
    ::= { fltStatTableEntry 1 }

fltStatFltFirings OBJECT-TYPE 
    SYNTAX  Counter32 
    MAX-ACCESS  read-only
    STATUS  current 
    DESCRIPTION 
        "The number of instances that the received packet matches the 
         filter rule."
    ::= { fltStatTableEntry 2 }

-- Global SLB Statitistics

-- Global SLB Remote Real Server Statistics

gslbStatRemRealServerTable OBJECT-TYPE
    SYNTAX  SEQUENCE OF GslbStatRemRealServerEntry
    MAX-ACCESS  not-accessible
    STATUS  current
    DESCRIPTION
        "The GSLB remote real server statistics table."
    ::= { gslbStats 1 }

gslbStatRemRealServerEntry OBJECT-TYPE
    SYNTAX  GslbStatRemRealServerEntry
    MAX-ACCESS  not-accessible
    STATUS  current
    DESCRIPTION
        "A row in the remote real server statistics table."
    INDEX   { gslbStatRemRealServerIndex }
    ::= { gslbStatRemRealServerTable 1 }

GslbStatRemRealServerEntry ::=	SEQUENCE {
    gslbStatRemRealServerIndex          Integer32,
    gslbStatRemRealServerDnsHandoffs    Counter32,
    gslbStatRemRealServerHttpRedirs     Counter32
    }

gslbStatRemRealServerIndex OBJECT-TYPE 
    SYNTAX  Integer32 
    MAX-ACCESS  read-only
    STATUS  current 
    DESCRIPTION 
        "The server number that identifies the remote real server." 
    ::= { gslbStatRemRealServerEntry 1 }

gslbStatRemRealServerDnsHandoffs OBJECT-TYPE 
    SYNTAX  Counter32 
    MAX-ACCESS  read-only
    STATUS  current 
    DESCRIPTION 
        "The number of DNS hanfoffs by the remote real server."
    ::= { gslbStatRemRealServerEntry 2 }

gslbStatRemRealServerHttpRedirs OBJECT-TYPE 
    SYNTAX  Counter32 
    MAX-ACCESS  read-only
    STATUS  current 
    DESCRIPTION 
        "The number of HTTP redirections by the remote real server."
    ::= { gslbStatRemRealServerEntry 3 }

-- The Global SLB Maintenance Statistics

gslbMaintStats OBJECT IDENTIFIER ::= { gslbStats 2 }

gslbStatMaintInGoodSiteUpdates OBJECT-TYPE 
    SYNTAX  Counter32 
    MAX-ACCESS  read-only
    STATUS  current 
    DESCRIPTION 
        "The number of good DSSPv1 remote site updates received."
    ::= { gslbMaintStats 1 }

gslbStatMaintInBadSiteUpdates OBJECT-TYPE 
    SYNTAX  Counter32 
    MAX-ACCESS  read-only
    STATUS  current 
    DESCRIPTION 
        "The number of bad remote site packets received."
    ::= { gslbMaintStats 2 }

gslbStatMaintOutSiteUpdates OBJECT-TYPE
    SYNTAX  Counter32
    MAX-ACCESS  read-only
    STATUS  current
    DESCRIPTION
        "The number of DSSPv1 remote site updates sent."
    ::= { gslbMaintStats 3 }

gslbStatMaintInGoodSiteUpdates2 OBJECT-TYPE
    SYNTAX  Counter32
    MAX-ACCESS  read-only
    STATUS  current
    DESCRIPTION
        "The number of good DSSPv2 remote site updates received."
    ::= { gslbMaintStats 4 }

gslbStatMaintOutSiteUpdates2 OBJECT-TYPE
    SYNTAX  Counter32
    MAX-ACCESS  read-only
    STATUS  current
    DESCRIPTION
        "The number of DSSPv2 remote site updates sent."
    ::= { gslbMaintStats 5 }


gslbStatMaintLocalSitePers OBJECT-TYPE
    SYNTAX  Counter32
    MAX-ACCESS  read-only
    STATUS  current
    DESCRIPTION
        "The number of local site DNS persistence cache entries added."
    ::= { gslbMaintStats 8 }


gslbStatMaintInDns OBJECT-TYPE
    SYNTAX  Counter32
    MAX-ACCESS  read-only
    STATUS  current
    DESCRIPTION
        "The number of DNS queries received."
    ::= { gslbMaintStats 10 }

gslbStatMaintInBadDns OBJECT-TYPE
    SYNTAX  Counter32
    MAX-ACCESS  read-only
    STATUS  current
    DESCRIPTION
        "The number of bad DNS queries received."
    ::= { gslbMaintStats 11 }

gslbStatMaintOutDns OBJECT-TYPE
    SYNTAX  Counter32
    MAX-ACCESS  read-only
    STATUS  current
    DESCRIPTION
        "The number of DNS responses sent."
    ::= { gslbMaintStats 12 }

gslbStatMaintInHttp OBJECT-TYPE
    SYNTAX  Counter32
    MAX-ACCESS  read-only
    STATUS  current
    DESCRIPTION
        "The number of HTTP requests received."
    ::= { gslbMaintStats 13 }

gslbStatMaintInBadHttp OBJECT-TYPE
    SYNTAX  Counter32
    MAX-ACCESS  read-only
    STATUS  current
    DESCRIPTION
        "The number of bad HTTP requests received."
    ::= { gslbMaintStats 14 }

gslbStatMaintOutHttp OBJECT-TYPE
    SYNTAX  Counter32
    MAX-ACCESS  read-only
    STATUS  current
    DESCRIPTION
        "The number of HTTP responses sent."
    ::= { gslbMaintStats 15 }

gslbStatMaintNoServer OBJECT-TYPE
    SYNTAX  Counter32
    MAX-ACCESS  read-only
    STATUS  current
    DESCRIPTION
        "The number of times no server returned."
    ::= { gslbMaintStats 16 }

gslbStatMaintNoDomain OBJECT-TYPE
    SYNTAX  Counter32
    MAX-ACCESS  read-only
    STATUS  current
    DESCRIPTION
        "The number of times no matching domain."
    ::= { gslbMaintStats 17 }

gslbStatMaintHostHits OBJECT-TYPE
    SYNTAX  Counter32
    MAX-ACCESS  read-only
    STATUS  current
    DESCRIPTION
        "The number of hostname domain hits."
    ::= { gslbMaintStats 18 }

gslbStatMaintRuleHits OBJECT-TYPE
    SYNTAX  Counter32
    MAX-ACCESS  read-only
    STATUS  current
    DESCRIPTION
        "The number of network domain hits."
    ::= { gslbMaintStats 19 }

gslbStatMaintVirtHits OBJECT-TYPE
    SYNTAX  Counter32
    MAX-ACCESS  read-only
    STATUS  current
    DESCRIPTION
        "The number of basic domain hits."
    ::= { gslbMaintStats 20 }

gslbStatMaintNoServerHost OBJECT-TYPE
    SYNTAX  Counter32
    MAX-ACCESS  read-only
    STATUS  current
    DESCRIPTION
        "The number of times no server returned for hostname domain."
    ::= { gslbMaintStats 21 }

gslbStatMaintNoServerRule OBJECT-TYPE
    SYNTAX  Counter32
    MAX-ACCESS  read-only
    STATUS  current
    DESCRIPTION
        "The number of times no server returned for network domain."
    ::= { gslbMaintStats 22 }

gslbStatMaintNoServerVirt OBJECT-TYPE
    SYNTAX  Counter32
    MAX-ACCESS  read-only
    STATUS  current
    DESCRIPTION
        "The number of times no server returned for basic domain."
    ::= { gslbMaintStats 23 }

gslbStatMaintLastNoResultDomain OBJECT-TYPE
    SYNTAX DisplayString (SIZE(0..255))
    MAX-ACCESS  read-only
    STATUS  current
    DESCRIPTION
        "The last no result domain."
    ::= { gslbMaintStats 24 }

gslbStatMaintLastSrcIp OBJECT-TYPE
    SYNTAX  IpAddress
    MAX-ACCESS  read-only
    STATUS  current
    DESCRIPTION
        "The last source IP address."
    ::= { gslbMaintStats 25 }

gslbStatMaintThresholdHits OBJECT-TYPE
    SYNTAX  Counter32
    MAX-ACCESS  read-only
    STATUS  current
    DESCRIPTION
        "The number of times any servers not returned due to threshold exceeded for the corresponding server."
    ::= { gslbMaintStats 26 }

-- Global SLB Group Statistics

gslbStatGroupTable OBJECT-TYPE
    SYNTAX  SEQUENCE OF GslbStatGroupEntry
    MAX-ACCESS  not-accessible
    STATUS  current
    DESCRIPTION
        "The GSLB group statistics table."
    ::= { gslbStats 3 }

gslbStatGroupEntry OBJECT-TYPE
    SYNTAX  GslbStatGroupEntry
    MAX-ACCESS  not-accessible
    STATUS  current
    DESCRIPTION
        "A row in the GSLB group statistics table."
    INDEX   { gslbStatGroupIndex }
    ::= { gslbStatGroupTable 1 }

GslbStatGroupEntry ::=	SEQUENCE {
    gslbStatGroupIndex          Integer32,
    gslbStatGroupDnsHandoffs    Counter32,
    gslbStatGroupHttpRedirs     Counter32
    }

gslbStatGroupIndex OBJECT-TYPE 
    SYNTAX  Integer32 
    MAX-ACCESS  read-only
    STATUS  current 
    DESCRIPTION 
        "The group number that identifies the real server group." 
    ::= { gslbStatGroupEntry 1 }

gslbStatGroupDnsHandoffs OBJECT-TYPE 
    SYNTAX  Counter32 
    MAX-ACCESS  read-only
    STATUS  current 
    DESCRIPTION 
        "The total number of DNS hand-offs sent to the remote real servers in 
         the group."
    ::= { gslbStatGroupEntry 2 }

gslbStatGroupHttpRedirs OBJECT-TYPE 
    SYNTAX  Counter32 
    MAX-ACCESS  read-only
    STATUS  current 
    DESCRIPTION 
        "The total number of HTTP redirects sent to the remote real servers in 
         the group."
    ::= { gslbStatGroupEntry 3 }

-- Global SLB Virtual Server Statistics

gslbStatVirtServerTable OBJECT-TYPE
    SYNTAX  SEQUENCE OF GslbStatVirtServerEntry
    MAX-ACCESS  not-accessible
    STATUS  current
    DESCRIPTION
        "The Global SLB virtual server statistics table."
    ::= { gslbStats 4 }

gslbStatVirtServerEntry OBJECT-TYPE
    SYNTAX  GslbStatVirtServerEntry
    MAX-ACCESS  not-accessible
    STATUS  current
    DESCRIPTION
        "A row in the Global SLB virtual server statistics table."
    INDEX   { gslbStatVirtServerIdx, gslbStatVirtServerServiceIdx, 
              gslbStatVirtServerRserverIdx }
    ::= { gslbStatVirtServerTable 1 }

GslbStatVirtServerEntry ::=	SEQUENCE {
    gslbStatVirtServerIdx            Integer32,
    gslbStatVirtServerServiceIdx     Integer32,
    gslbStatVirtServerRserverIdx     Integer32,
    gslbStatVirtServerVirtPort       Integer32,
    gslbStatVirtServerIpAddress      IpAddress,
    gslbStatVirtServerResponseTime   Integer32,
    gslbStatVirtServerMinSessAvail   Gauge32,
    gslbStatVirtServerDname          DisplayString,
    gslbStatVirtServerRemSite        Integer32,
    gslbStatVirtDnsDirect            Counter32
    }
  
gslbStatVirtServerIdx OBJECT-TYPE 
    SYNTAX  Integer32 
    MAX-ACCESS  read-only
    STATUS  current 
    DESCRIPTION 
        "The virtual server number that identifies the virtual server." 
    ::= { gslbStatVirtServerEntry 1 }

gslbStatVirtServerServiceIdx OBJECT-TYPE 
    SYNTAX  Integer32 
    MAX-ACCESS  read-only
    STATUS  current 
    DESCRIPTION 
        "The virtual server service number that identifies the virtual 
         service." 
    ::= { gslbStatVirtServerEntry 2 }

gslbStatVirtServerRserverIdx OBJECT-TYPE 
    SYNTAX  Integer32 
    MAX-ACCESS  read-only
    STATUS  current 
    DESCRIPTION 
        "The real server number that identifies a remote site. A index of 
         0 indicates a local virtual server number." 
    ::= { gslbStatVirtServerEntry 3 }

gslbStatVirtServerVirtPort OBJECT-TYPE 
    SYNTAX  Integer32
    MAX-ACCESS  read-only
    STATUS  current 
    DESCRIPTION 
        "The virtual server service port."
    ::= { gslbStatVirtServerEntry 4 }

gslbStatVirtServerIpAddress OBJECT-TYPE 
    SYNTAX  IpAddress
    MAX-ACCESS  read-only
    STATUS  current 
    DESCRIPTION 
        "The IP address of the virtual server or remote real server."
    ::= { gslbStatVirtServerEntry 5 }

gslbStatVirtServerResponseTime OBJECT-TYPE 
    SYNTAX  Integer32
    MAX-ACCESS  read-only
    STATUS  current 
    DESCRIPTION 
        "The average time (current weight) that each service takes to respond
         to information exchanges with its peers The time is specified in 
         ticks of 65 milliseconds."
    ::= { gslbStatVirtServerEntry 6 }

gslbStatVirtServerMinSessAvail OBJECT-TYPE 
    SYNTAX  Gauge32
    MAX-ACCESS  read-only
    STATUS  current 
    DESCRIPTION 
        "The current number of sessions available for serving client requests.
         This number will change as client traffic loads change, or as real 
         servers under the virtual server or remote sites go in or out of 
         service."
    ::= { gslbStatVirtServerEntry 7 }

gslbStatVirtServerDname OBJECT-TYPE
    SYNTAX DisplayString (SIZE(0..64))
    MAX-ACCESS read-only
    STATUS current
    DESCRIPTION
        "The domain name of the virtual server and remote real server."
    ::= { gslbStatVirtServerEntry 8 }

gslbStatVirtServerRemSite OBJECT-TYPE
    SYNTAX Integer32
    MAX-ACCESS read-only
    STATUS current
    DESCRIPTION
        "The remote site of the remote real server. For virtual server, the remote site is 0."
    ::= { gslbStatVirtServerEntry 9 }

gslbStatVirtDnsDirect OBJECT-TYPE
    SYNTAX Counter32
    MAX-ACCESS read-only
    STATUS current
    DESCRIPTION
        "The total number of DNS directs sent to the virtual server or remote real server."
    ::= { gslbStatVirtServerEntry 10 }

-- Global SLB Remote Site Statistics

gslbStatRemSiteTable OBJECT-TYPE
    SYNTAX SEQUENCE OF GslbStatRemSiteTableEntry
    MAX-ACCESS not-accessible
    STATUS current
    DESCRIPTION
        "The Global SLB remote site statistics table."
    ::= { gslbStats 5 }

gslbStatRemSiteTableEntry OBJECT-TYPE
    SYNTAX GslbStatRemSiteTableEntry
    MAX-ACCESS not-accessible
    STATUS current
    DESCRIPTION
        "A row in the Global SLB remote site statistics table."
    INDEX { gslbStatRemSiteIdx }
    ::= { gslbStatRemSiteTable 1 }

GslbStatRemSiteTableEntry ::=     SEQUENCE {
    gslbStatRemSiteIdx            Integer32,
    gslbStatRemSiteOutUpdates     Counter32,
    gslbStatRemSiteInUpdates      Counter32,
    gslbStatRemSiteOutUpdates2    Counter32,
    gslbStatRemSiteInUpdates2     Counter32,
    gslbStatRemSiteInBadUpdates   Counter32
    }

gslbStatRemSiteIdx OBJECT-TYPE
    SYNTAX Integer32
    MAX-ACCESS read-only
    STATUS current
    DESCRIPTION
        "The remote site number that identifies the remote site."
    ::= { gslbStatRemSiteTableEntry 1 }

gslbStatRemSiteOutUpdates OBJECT-TYPE
    SYNTAX Counter32
    MAX-ACCESS read-only
    STATUS current
    DESCRIPTION
        "The number of DSSPv1 remote site updates sent."
    ::= { gslbStatRemSiteTableEntry 2 }

gslbStatRemSiteInUpdates OBJECT-TYPE
    SYNTAX Counter32
    MAX-ACCESS read-only
    STATUS current
    DESCRIPTION
        "The number of good DSSPv1 remote site updates received."
    ::= { gslbStatRemSiteTableEntry 3 }

gslbStatRemSiteOutUpdates2 OBJECT-TYPE
    SYNTAX Counter32
    MAX-ACCESS read-only
    STATUS current
    DESCRIPTION
        "The number of DSSPv2 remote site updates sent."
    ::= { gslbStatRemSiteTableEntry 4 }

gslbStatRemSiteInUpdates2 OBJECT-TYPE
    SYNTAX Counter32
    MAX-ACCESS read-only
    STATUS current
    DESCRIPTION
        "The number of good DSSPv2 remote site updates received."
    ::= { gslbStatRemSiteTableEntry 5 }

gslbStatRemSiteInBadUpdates OBJECT-TYPE
    SYNTAX Counter32
    MAX-ACCESS read-only
    STATUS current
    DESCRIPTION
        "The number of bad remote site updates received."
    ::= { gslbStatRemSiteTableEntry 6 }


-- Global SLB Enhanced Network Statistics

gslbStatEnhNetworkTable OBJECT-TYPE
    SYNTAX SEQUENCE OF GslbStatEnhNetworkTableEntry
    MAX-ACCESS not-accessible
    STATUS current
    DESCRIPTION
        "The Global SLB network statistics table."
    ::= { gslbStats 6 }

gslbStatEnhNetworkTableEntry OBJECT-TYPE
    SYNTAX GslbStatEnhNetworkTableEntry
    MAX-ACCESS not-accessible
    STATUS current
    DESCRIPTION
        "A row in the Global SLB network statistics table."
    INDEX { gslbStatEnhNetworkIdx }
    ::= { gslbStatEnhNetworkTable 1 }

GslbStatEnhNetworkTableEntry ::=     SEQUENCE {
    gslbStatEnhNetworkIdx             Integer32,
    gslbStatEnhNetworkHit             Counter32
    }

gslbStatEnhNetworkIdx OBJECT-TYPE
    SYNTAX Integer32
    MAX-ACCESS read-only
    STATUS current
    DESCRIPTION
        "The network number that identifies the network."
    ::= { gslbStatEnhNetworkTableEntry 1 }

gslbStatEnhNetworkHit OBJECT-TYPE
    SYNTAX Counter32
    MAX-ACCESS read-only
    STATUS current
    DESCRIPTION
        "The number of times network is selected."
    ::= { gslbStatEnhNetworkTableEntry 2 }

-- Global SLB Rule Statistics

gslbStatRuleTable OBJECT-TYPE
    SYNTAX SEQUENCE OF GslbStatRuleTableEntry
    MAX-ACCESS not-accessible
    STATUS current
    DESCRIPTION
        "The Global SLB rule statistics table."
    ::= { gslbStats 7 }

gslbStatRuleTableEntry OBJECT-TYPE
    SYNTAX GslbStatRuleTableEntry
    MAX-ACCESS not-accessible
    STATUS current
    DESCRIPTION
        "A row in the Global SLB rule statistics table."
    INDEX { gslbStatRuleIdx }
    ::= { gslbStatRuleTable 1 }

GslbStatRuleTableEntry ::=     SEQUENCE {
    gslbStatRuleIdx               Integer32,
    gslbStatRuleLeastconns        Counter32,
    gslbStatRuleRoundrobin        Counter32,
    gslbStatRuleMinmisses         Counter32,
    gslbStatRuleHash              Counter32,
    gslbStatRuleResponse          Counter32,
    gslbStatRuleGeographical      Counter32,
    gslbStatRuleNetwork           Counter32,
    gslbStatRuleRandom            Counter32,
    gslbStatRuleAvailability      Counter32,
    gslbStatRuleQos               Counter32,
    gslbStatRulePersistence       Counter32,
    gslbStatRuleLocal             Counter32,
    gslbStatRuleAlways            Counter32,
    gslbStatRuleRemote            Counter32,
    gslbStatRuleTotal             Counter32
    }

gslbStatRuleIdx OBJECT-TYPE
    SYNTAX Integer32
    MAX-ACCESS read-only
    STATUS current
    DESCRIPTION
        "The rule number that identifies the rule."
    ::= { gslbStatRuleTableEntry 1 }

gslbStatRuleLeastconns OBJECT-TYPE
    SYNTAX Counter32
    MAX-ACCESS read-only
    STATUS current
    DESCRIPTION
        "The number of times leastconns is used."
    ::= { gslbStatRuleTableEntry 2 }

gslbStatRuleRoundrobin OBJECT-TYPE
    SYNTAX Counter32
    MAX-ACCESS read-only
    STATUS current
    DESCRIPTION
        "The number of times roundrobin is used."
    ::= { gslbStatRuleTableEntry 3 }

gslbStatRuleMinmisses OBJECT-TYPE
    SYNTAX Counter32
    MAX-ACCESS read-only
    STATUS current
    DESCRIPTION
        "The number of times minmisses is used."
    ::= { gslbStatRuleTableEntry 4 }

gslbStatRuleHash OBJECT-TYPE
    SYNTAX Counter32
    MAX-ACCESS read-only
    STATUS current
    DESCRIPTION
        "The number of times hash is used."
    ::= { gslbStatRuleTableEntry 5 }

gslbStatRuleResponse OBJECT-TYPE
    SYNTAX Counter32
    MAX-ACCESS read-only
    STATUS current
    DESCRIPTION
        "The number of times response is used."
    ::= { gslbStatRuleTableEntry 6 }

gslbStatRuleGeographical OBJECT-TYPE
    SYNTAX Counter32
    MAX-ACCESS read-only
    STATUS current
    DESCRIPTION
        "The number of times geographical is used."
    ::= { gslbStatRuleTableEntry 7 }

gslbStatRuleNetwork OBJECT-TYPE
    SYNTAX Counter32
    MAX-ACCESS read-only
    STATUS current
    DESCRIPTION
        "The number of times network is used."
    ::= { gslbStatRuleTableEntry 8 }

gslbStatRuleRandom OBJECT-TYPE
    SYNTAX Counter32
    MAX-ACCESS read-only
    STATUS current
    DESCRIPTION
        "The number of times random is used."
    ::= { gslbStatRuleTableEntry 9 }

gslbStatRuleAvailability OBJECT-TYPE
    SYNTAX Counter32
    MAX-ACCESS read-only
    STATUS current
    DESCRIPTION
        "The number of times availability is used."
    ::= { gslbStatRuleTableEntry 10 }

gslbStatRuleQos OBJECT-TYPE
    SYNTAX Counter32
    MAX-ACCESS read-only
    STATUS current
    DESCRIPTION
        "The number of times qos is used."
    ::= { gslbStatRuleTableEntry 11 }

gslbStatRulePersistence OBJECT-TYPE
    SYNTAX Counter32
    MAX-ACCESS read-only
    STATUS current
    DESCRIPTION
        "The number of times persistence is used."
    ::= { gslbStatRuleTableEntry 12 }

gslbStatRuleLocal OBJECT-TYPE
    SYNTAX Counter32
    MAX-ACCESS read-only
    STATUS current
    DESCRIPTION
        "The number of times local is used."
    ::= { gslbStatRuleTableEntry 13 }

gslbStatRuleAlways OBJECT-TYPE
    SYNTAX Counter32
    MAX-ACCESS read-only
    STATUS current
    DESCRIPTION
        "The number of times always is used."
    ::= { gslbStatRuleTableEntry 14 }

gslbStatRuleRemote OBJECT-TYPE
    SYNTAX Counter32
    MAX-ACCESS read-only
    STATUS current
    DESCRIPTION
        "The number of times remote is used."
    ::= { gslbStatRuleTableEntry 15 }

gslbStatRuleTotal OBJECT-TYPE
    SYNTAX Counter32
    MAX-ACCESS read-only
    STATUS current
    DESCRIPTION
        "The number of times all the metrics are used."
    ::= { gslbStatRuleTableEntry 16 }

-- Global SLB Geographical Statistics

gslbStatGeo OBJECT IDENTIFIER ::= { gslbStats 8 }

gslbStatGeoNA OBJECT-TYPE
    SYNTAX Counter32
    MAX-ACCESS read-only
    STATUS current
    DESCRIPTION
        "The number of times North America is selected."
    ::= { gslbStatGeo 1 }

gslbStatGeoSA OBJECT-TYPE
    SYNTAX Counter32
    MAX-ACCESS read-only
    STATUS current
    DESCRIPTION
        "The number of times South America is selected."
    ::= { gslbStatGeo 2 }

gslbStatGeoEU OBJECT-TYPE
    SYNTAX Counter32
    MAX-ACCESS read-only
    STATUS current
    DESCRIPTION
        "The number of times Europe is selected."
    ::= { gslbStatGeo 3 }

gslbStatGeoCA OBJECT-TYPE
    SYNTAX Counter32
    MAX-ACCESS read-only
    STATUS current
    DESCRIPTION
        "The number of times Caribbean is selected."
    ::= { gslbStatGeo 4 }

gslbStatGeoPR OBJECT-TYPE
    SYNTAX Counter32
    MAX-ACCESS read-only
    STATUS current
    DESCRIPTION
        "The number of times Pacific Rim is selected."
    ::= { gslbStatGeo 5 }

gslbStatGeoSS OBJECT-TYPE
    SYNTAX Counter32
    MAX-ACCESS read-only
    STATUS current
    DESCRIPTION
        "The number of times Sub-Sahara is selected."
    ::= { gslbStatGeo 6 }

gslbStatGeoJP OBJECT-TYPE
    SYNTAX Counter32
    MAX-ACCESS read-only
    STATUS current
    DESCRIPTION
        "The number of times Japan is selected."
    ::= { gslbStatGeo 7 }

gslbStatGeoTotal OBJECT-TYPE
    SYNTAX Counter32
    MAX-ACCESS read-only
    STATUS current
    DESCRIPTION
        "The number of times any of the regions are selected."
    ::= { gslbStatGeo 8 }

gslbStatGeoAF OBJECT-TYPE
    SYNTAX Counter32
    MAX-ACCESS read-only
    STATUS current
    DESCRIPTION
        "The number of times Africa is selected."
    ::= { gslbStatGeo 9 }

-- Global SLB DNS Persistence Cache Statistics

gslbStatPers OBJECT IDENTIFIER ::= { gslbStats 9 }

gslbStatPersCurrent OBJECT-TYPE
    SYNTAX Counter32
    MAX-ACCESS read-only
    STATUS current
    DESCRIPTION
        "The current number of entries in the DNS persistence cache."
    ::= { gslbStatPers 1 }

gslbStatPersHiwat OBJECT-TYPE
    SYNTAX Counter32
    MAX-ACCESS read-only
    STATUS current
    DESCRIPTION
        "The highest number of entries recorded in the DNS persistence cache."
    ::= { gslbStatPers 2 }

gslbStatPersMax OBJECT-TYPE
    SYNTAX Counter32
    MAX-ACCESS read-only
    STATUS current
    DESCRIPTION
        "The maximum number of entries supported in the DNS persistence cache."
    ::= { gslbStatPers 3 }

-- FTP Passive SLB/NAT Statistics

ftpSlbStatTotal  OBJECT-TYPE
    SYNTAX  Counter32
    MAX-ACCESS  read-only
    STATUS  current
    DESCRIPTION
        "The number of times the switch receives both active and passive
         FTP connections."
    ::= { ftpStats 1 }

ftpNatStatTotal  OBJECT-TYPE
    SYNTAX  Counter32
    MAX-ACCESS  read-only
    STATUS  current
    DESCRIPTION
	"The number of times the switch receives the 'port' command from 
         the client."
    ::= { ftpStats 2 } 

ftpStatActiveNatIndex  OBJECT-TYPE
    SYNTAX  Counter32
    MAX-ACCESS  read-only
    STATUS  current
    DESCRIPTION
	"The number of times the switch creates a new index due to 'port'
         command from the client."
    ::= { ftpStats 3 } 

ftpStatNatAckSeqDiff  OBJECT-TYPE
    SYNTAX  Counter32
    MAX-ACCESS  read-only
    STATUS  current
    DESCRIPTION
 	"The difference in the numbers of ACK and SEQ that the switch needs 
         for packet adjustment." 
    ::= { ftpStats 4 } 

ftpStatSlbParseIndex  OBJECT-TYPE
    SYNTAX  Counter32
    MAX-ACCESS  read-only
    STATUS  current
    DESCRIPTION
	"The number of times the switch creates a new index in response to the
         'pasv' command from the client."
    ::= { ftpStats 5 } 

ftpStatSlbParseAckSeqDiff  OBJECT-TYPE
    SYNTAX  Counter32
    MAX-ACCESS  read-only
    STATUS  current
    DESCRIPTION
 	"The difference in the numbers of ACK and SEQ that the switch needs 
         for FTP SLB parsing." 
    ::= { ftpStats 6 } 

ftpStatModeSwitchError OBJECT-TYPE
    SYNTAX  Counter32
    MAX-ACCESS  read-only
    STATUS  current
    DESCRIPTION
	"The number of times the switch is not able to switch modes from
         active to passive and vice versa." 
    ::= { ftpStats 7 } 

radiusAcctReqsStats     OBJECT IDENTIFIER ::= { wapStats 1 }
tpcpAddSessReqsStats    OBJECT IDENTIFIER ::= { wapStats 2 }
tpcpDeleteSessReqsStats OBJECT IDENTIFIER ::= { wapStats 3 }

radiusAcctReqs OBJECT-TYPE 
    SYNTAX  Counter32 
    MAX-ACCESS  read-only
    STATUS  current 
    DESCRIPTION 
        "Radius Account Request."
    ::= { radiusAcctReqsStats 1 }

radiusAcctWrapReqs OBJECT-TYPE 
    SYNTAX  Counter32 
    MAX-ACCESS  read-only
    STATUS  current 
    DESCRIPTION 
        "Radius Account Wrap Request."
    ::= { radiusAcctReqsStats 2 }

radiusAcctStartReqs OBJECT-TYPE 
    SYNTAX  Counter32 
    MAX-ACCESS  read-only
    STATUS  current 
    DESCRIPTION 
        "Radius Account Start Request."
    ::= { radiusAcctReqsStats 3 }

radiusAcctUpdateReqs OBJECT-TYPE 
    SYNTAX  Counter32 
    MAX-ACCESS  read-only
    STATUS  current 
    DESCRIPTION 
        "Radius Account Update Request."
    ::= { radiusAcctReqsStats 4 }

radiusAcctStopReqs OBJECT-TYPE 
    SYNTAX  Counter32 
    MAX-ACCESS  read-only
    STATUS  current 
    DESCRIPTION 
        "Radius Account stop Request."
    ::= { radiusAcctReqsStats 5 }

radiusAcctBadReqs OBJECT-TYPE 
    SYNTAX  Counter32 
    MAX-ACCESS  read-only
    STATUS  current 
    DESCRIPTION 
        "Radius Account Bad Request."
    ::= { radiusAcctReqsStats 6 }

radiusAcctAddSessionReqs OBJECT-TYPE 
    SYNTAX  Counter32 
    MAX-ACCESS  read-only
    STATUS  current 
    DESCRIPTION 
        "Radius Account add session Request."
    ::= { radiusAcctReqsStats 7 }

radiusAcctDeleteSessionReqs OBJECT-TYPE 
    SYNTAX  Counter32 
    MAX-ACCESS  read-only
    STATUS  current 
    DESCRIPTION 
        "Radius Account delete session Request."
    ::= { radiusAcctReqsStats 8 }

radiusAcctReqFailsSPDead OBJECT-TYPE 
    SYNTAX  Counter32 
    MAX-ACCESS  read-only
    STATUS  current 
    DESCRIPTION 
        "Radius Account request fails SP Dead."
    ::= { radiusAcctReqsStats 10 }

radiusAcctReqFailsDMAFails OBJECT-TYPE 
    SYNTAX  Counter32 
    MAX-ACCESS  read-only
    STATUS  current 
    DESCRIPTION 
        "Radius Account request fails DMA fails."
    ::= { radiusAcctReqsStats 11 }

radiusAcctReqWithFramedIp OBJECT-TYPE 
    SYNTAX  Counter32 
    MAX-ACCESS  read-only
    STATUS  current 
    DESCRIPTION 
        "Radius Account request containing the FRAMED_IP field."
    ::= { radiusAcctReqsStats 12 }

radiusAcctReqWithoutFramedIp OBJECT-TYPE 
    SYNTAX  Counter32 
    MAX-ACCESS  read-only
    STATUS  current 
    DESCRIPTION 
        "Radius Account request not containing the FRAMED_IP field."
    ::= { radiusAcctReqsStats 13 }

tpcpAddSessReqs OBJECT-TYPE 
    SYNTAX  Counter32 
    MAX-ACCESS  read-only
    STATUS  current 
    DESCRIPTION 
        "WAP add Session requests." 
    ::= { tpcpAddSessReqsStats 1 }

tpcpAddSessReqsFailsSPDead OBJECT-TYPE 
    SYNTAX  Counter32 
    MAX-ACCESS  read-only
    STATUS  current 
    DESCRIPTION 
        "WAP add Session Fails as the SP is dead."
    ::= { tpcpAddSessReqsStats 3 }

tpcpDeleteSessReqs OBJECT-TYPE 
    SYNTAX  Counter32 
    MAX-ACCESS  read-only
    STATUS  current 
    DESCRIPTION 
        "TPCP Delete Session Requests." 
    ::= { tpcpDeleteSessReqsStats 1 }

tpcpDeleteSessReqsFailsSPDead OBJECT-TYPE 
    SYNTAX  Counter32 
    MAX-ACCESS  read-only
    STATUS current 
    DESCRIPTION 
        "TPCP Delete Session Fails as the SP is dead."
    ::= { tpcpDeleteSessReqsStats 3 }

wapRequestToWrongSP OBJECT-TYPE 
    SYNTAX  Counter32 
    MAX-ACCESS  read-only
    STATUS  current 
    DESCRIPTION 
        "The  WAP delete Session Entries sent to wrong SP."
    ::= { wapStats 4 }

-- RTSP Statistics

rtspStatControlConns OBJECT-TYPE 
    SYNTAX  Gauge32
    MAX-ACCESS  read-only
    STATUS  current 
    DESCRIPTION 
        "Total number of active RTSP control connections."
    ::= { rtspStats 1 }

rtspStatUDPStreams OBJECT-TYPE 
    SYNTAX  Gauge32
    MAX-ACCESS  read-only
    STATUS  current 
    DESCRIPTION 
        "Total number of active UDP streams."
    ::= { rtspStats 2 }

rtspStatRedirects OBJECT-TYPE 
    SYNTAX  Counter32
    MAX-ACCESS  read-only
    STATUS  current 
    DESCRIPTION 
        "Total number of switch redirects."
    ::= { rtspStats 3 }

rtspStatConnDenied OBJECT-TYPE 
    SYNTAX  Counter32
    MAX-ACCESS  read-only
    STATUS  current 
    DESCRIPTION 
        "Total connections denied due to RTSP connection limit."
    ::= { rtspStats 4 }

rtspStatAllocFails OBJECT-TYPE 
    SYNTAX  Counter32
    MAX-ACCESS  read-only
    STATUS  current 
    DESCRIPTION 
        "Total cases of heap memory allocation failures."
    ::= { rtspStats 5 }

rtspStatBufferAllocs OBJECT-TYPE 
    SYNTAX  Gauge32
    MAX-ACCESS  read-only
    STATUS  current 
    DESCRIPTION 
        "The total number of buffer allocations used."
    ::= { rtspStats 6 }

-- TCP Rate Limiting Statistics
tcpLimitStatHoldDowns OBJECT-TYPE 
    SYNTAX  Counter32
    MAX-ACCESS  read-only
    STATUS  current 
    DESCRIPTION 
        "Total number of client hold downs triggered."
    ::= { tcpLimitStats 1 }

tcpLimitStatClientEntries OBJECT-TYPE 
    SYNTAX  Gauge32
    MAX-ACCESS  read-only
    STATUS  current 
    DESCRIPTION 
        "Current number of TCP rate limiting per-client state entries."
    ::= { tcpLimitStats 2 }
    
udpLimitStatHoldDowns OBJECT-TYPE 
    SYNTAX  Counter32
    MAX-ACCESS  read-only
    STATUS  current 
    DESCRIPTION 
        "Total number of UDP client hold downs triggered."
    ::= { tcpLimitStats 3 }
    
icmpLimitStatHoldDowns OBJECT-TYPE 
    SYNTAX  Counter32
    MAX-ACCESS  read-only
    STATUS  current 
    DESCRIPTION 
        "Total number of ICMP client hold downs triggered."
    ::= { tcpLimitStats 4 }

udpLimitStatClientEntries OBJECT-TYPE 
    SYNTAX  Gauge32
    MAX-ACCESS  read-only
    STATUS  current 
    DESCRIPTION 
        "Current number of UDP rate limiting per-client state entries."
    ::= { tcpLimitStats 5 }
    
icmpLimitStatClientEntries OBJECT-TYPE 
    SYNTAX  Gauge32
    MAX-ACCESS  read-only
    STATUS  current 
    DESCRIPTION 
        "Current number of ICMP rate limiting per-client state entries."
    ::= { tcpLimitStats 6 }    
    
-- DNS SLB Statistics

dnsSlbStatTCPQueries OBJECT-TYPE 
    SYNTAX  Counter32
    MAX-ACCESS  read-only
    STATUS  current 
    DESCRIPTION 
        "Total number of TCP DNS queries."
    ::= { dnsSlbStats 1 }

dnsSlbStatUDPQueries OBJECT-TYPE 
    SYNTAX  Counter32
    MAX-ACCESS  read-only
    STATUS  current 
    DESCRIPTION 
        "Total number of UDP DNS queries."
    ::= { dnsSlbStats 2 }

dnsSlbStatInvalidQueries OBJECT-TYPE 
    SYNTAX  Counter32
    MAX-ACCESS  read-only
    STATUS  current 
    DESCRIPTION 
        "Total number of invalid DNS queries."
    ::= { dnsSlbStats 3 }

dnsSlbStatMultipleQueries OBJECT-TYPE 
    SYNTAX  Counter32
    MAX-ACCESS  read-only
    STATUS  current 
    DESCRIPTION 
        "Total number of multiple DNS queries."
    ::= { dnsSlbStats 4 }

dnsSlbStatDnameParseErrors OBJECT-TYPE 
    SYNTAX  Counter32
    MAX-ACCESS  read-only
    STATUS  current 
    DESCRIPTION 
        "Total number of domain name parse errors."
    ::= { dnsSlbStats 5 }

dnsSlbStatFailedMatches OBJECT-TYPE 
    SYNTAX  Counter32
    MAX-ACCESS  read-only
    STATUS  current 
    DESCRIPTION 
        "Total number of failed real server name matches."
    ::= { dnsSlbStats 6 }

dnsSlbStatInternalErrors OBJECT-TYPE 
    SYNTAX  Counter32
    MAX-ACCESS  read-only
    STATUS  current 
    DESCRIPTION 
        "Total number of DNS parsing internal errors."
    ::= { dnsSlbStats 7 }

slbStatsClear OBJECT-TYPE
    SYNTAX INTEGER {
	ok(1),
	clear(2)
	}
    MAX-ACCESS read-write
    STATUS current
    DESCRIPTION
        "This is an action object to clear the non-operational SLB statistics. 
         ok(1) is returned when read."
    ::= { layer4Stats 15 }

slbStatAuxSessTable OBJECT-TYPE
    SYNTAX  SEQUENCE OF SlbStatAuxSessEntry
    MAX-ACCESS  not-accessible
    STATUS  current
    DESCRIPTION
        "The auxiliary session table statistics."
    ::= { layer4Stats 17 }

slbStatAuxSessEntry OBJECT-TYPE
    SYNTAX  SlbStatAuxSessEntry
    MAX-ACCESS  not-accessible
    STATUS  current
    DESCRIPTION
        "The statistics of a particular auxiliary session table entry."
    INDEX   { slbStatAuxSessIndex }
    ::= { slbStatAuxSessTable 1 }

SlbStatAuxSessEntry ::= SEQUENCE {
    slbStatAuxSessIndex               Integer32,
    slbStatAuxSessCurConn             Gauge32,
    slbStatAuxSessMaxConn             Integer32,
    slbStatAuxSessAllocFails          Counter32
    }

slbStatAuxSessIndex OBJECT-TYPE
    SYNTAX  Integer32
    MAX-ACCESS  read-only
    STATUS  current
    DESCRIPTION
        "The auxiliary session table number." 
    ::= { slbStatAuxSessEntry 1 }

slbStatAuxSessCurConn OBJECT-TYPE 
    SYNTAX  Gauge32
    MAX-ACCESS  read-only
    STATUS  current 
    DESCRIPTION 
        "The number of connections in this auxiliary sessions table."
    ::= { slbStatAuxSessEntry 2 }

slbStatAuxSessMaxConn OBJECT-TYPE 
    SYNTAX  Integer32 
    MAX-ACCESS  read-only
    STATUS  current 
    DESCRIPTION 
        "The maximum number of connections handled by this auxiliary session 
         table."
    ::= { slbStatAuxSessEntry 3 }

slbStatAuxSessAllocFails OBJECT-TYPE 
    SYNTAX  Counter32 
    MAX-ACCESS  read-only
    STATUS  current 
    DESCRIPTION 
        "The total number of allocation failures for this auxiliary session 
         table."
    ::= { slbStatAuxSessEntry 4 }

-- SSL SLB Statistics

sslSlbStatSessIdAllocFails OBJECT-TYPE 
    SYNTAX  Counter32
    MAX-ACCESS  read-only
    STATUS  current 
    DESCRIPTION 
        "The number of times allocation of a session table entry failed when
         attempting to store a SessionId in the table."
    ::= { sslSlbStats 1 }

sslSlbStatCurSessions OBJECT-TYPE 
    SYNTAX  Gauge32
    MAX-ACCESS  read-only
    STATUS  current 
    DESCRIPTION 
        "The current number of different TCP sessions using SSL service."
    ::= { sslSlbStats 2 }

sslSlbStatTotalSessions OBJECT-TYPE 
    SYNTAX  Counter32
    MAX-ACCESS  read-only
    STATUS  current 
    DESCRIPTION 
        "The total number of different TCP sessions using SSL service."
    ::= { sslSlbStats 3 }

sslSlbStatHighestSessions OBJECT-TYPE 
    SYNTAX  Counter32
    MAX-ACCESS  read-only
    STATUS  current 
    DESCRIPTION 
        "The high water mark of current sessions of different TCP sessions 
         using SSL service."
    ::= { sslSlbStats 4 }

sslSlbStatUniqCurSessions OBJECT-TYPE 
    SYNTAX  Gauge32
    MAX-ACCESS  read-only
    STATUS  current 
    DESCRIPTION 
        "The current number of unique SSL sessions seen on the switch."
    ::= { sslSlbStats 5 }

sslSlbStatUniqTotalSessions OBJECT-TYPE 
    SYNTAX  Counter32
    MAX-ACCESS  read-only
    STATUS  current 
    DESCRIPTION 
        "The total number of unique SSL sessions seen on the switch."
    ::= { sslSlbStats 6 }

sslSlbStatUniqHighestSessions OBJECT-TYPE 
    SYNTAX  Counter32
    MAX-ACCESS  read-only
    STATUS  current 
    DESCRIPTION 
        "The high water mark of unique SSL sessions seen on the switch."
    ::= { sslSlbStats 7 }

sslSlbStatPersistPortCurSessions OBJECT-TYPE 
    SYNTAX  Gauge32
    MAX-ACCESS  read-only
    STATUS  current 
    DESCRIPTION 
        "The current number of SessionIds maintained on SP 4, to allow for 
         persistence across different client ports."
    ::= { sslSlbStats 8 }

sslSlbStatPersistPortTotalSessions OBJECT-TYPE 
    SYNTAX  Counter32
    MAX-ACCESS  read-only
    STATUS  current 
    DESCRIPTION 
        "The total number of SessionIds maintained on SP 4, to allow for 
         persistence across different client ports."
    ::= { sslSlbStats 9 }

sslSlbStatPersistPortHighestSessions OBJECT-TYPE 
    SYNTAX  Counter32
    MAX-ACCESS  read-only
    STATUS  current 
    DESCRIPTION 
        "The high water mask of SessionIds maintained on SP 4, to allow for 
         persistence across different client ports."
    ::= { sslSlbStats 10 }


-- SLB Virtual Service Statistics Table

slbStatVirtServiceTable OBJECT-TYPE
    SYNTAX  SEQUENCE OF SlbStatVirtServiceEntry
    MAX-ACCESS  not-accessible
    STATUS  current
    DESCRIPTION
        "The virtual service statistics table."
    ::= { layer4Stats 18 }

slbStatVirtServiceEntry OBJECT-TYPE
    SYNTAX  SlbStatVirtServiceEntry
    MAX-ACCESS  not-accessible
    STATUS  current
    DESCRIPTION
        "The statistics of a particular virtual service."
    INDEX   { slbStatVirtServerIndex, slbStatVirtServiceIndex, slbStatRealServerIndex }
    ::= { slbStatVirtServiceTable 1 }

SlbStatVirtServiceEntry ::= SEQUENCE {
    slbStatVirtServerIndex                 Integer32,
    slbStatVirtServiceIndex                Integer32,
    slbStatRealServerIndex                 Integer32,
    slbStatVirtServiceCurrSessions         Gauge32,
    slbStatVirtServiceTotalSessions        Counter32,
    slbStatVirtServiceHighestSessions      Counter32,
    slbStatVirtServiceHCOctetsLow32        Counter32,
    slbStatVirtServiceHCOctetsHigh32       Counter32,
    slbStatVirtServiceHCOctets             Counter64
    }
    
slbStatVirtServerIndex OBJECT-TYPE
    SYNTAX  Integer32
    MAX-ACCESS  read-only
    STATUS  current
    DESCRIPTION
        "The virtual server number that identifies the service." 
    ::= { slbStatVirtServiceEntry 1 }
    
slbStatVirtServiceIndex OBJECT-TYPE
    SYNTAX  Integer32
    MAX-ACCESS  read-only
    STATUS  current
    DESCRIPTION
        "The virtual service number that identifies the service." 
    ::= { slbStatVirtServiceEntry 2 }
    
slbStatRealServerIndex OBJECT-TYPE
    SYNTAX  Integer32
    MAX-ACCESS  read-only
    STATUS  current
    DESCRIPTION
        "The real server index." 
    ::= { slbStatVirtServiceEntry 3 }
    
slbStatVirtServiceCurrSessions OBJECT-TYPE 
    SYNTAX  Gauge32
    MAX-ACCESS  read-only
    STATUS  current 
    DESCRIPTION 
        "The number of sessions that are currently handled by the 
         virtual service."
    ::= { slbStatVirtServiceEntry 4 }
    
slbStatVirtServiceTotalSessions OBJECT-TYPE 
    SYNTAX  Counter32 
    MAX-ACCESS  read-only
    STATUS  current 
    DESCRIPTION 
        "The total number of sessions that are handled by the virtual service."
    ::= { slbStatVirtServiceEntry 5}

slbStatVirtServiceHighestSessions OBJECT-TYPE 
    SYNTAX  Counter32 
    MAX-ACCESS  read-only
    STATUS  current 
    DESCRIPTION 
        "The highest sessions that have been handled by the virtual service."
    ::= { slbStatVirtServiceEntry 6}

slbStatVirtServiceHCOctetsLow32 OBJECT-TYPE
    SYNTAX  Counter32
    MAX-ACCESS  read-only
    STATUS  current
    DESCRIPTION
        "The lower 32 bit value of octets received and transmitted out
         of the virtual service."
    ::= { slbStatVirtServiceEntry 7}

slbStatVirtServiceHCOctetsHigh32 OBJECT-TYPE
    SYNTAX  Counter32
    MAX-ACCESS  read-only
    STATUS  current
    DESCRIPTION
        "The higher 32 bit value of octets received and transmitted out
         of the virtual service."
    ::= { slbStatVirtServiceEntry 8}

slbStatVirtServiceHCOctets OBJECT-TYPE
    SYNTAX  Counter64
    MAX-ACCESS  read-only
    STATUS  current
    DESCRIPTION
        "The total octets received and transmitted by the virtual service."
    ::= { slbStatVirtServiceEntry 9}



-- SIP statistics
sipTotalClientParseErrors OBJECT-TYPE 
    SYNTAX  Counter32 
    MAX-ACCESS  read-only
    STATUS  current 
    DESCRIPTION 
        "Total number of SIP Client parse Errors."
    ::= { sipStats 1 }

sipTotalServerParseErrors OBJECT-TYPE 
    SYNTAX  Counter32 
    MAX-ACCESS  read-only
    STATUS  current 
    DESCRIPTION 
        "Total number of SIP Server parse Errors."
    ::= { sipStats 2 }

sipTotalUnknownMethodReq OBJECT-TYPE 
    SYNTAX  Counter32 
    MAX-ACCESS  read-only
    STATUS  current 
    DESCRIPTION 
        "Total number of SIP unknown method requests."
    ::= { sipStats 3 }

sipTotalIncompleteMsgs OBJECT-TYPE 
    SYNTAX  Counter32 
    MAX-ACCESS  read-only
    STATUS  current 
    DESCRIPTION 
        "Total number of SIP Incomplete messages."
    ::= { sipStats 4 }

sipTotalSdpNatPackets OBJECT-TYPE
    SYNTAX  Counter32
    MAX-ACCESS  read-only
    STATUS  current
    DESCRIPTION
        "Total number of SDP NAT packets."
    ::= { sipStats 5 }


-- SLB WLM Statistics Table


wlmStats          OBJECT IDENTIFIER ::= { layer4Stats  21 }

slbStatWlmTable OBJECT-TYPE
    SYNTAX  SEQUENCE OF SlbStatWlmEntry
    MAX-ACCESS  not-accessible
    STATUS  current
    DESCRIPTION
        "The WLM statistics table."
    ::= { wlmStats 1 }

slbStatWlmEntry OBJECT-TYPE
    SYNTAX  SlbStatWlmEntry
    MAX-ACCESS  not-accessible
    STATUS  current
    DESCRIPTION
        "The statistics of a particular work load manager."
    INDEX   { slbStatWlmIndex }
    ::= { slbStatWlmTable 1 }

SlbStatWlmEntry ::= SEQUENCE {
    slbStatWlmIndex                   Integer32, 
    slbStatWlmRegReq                  Counter32,
    slbStatWlmRegRep                  Counter32,
    slbStatWlmRegRepErr               Counter32,
    slbStatWlmDeregReq                Counter32,
    slbStatWlmDeregRep                Counter32,
    slbStatWlmDeregRepErr             Counter32,
    slbStatWlmLbStateReq              Counter32,
    slbStatWlmLbStateRep              Counter32,
    slbStatWlmLbStateRepErr           Counter32,
    slbStatWlmMembStateReq            Counter32,
    slbStatWlmMembStateRep            Counter32,
    slbStatWlmMembStateRepErr         Counter32,
    slbStatWlmWtMsgRecv               Counter32,
    slbStatWlmWtMsgParErr             Counter32,
    slbStatWlmTotInvalidLb            Counter32,
    slbStatWlmTotInvalidGrp           Counter32,
    slbStatWlmTotInvalidRealSer       Counter32,
    slbStatWlmMsgInvalidSASPHeader    Counter32,
    slbStatWlmMsgParseErr             Counter32,
    slbStatWlmMsgUnsupMsgType         Counter32
    }

slbStatWlmIndex OBJECT-TYPE
    SYNTAX Integer32
    MAX-ACCESS  read-only
    STATUS  current
    DESCRIPTION
       "The work load manager number." 
    ::= { slbStatWlmEntry 1 }

slbStatWlmRegReq OBJECT-TYPE
    SYNTAX  Counter32
    MAX-ACCESS  read-only
    STATUS  current
    DESCRIPTION
        "Total number of registration request messages sent by the switch."
    ::= { slbStatWlmEntry 2 }

slbStatWlmRegRep OBJECT-TYPE
    SYNTAX  Counter32
    MAX-ACCESS  read-only
    STATUS  current
    DESCRIPTION
        "Total number of registration replies received from the GWM."
    ::= { slbStatWlmEntry 3 }

slbStatWlmRegRepErr OBJECT-TYPE
    SYNTAX  Counter32
    MAX-ACCESS  read-only
    STATUS  current
    DESCRIPTION
        "Total number of registration replies received where the return 
         code indicates an error."
    ::= { slbStatWlmEntry 4 }
slbStatWlmDeregReq OBJECT-TYPE
    SYNTAX  Counter32
    MAX-ACCESS  read-only
    STATUS  current
    DESCRIPTION
        "Total number of deregistration request messages sent by the switch."
    ::= { slbStatWlmEntry 5 }

slbStatWlmDeregRep OBJECT-TYPE
    SYNTAX  Counter32
    MAX-ACCESS  read-only
    STATUS  current
    DESCRIPTION
        "Total number of deregistration replies received from the GWM."
    ::= { slbStatWlmEntry 6 }

slbStatWlmDeregRepErr OBJECT-TYPE
    SYNTAX  Counter32
    MAX-ACCESS  read-only
    STATUS  current
    DESCRIPTION
        "Total number of deregistration replies received where the return code flag
         set indicating an error in processing of the deregistration request."
    ::= { slbStatWlmEntry 7 }

slbStatWlmLbStateReq OBJECT-TYPE
    SYNTAX  Counter32
    MAX-ACCESS  read-only
    STATUS  current
    DESCRIPTION
        "Total number of set LB state  request messages sent by the switch."
    ::= { slbStatWlmEntry 8 }

slbStatWlmLbStateRep OBJECT-TYPE
    SYNTAX  Counter32
    MAX-ACCESS  read-only
    STATUS  current
    DESCRIPTION
        "Total number of set LB state replies received from the GWM."
    ::= { slbStatWlmEntry 9 }

slbStatWlmLbStateRepErr OBJECT-TYPE
    SYNTAX  Counter32
    MAX-ACCESS  read-only
    STATUS  current
    DESCRIPTION
        "Total number of set LB state replies received where the return code code 
         flag set indicating an error in processing of the set LB state request."
    ::= { slbStatWlmEntry 10 }

slbStatWlmMembStateReq OBJECT-TYPE
    SYNTAX  Counter32
    MAX-ACCESS  read-only
    STATUS  current
    DESCRIPTION
        "Total number of set member state  request messages sent by the switch."
    ::= { slbStatWlmEntry 11 }

slbStatWlmMembStateRep OBJECT-TYPE
    SYNTAX  Counter32
    MAX-ACCESS  read-only
    STATUS  current
    DESCRIPTION
        "Total number of set member state  replies received from the GWM."
    ::= { slbStatWlmEntry 12 }

slbStatWlmMembStateRepErr OBJECT-TYPE
    SYNTAX  Counter32
    MAX-ACCESS  read-only
    STATUS  current
    DESCRIPTION
        "Total number of set member state replies received where the return 
         code code flag set indicating an error in processing of the set
	 member state request."
    ::= { slbStatWlmEntry 13 }

slbStatWlmWtMsgRecv OBJECT-TYPE
    SYNTAX  Counter32
    MAX-ACCESS  read-only
    STATUS  current
    DESCRIPTION
        "Total number of weight updates received from the GWM."
    ::= { slbStatWlmEntry 14 }

slbStatWlmWtMsgParErr OBJECT-TYPE
    SYNTAX  Counter32
    MAX-ACCESS  read-only
    STATUS  current
    DESCRIPTION
        "Total number of errorsencountered during parsing of the send weights message."
    ::= { slbStatWlmEntry 15 }

slbStatWlmTotInvalidLb  OBJECT-TYPE
    SYNTAX  Counter32
    MAX-ACCESS  read-only
    STATUS  current
    DESCRIPTION
        "This counter is incremented when the LB name in send weights message 
         does not match the switch LB name."
    ::= { slbStatWlmEntry 16 }

slbStatWlmTotInvalidGrp  OBJECT-TYPE
    SYNTAX  Counter32
    MAX-ACCESS  read-only
    STATUS  current
    DESCRIPTION
        "This counter is incremented when the group name in send weights message 
         does not match with any of the groups configured on the switch."
    ::= { slbStatWlmEntry 17 }

slbStatWlmTotInvalidRealSer  OBJECT-TYPE
    SYNTAX  Counter32
    MAX-ACCESS  read-only
    STATUS  current
    DESCRIPTION
        "This counter is incremented when the real server name in send weights message
         does not match with any of the reals configured on the switch."
    ::= { slbStatWlmEntry 18 }

slbStatWlmMsgInvalidSASPHeader  OBJECT-TYPE
    SYNTAX  Counter32
    MAX-ACCESS  read-only
    STATUS  current
    DESCRIPTION
        "Total number of messages received from the GWM with invalid headers."
    ::= { slbStatWlmEntry 19 }

slbStatWlmMsgParseErr  OBJECT-TYPE
    SYNTAX  Counter32
    MAX-ACCESS  read-only
    STATUS  current
    DESCRIPTION
        "Total number of parse errors."
    ::= { slbStatWlmEntry 20 }

slbStatWlmMsgUnsupMsgType  OBJECT-TYPE
    SYNTAX  Counter32
    MAX-ACCESS  read-only
    STATUS  current
    DESCRIPTION
        "Total messages received where the message type is not supported by the switch."
    ::= { slbStatWlmEntry 21 }



sessMirrorTotalCreateSessionMsgRx OBJECT-TYPE
    SYNTAX  Counter32
    MAX-ACCESS  read-only
    STATUS  current
    DESCRIPTION
        "Total number of create session messages received."
    ::= { sessMirrorStats 1 }

sessMirrorTotalCreateSessionMsgTx OBJECT-TYPE
    SYNTAX  Counter32
    MAX-ACCESS  read-only
    STATUS  current
    DESCRIPTION
        "Total number of create session messages transmitted ."
    ::= { sessMirrorStats 2 }

sessMirrorTotalCreateDataSessionMsgRx OBJECT-TYPE
    SYNTAX  Counter32
    MAX-ACCESS  read-only
    STATUS  current
    DESCRIPTION
        "Total number of create data session messages received."
    ::= { sessMirrorStats 3 }

sessMirrorTotalCreateDataSessionMsgTx OBJECT-TYPE
    SYNTAX  Counter32
    MAX-ACCESS  read-only
    STATUS  current
    DESCRIPTION
        "Total number of create data session messages transmitted."
    ::= { sessMirrorStats 4 }

sessMirrorTotalUpdateSessionMsgRx OBJECT-TYPE
    SYNTAX  Counter32
    MAX-ACCESS  read-only
    STATUS  current
    DESCRIPTION
        "Total number of update session messages received."
    ::= { sessMirrorStats 5 }

sessMirrorTotalUpdateSessionMsgTx OBJECT-TYPE
    SYNTAX  Counter32
    MAX-ACCESS  read-only
    STATUS  current
    DESCRIPTION
        "Total number of update session messages transmitted."
    ::= { sessMirrorStats 6 }

sessMirrorTotalUpdateDataSessionMsgRx OBJECT-TYPE
    SYNTAX  Counter32
    MAX-ACCESS  read-only
    STATUS  current
    DESCRIPTION
        "Total number of update data session messages received."
    ::= { sessMirrorStats 7 }

sessMirrorTotalUpdateDataSessionMsgTx OBJECT-TYPE
    SYNTAX  Counter32
    MAX-ACCESS  read-only
    STATUS  current
    DESCRIPTION
        "Total number of update data session messages transmitted."
    ::= { sessMirrorStats 8 }

sessMirrorTotalDeleteSessionMsgRx OBJECT-TYPE
    SYNTAX  Counter32
    MAX-ACCESS  read-only
    STATUS  current
    DESCRIPTION
        "Total number of delete session messages received."
    ::= { sessMirrorStats 9 }

sessMirrorTotalDeleteSessionMsgTx OBJECT-TYPE
    SYNTAX  Counter32
    MAX-ACCESS  read-only
    STATUS  current
    DESCRIPTION
        "Total number of delete session messages transmitted."
    ::= { sessMirrorStats 10 }

sessMirrorTotalDeleteDataSessionMsgRx OBJECT-TYPE
    SYNTAX  Counter32
    MAX-ACCESS  read-only
    STATUS  current
    DESCRIPTION
        "Total number of delete data session messages received."
    ::= { sessMirrorStats 11 }

sessMirrorTotalDeleteDataSessionMsgTx OBJECT-TYPE
    SYNTAX  Counter32
    MAX-ACCESS  read-only
    STATUS  current
    DESCRIPTION
        "Total number of delete data session messages transmitted."
    ::= { sessMirrorStats 12 }

sessMirrorTotalSessionsCreated OBJECT-TYPE
    SYNTAX  Counter32
    MAX-ACCESS  read-only
    STATUS  current
    DESCRIPTION
        "Total number of sessions created."
    ::= { sessMirrorStats 13 }

sessMirrorTotalDataSessionsCreated OBJECT-TYPE
    SYNTAX  Counter32
    MAX-ACCESS  read-only
    STATUS  current
    DESCRIPTION
        "Total number of data sessions created."
    ::= { sessMirrorStats 14 }

sessMirrorTotalSessionsUpdated OBJECT-TYPE
    SYNTAX  Counter32
    MAX-ACCESS  read-only
    STATUS  current
    DESCRIPTION
        "Total number of sessions updated."
    ::= { sessMirrorStats 15 }

sessMirrorTotalDataSessionsUpdated OBJECT-TYPE
    SYNTAX  Counter32
    MAX-ACCESS  read-only
    STATUS  current
    DESCRIPTION
        "Total number of data sessions updated."
    ::= { sessMirrorStats 16 }

sessMirrorTotalSessionsDeleted OBJECT-TYPE
    SYNTAX  Counter32
    MAX-ACCESS  read-only
    STATUS  current
    DESCRIPTION
        "Total number of sessions deleted."
    ::= { sessMirrorStats 17 }

sessMirrorTotalDataSessionsDeleted OBJECT-TYPE
    SYNTAX  Counter32
    MAX-ACCESS  read-only
    STATUS  current
    DESCRIPTION
        "Total number of data sessions deleted."
    ::= { sessMirrorStats 18 }

sessMirrorSessionTableFullErr OBJECT-TYPE
    SYNTAX  Counter32
    MAX-ACCESS  read-only
    STATUS  current
    DESCRIPTION
        "Error indicates session table full."
    ::= { sessMirrorStats 19 }

sessMirrorNoPortErr OBJECT-TYPE
    SYNTAX  Counter32
    MAX-ACCESS  read-only
    STATUS  current
    DESCRIPTION
        "Error indicates unavailable port."
    ::= { sessMirrorStats 20 }

sessMirrorSessionPresentErr OBJECT-TYPE
    SYNTAX  Counter32
    MAX-ACCESS  read-only
    STATUS  current
    DESCRIPTION
        "Error indicates session already present."
    ::= { sessMirrorStats 21 }

sessMirrorSessionNotFoundErr OBJECT-TYPE
    SYNTAX  Counter32
    MAX-ACCESS  read-only
    STATUS  current
    DESCRIPTION
        "Error indicates session not found."
    ::= { sessMirrorStats 22 }

sessMirrorCtrlSessionNotFoundErr OBJECT-TYPE
    SYNTAX  Counter32
    MAX-ACCESS  read-only
    STATUS  current
    DESCRIPTION
        "Error indicates control session not found."
    ::= { sessMirrorStats 23 }


-- Real Server Information Table

slbRealServerInfoTable OBJECT-TYPE
    SYNTAX  SEQUENCE OF SlbRealServerInfoEntry
    MAX-ACCESS  not-accessible
    STATUS  current
    DESCRIPTION
        "The table of real server run-time information."
    ::= { layer4Info 1 }

slbRealServerInfoEntry OBJECT-TYPE
    SYNTAX  SlbRealServerInfoEntry
    MAX-ACCESS  not-accessible
    STATUS  current
    DESCRIPTION
        "A row in the real server information table."
    INDEX   { slbRealServerInfoIndex }
    ::= { slbRealServerInfoTable 1 }
 
SlbRealServerInfoEntry ::= SEQUENCE {
    slbRealServerInfoIndex           Integer32,
    slbRealServerInfoIpAddr          IpAddress,
    slbRealServerMacAddr             PhysAddress,
    slbRealServerInfoSwitchPort      Integer32,
    slbRealServerInfoHealthLayer     INTEGER,
    slbRealServerInfoOverflow        INTEGER,
    slbRealServerInfoState           INTEGER,
    slbRealServerInfoVlan            Integer32
    }

slbRealServerInfoIndex OBJECT-TYPE
    SYNTAX  Integer32
    MAX-ACCESS  read-only
    STATUS  current
    DESCRIPTION
        "The real server index" 
    ::= { slbRealServerInfoEntry 1 }

slbRealServerInfoIpAddr OBJECT-TYPE
    SYNTAX  IpAddress
    MAX-ACCESS  read-only
    STATUS  current
    DESCRIPTION
        "IP address of the real server." 
    ::= { slbRealServerInfoEntry 2 }

slbRealServerMacAddr OBJECT-TYPE
    SYNTAX  PhysAddress
    MAX-ACCESS  read-only
    STATUS  current
    DESCRIPTION
        "The MAC address of the real server." 
    ::= { slbRealServerInfoEntry 3 }

slbRealServerInfoSwitchPort OBJECT-TYPE
    SYNTAX  Integer32
    MAX-ACCESS  read-only
    STATUS  current
    DESCRIPTION
        "The switch port that the real server is connected to." 
    ::= { slbRealServerInfoEntry 4 }

slbRealServerInfoHealthLayer  OBJECT-TYPE
    SYNTAX  INTEGER { 
        layer1(1), 
        layer3(3),
        layer4(4)
        } 
    MAX-ACCESS  read-only
    STATUS  current
    DESCRIPTION
        "The OSI layer at which the real server functionality is verified."
    ::= { slbRealServerInfoEntry 5 }

slbRealServerInfoOverflow OBJECT-TYPE
    SYNTAX  INTEGER {
	overflow(1),
        no-overflow(2) 
        } 
    MAX-ACCESS  read-only
    STATUS  current
    DESCRIPTION
        "The overflow state of the real server." 
    ::= { slbRealServerInfoEntry 6 }

slbRealServerInfoState OBJECT-TYPE
    SYNTAX  INTEGER {
        running(2),
        failed(3),
        disabled(4)
        } 
    MAX-ACCESS  read-only
    STATUS  current
    DESCRIPTION
        "The state of the real server."
    ::= { slbRealServerInfoEntry 7 }

slbRealServerInfoVlan OBJECT-TYPE
    SYNTAX  Integer32
    MAX-ACCESS  read-only
    STATUS  current
    DESCRIPTION
        "The VLAN that the real server belongs to." 
    ::= { slbRealServerInfoEntry 8 }

-- Real Server Rport Table
slbRealServerRportInfoTable OBJECT-TYPE
    SYNTAX  SEQUENCE OF SlbRealServerRportInfoEntry
    MAX-ACCESS  not-accessible
    STATUS  current
    DESCRIPTION
        "The table of real server rport run-time information."
    ::= { layer4Info 3 }

slbRealServerRportInfoEntry OBJECT-TYPE
    SYNTAX  SlbRealServerRportInfoEntry
    MAX-ACCESS  not-accessible
    STATUS  current
    DESCRIPTION
        "A row in the real server rport information table."
    INDEX   { slbRealServerRportRealIndex, slbRealServerRportServIndex  }
    ::= { slbRealServerRportInfoTable 1 }
 
SlbRealServerRportInfoEntry ::= SEQUENCE {
    slbRealServerRportRealIndex           Integer32,
    slbRealServerRportServIndex           Integer32,
    slbRealServerRportInfoRport           Integer32,
    slbRealServerRportInfoState           INTEGER
    --slbRealServerRportInfoGroup           INTEGER
    }

slbRealServerRportRealIndex OBJECT-TYPE
    SYNTAX  Integer32
    MAX-ACCESS  read-only
    STATUS  current
    DESCRIPTION
        "The real server index" 
    ::= { slbRealServerRportInfoEntry 1 }

slbRealServerRportServIndex OBJECT-TYPE
    SYNTAX  Integer32
    MAX-ACCESS  read-only
    STATUS  current
    DESCRIPTION
        "The real server service index" 
    ::= { slbRealServerRportInfoEntry 2 }

slbRealServerRportInfoRport OBJECT-TYPE
    SYNTAX  Integer32
    MAX-ACCESS  read-only
    STATUS  current
    DESCRIPTION
        "The real server real port number" 
    ::= { slbRealServerRportInfoEntry 3 }

slbRealServerRportInfoState OBJECT-TYPE
    SYNTAX  INTEGER {
        up(1),
        down(2)
        } 
    MAX-ACCESS  read-only
    STATUS  current
    DESCRIPTION
        "The state of the real server port."
    ::= { slbRealServerRportInfoEntry 4 }

--slbRealServerRportInfoGroup OBJECT-TYPE
--    SYNTAX  INTEGER
--    MAX-ACCESS  read-only
--    STATUS  current
--    DESCRIPTION
--        "The real server group number."
--    ::= { slbRealServerRportInfoEntry 5 }

-- Virtual Server Service Information Table

slbVirtServicesInfoTable OBJECT-TYPE
    SYNTAX  SEQUENCE OF SlbVirtServicesInfoEntry
    MAX-ACCESS  not-accessible
    STATUS  current
    DESCRIPTION
        "The table of virtual server services run-time information."
    ::= { layer4Info 4 }

slbVirtServicesInfoEntry OBJECT-TYPE
    SYNTAX  SlbVirtServicesInfoEntry
    MAX-ACCESS  not-accessible
    STATUS  current
    DESCRIPTION
        "A row in the virtual service information table."
    INDEX   { slbVirtServicesInfoVirtServIndex, slbVirtServicesInfoSvcIndex, 
              slbVirtServicesInfoRealServIndex }
    ::= { slbVirtServicesInfoTable 1 }
 
SlbVirtServicesInfoEntry ::= SEQUENCE {
    slbVirtServicesInfoVirtServIndex   Integer32,
    slbVirtServicesInfoSvcIndex        Integer32,
    slbVirtServicesInfoRealServIndex   Integer32,
    slbVirtServicesInfoVport           Integer32,
    slbVirtServicesInfoRport           Integer32,
    slbVirtServicesInfoState           INTEGER,
    slbVirtServicesInfoResponseTime    Integer32,
    slbVirtServicesInfoWeight          Integer32
    }

slbVirtServicesInfoVirtServIndex OBJECT-TYPE
    SYNTAX  Integer32
    MAX-ACCESS  read-only
    STATUS  current
    DESCRIPTION
        "The virtual server index." 
    ::= { slbVirtServicesInfoEntry 1 }

slbVirtServicesInfoSvcIndex OBJECT-TYPE
    SYNTAX  Integer32
    MAX-ACCESS  read-only
    STATUS  current
    DESCRIPTION
        "The virtual service index." 
    ::= { slbVirtServicesInfoEntry 2 }

slbVirtServicesInfoRealServIndex OBJECT-TYPE
    SYNTAX  Integer32
    MAX-ACCESS  read-only
    STATUS  current
    DESCRIPTION
        "The real server index." 
    ::= { slbVirtServicesInfoEntry 3 }

slbVirtServicesInfoVport OBJECT-TYPE
    SYNTAX  Integer32
    MAX-ACCESS  read-only
    STATUS  current
    DESCRIPTION
        "The layer 4 virtual port number for the service." 
    ::= { slbVirtServicesInfoEntry 4 }

slbVirtServicesInfoRport OBJECT-TYPE
    SYNTAX  Integer32
    MAX-ACCESS  read-only
    STATUS  current
    DESCRIPTION
        "The layer 4 real port number for the service." 
    ::= { slbVirtServicesInfoEntry 5 }

slbVirtServicesInfoState OBJECT-TYPE
    SYNTAX  INTEGER {
        blocked(1),
        running(2),
        failed(3),
        disabled(4)
	}
    MAX-ACCESS  read-only
    STATUS  current
    DESCRIPTION
        "The state of the real server for this virtual service." 
    ::= { slbVirtServicesInfoEntry 6 }

slbVirtServicesInfoResponseTime OBJECT-TYPE
    SYNTAX  Integer32
    MAX-ACCESS  read-only
    STATUS  current
    DESCRIPTION
        "The health check response time for the real server for this 
         virtual service." 
    ::= { slbVirtServicesInfoEntry 7 }

slbVirtServicesInfoWeight OBJECT-TYPE
    SYNTAX  Integer32
    MAX-ACCESS  read-only
    STATUS  current
    DESCRIPTION
        "The real server weight." 
    ::= { slbVirtServicesInfoEntry 8 }


-- slb session table info
slbSessionInfo        OBJECT IDENTIFIER ::= { layer4Info 5 }

slbSessionInfoState OBJECT-TYPE
    SYNTAX  INTEGER {
	start(1), 
        idle(2),
        inprogress(3),
	complete(4)
	}
    MAX-ACCESS  read-write
    STATUS  current
    DESCRIPTION
 	"When this object is read the current state is returned.
         idle(2) indicates that there is no session binding table request
         in progress.
	 When a read on this object returns inprogress(3) indicates that
	 a session binding table retrieval request is in progress.
         Setting the value to start(1), will start a new session table 
         retrieval operation based on the filtering criteria.
         complete(4) indicates that the session table has been retrieved.
         Once the slbSessionInfoTable is read the state should be set back to 
         'idle' which frees the session table buffer and others can issue a 
         request command via SNMP."
	
    ::= { slbSessionInfo 1 }

slbSessionInfoType OBJECT-TYPE
    SYNTAX  INTEGER {
	all(1),
	cip(2),
	cport(3),
	dip(4),
	dport(5),
	pip(6),
	pport(7),
	filter(8),
	flag(9),
	port(10),
	real(11)
	}
    MAX-ACCESS  read-write
    STATUS  current
    DESCRIPTION
        "This identifies the filtering criteria for the 
         session binding table request. 
	 all(1)   : Show all session entries
	 cip(2)   : Show all session entries with source IP address
         cport(3) : Show all session entries with source port
         dip(4)   : Show all session entries with destination IP address
         dport(5) : Show all session entries with destination port
         pip(6)   : Show all session entries with proxy IP address
         pport(7) : Show all session entries with proxy port
         filter(8): Show all session entries with matching filter
         flag(9)  : Show all session entries with matching flag
         port(10) : Show all session entries with ingress port
         real(11) : Show all session entries with real IP address."
    ::= { slbSessionInfo 2 }

slbSessionInfoIpAddr OBJECT-TYPE
    SYNTAX  IpAddress
    MAX-ACCESS  read-write
    STATUS  current
    DESCRIPTION
        "IP address of the requested filtering criteria 
	 0.0.0.0 if the filtering criteria is not  to match
         session entries with the same IP address."
    ::= { slbSessionInfo 3 }

slbSessionInfoFilterId OBJECT-TYPE
    SYNTAX  Integer32
    MAX-ACCESS  read-write
    STATUS  current
    DESCRIPTION
         "This field indicates that the session is created by filtering
          code as a result of the IP header keys matching the filtering
          criteria. 0 if slbSessionInfoFilterID is not the matching criteria."
    ::= { slbSessionInfo 4 }

slbSessionInfoPortId OBJECT-TYPE
    SYNTAX  Integer32
    MAX-ACCESS  read-write
    STATUS  current
    DESCRIPTION
        "The <port number> if the filtering criteria is (port) to
         match all session entries with the matching ingress port 
         or this represents the <real port> if the requested filtering
         criteria is to match session entries with (pport) proxy port, 
         (cport) source port, (dport) destination port,  
         This entry is 0 if the filtering criteria is not to match
         session entries with the same port."
    ::= { slbSessionInfo 5 }

slbSessionInfoFlag OBJECT-TYPE
    SYNTAX  INTEGER {
	eFlag(1),
	lFlag(2),
	nFlag(3),
	pFlag(4),
	sFlag(5),
	tFlag(6),
	uFlag(7),
	wFlag(8),
	ruFlag(9),
	riFlag(10),
	viFlag(11),
	vrFlag(12),
	vsFlag(13),
        vmFlag(14),
	vdFlag(15),
	none(20)
	}
    MAX-ACCESS  read-write
    STATUS  current
    DESCRIPTION
        "If the filtering criteria is flag select one of e|l|n|p|s|t|u|w(Flag)
         none(20) is selected if flag is not the fitering criteria.

         eFlag: Indicates the session is in use and will be aged out if no
                traffic is received within session timeout value.

         lFlag: Indicates the session is a link load balance session.

         nFlag: Indicates the session only translates the destination
                MAC when forwarding client traffic to the real server.

         pFlag: Indicates the session is a persistent session and is not to
                be aged out. Fields (6), (7) and (8) are not shown for
                persistent session.

         sFlag: Indicates the session is a persistent session and the
                application is SSL or Cookie Pbind.

         tFlag: Indicates the session is TCP rate limiting per-client entry.

         uFlag: Indicates the session is L7 delay binding and switch is
                trying to open TCP connection to real server.

         wFlag: Indicates the session only translates the destination
                MAC when forwarding layer 7 WCR traffic to the real server.

         ruFlag: Indicates the session is a UDP rate limiting per-client entry.

         riFlag: Indicates the session is a ICMP rate limiting per-client 
                 entry.

         viFlag: Indicates the session is a SIP INVITE session.

         vrFlag: Indicates the session is a SIP REGISTER session.

         vsFlag: Indicates the session is a SIP SUBSCRIBE session.

         vmFlag: Indicates the session is a SIP MESSAGE session.

         vdFlag: Indicates the session is a SIP NAT data session."

    ::= { slbSessionInfo 6 }

slbSessionInfoStringFormatFlag OBJECT-TYPE
    SYNTAX  INTEGER {
	formatted(1),
	none(2)
	}
    MAX-ACCESS  read-write
    STATUS  current
    DESCRIPTION
        "The flag which determines if the session table entries
         have to be formatted or (none) indicates no formatting to be done." 
    ::= { slbSessionInfo 7 }

slbSessionInfoMaxSessDump OBJECT-TYPE
    SYNTAX  Integer32 
    MAX-ACCESS  read-only
    STATUS  current
    DESCRIPTION
    "The maximum number of sessions that can exist at any given time."
    ::= { slbSessionInfo 9 }

slbSessionInfoTable OBJECT-TYPE
    SYNTAX SEQUENCE OF SlbSessionInfoEntry
    MAX-ACCESS not-accessible
    STATUS current
    DESCRIPTION
        "The table of SLB session entries."
    ::= { slbSessionInfo 8 }

slbSessionInfoEntry OBJECT-TYPE
    SYNTAX SlbSessionInfoEntry
    MAX-ACCESS not-accessible
    STATUS current
    DESCRIPTION
        "Information about SLB sessions."
    INDEX { slbSessionInfoSpIndex, slbSessionInfoIndex }
    ::= { slbSessionInfoTable 1 }
 
SlbSessionInfoEntry ::= SEQUENCE {
    slbSessionInfoSpIndex                    Integer32,
    slbSessionInfoIndex                      Integer32,
    slbSessionInfoString            	     OCTET STRING
    }

slbSessionInfoSpIndex OBJECT-TYPE
    SYNTAX  Integer32
    MAX-ACCESS  read-only
    STATUS  current
    DESCRIPTION
        "The SP which created the session." 
    ::= { slbSessionInfoEntry 1 }

slbSessionInfoIndex OBJECT-TYPE
    SYNTAX  Integer32
    MAX-ACCESS  read-only
    STATUS  current
    DESCRIPTION
        "The index to the slbSessionInfoTable." 
    ::= { slbSessionInfoEntry 2 }

slbSessionInfoString OBJECT-TYPE
    SYNTAX OCTET STRING
    MAX-ACCESS read-only
    STATUS current
    DESCRIPTION
        "The string representing the SLB session entries in the formatted case:
	 The fields, (1)-(13), associated with a session, as identified in the
	 example below are described in the following.

3, 01: 1.1.1.1 4586, 2.2.2.1 http -> 3567 3.3.3.1 http age 6 f:10 ELNPSRtUW c:#
(1) (2) (3)     (4)  (5)      (6)     (7)   (8)    (9)  (10)  (11)  (12) (13)

3, 01: 1.1.1.1 4586, 2.2.2.1 http ->
(1) (2) (3)     (4)  (5)      (6)
       1.1.1.2 3567 3.3.3.1 http age 6 f:10 ELNPSRtUW c:#
        (7a)     (7)   (8)    (9) (10)  (11)  (12) (13)

------------------------------------------------------------------
(1) SP number:
    This field indicates which SP created the session.

(2) Ingress port:
    This field shows the physical port# of the client traffic that
    entered to the switch.

(3) Source IP address:
    This field contains the source IP address from client IP packet.

(4) Source port:                          
    This field identifies the TCP/UDP source port from client packet.

(5) Destination IP address:
    This is the destination IP address from client TCP/UDP packet.

    For load balancing, this address is the virtual IP address.
    For filtering redirect, this address is the destination server's address.

(6) Destination port:
    This field identifies the TCP/UDP destination port from client packet.

(7a)Proxy IP address:                     
    This field contains the proxy IP address substituted by the switch.

(7) Proxy port:                           
    This field identifies the TCP/UDP source port substituted by the switch.

    The switch does this substitution when Direct Access Mode is enabled or
    Proxy is enabled.

(8) Real server IP address:               
    For load balancing, this field contains the IP address of the real
    server that the switch selects to forward client packet to.
    If the switch does not find live server, this field is the
    same as destination IP address(5).

    e.g. 3,01: 1.1.1.1 1040, 2.2.2.1 http -> 3.3.3.1 http age 10
         3,01: 1.1.1.1 1040, 2.2.2.1 http -> 2.2.2.1 http age 10

    For filtering, this field also shows the real server IP address. No
    address is shown if the filter action is Allow, Deny or NAT.
    It will show ALLOW, DENY or NAT instead.

    e.g. 3,01: 1.1.1.1 1040, 2.2.2.1 http -> 3.3.3.1 http age 10 f:11
         3,01: 1.1.1.1 1040, 2.2.2.1 http ALLOW age 10 f:22

(9) Server port:                          
    For load balancing, this field is the same as destination port(6)
    except for the RTSP UDP session. For RTSP UDP session, this server
    port is obtained from client-server negotiation.

    e.g. 3,01: 1.1.1.1 1040, 2.2.2.1 http -> 3.3.3.1 http age 10
         3,01: 1.1.1.1 6970, 2.2.2.1 rtsp -> 3.3.3.1 21220 age 10 P

    For filtering, this field is the filtering application port.
    It is for internal use only. This field can be urlwcr, wcr,
    idslb, linkslb or nonat.
    e.g. 3,01: 1.1.1.1 1040, 2.2.2.1 http -> 3.3.3.1 urlwcr age 4 f:123
         2,07: 1.1.1.1 1706, 2.2.2.1 http -> 192.168.4.10 linklb age 8 f:10 E

(10) Age:
    This is the session timeout value. If no packet is received within
    the value specified, the session is freed.
    e.g. age 10    - The session is aged out in 10 minutes.
         age < 160 - The session is aged out in 160 minutes. This <
                     indicates that slowage is used(user configures
                     /cfg/slb/adv/slowage)

(11) Filter number:                       
     This field indicates that the session is created by filtering
     code as a result of the IP header keys matching the filtering
     criteria.

(12) Flag:
     E: Indicates the session is in use and will be aged out if no
        traffic is received within session timeout value.

     L: Indicates the session is a link load balance session.

     N: Indicates the session only translates the destination
        MAC when forwarding client traffic to the real server.

     P: Indicates the session is a persistent session and is not to
        be aged out. Fields (6), (7) and (8) are not shown for
        persistent session.

     S: Indicates the session is a persistent session and the
        application is SSL or Cookie Pbind.

     Rt: Indicates the session is TCP rate limiting per-client entry.

     Ru: Indicates the session is UDP rate limiting per-client entry.

     Ri: Indicates the session is ICMP rate limiting per-client entry.

     U: Indicates the session is L7 delay binding and switch is
        trying to open TCP connection to real server.

     W: Indicates the session only translates the destination
        MAC when forwarding layer 7 WCR traffic to the real server.

(13) Persistent session user count:
     This counter indicates the number of client sessions created
     associated with this persistent session."
    ::= { slbSessionInfoEntry 3 }

-- Global SLB Information

gslbInfo         OBJECT IDENTIFIER ::= { layer4Info 6 }

-- Global SLB Remote Real Server Information

gslbInfoRemRealServerTable OBJECT-TYPE
    SYNTAX SEQUENCE OF GslbInfoRemRealServerEntry
    MAX-ACCESS not-accessible
    STATUS current
    DESCRIPTION
        "The Global SLB virtual server information table."
    ::= { gslbInfo 1 }

gslbInfoRemRealServerEntry OBJECT-TYPE
    SYNTAX GslbInfoRemRealServerEntry
    MAX-ACCESS not-accessible
    STATUS current
    DESCRIPTION
        "A row in the Global SLB remote real server information table."
    INDEX { gslbInfoRemRealServerIdx }
    ::= { gslbInfoRemRealServerTable 1 }

GslbInfoRemRealServerEntry ::=     SEQUENCE {
    gslbInfoRemRealServerIdx            Integer32,
    gslbInfoRemRealServerIpAddr         IpAddress,
    gslbInfoRemRealServerName           DisplayString,
    gslbInfoRemRealServerState          INTEGER
    }

gslbInfoRemRealServerIdx OBJECT-TYPE
    SYNTAX Integer32
    MAX-ACCESS read-only
    STATUS current
    DESCRIPTION
        "The remote real server number that identifies the remote real server."
    ::= { gslbInfoRemRealServerEntry 1 }

gslbInfoRemRealServerIpAddr OBJECT-TYPE
    SYNTAX IpAddress
    MAX-ACCESS read-only
    STATUS current
    DESCRIPTION
        "IP address of the remote real server."
    ::= { gslbInfoRemRealServerEntry 2 }

gslbInfoRemRealServerName OBJECT-TYPE
    SYNTAX DisplayString (SIZE(0..31))
    MAX-ACCESS read-only
    STATUS current
    DESCRIPTION
        "The name of the remote real server."
    ::= { gslbInfoRemRealServerEntry 3 }

gslbInfoRemRealServerState OBJECT-TYPE
    SYNTAX INTEGER {
        running(2),
        failed(3),
        disabled(4)
        }
    MAX-ACCESS read-only
    STATUS current
    DESCRIPTION
        "The state of the remote real server."
    ::= { gslbInfoRemRealServerEntry 4 }

-- Global SLB Virtual Server Information

gslbInfoVirtServerTable OBJECT-TYPE
    SYNTAX SEQUENCE OF GslbInfoVirtServerEntry
    MAX-ACCESS not-accessible
    STATUS current
    DESCRIPTION
        "The Global SLB virtual server information table."
    ::= { gslbInfo 2 }

gslbInfoVirtServerEntry OBJECT-TYPE
    SYNTAX GslbInfoVirtServerEntry
    MAX-ACCESS not-accessible
    STATUS current
    DESCRIPTION
        "A row in the Global SLB virtual server information table."
    INDEX { gslbInfoVirtServerIdx, gslbInfoVirtServerServiceIdx,
            gslbInfoVirtServerRserverIdx }
    ::= { gslbInfoVirtServerTable 1 }

GslbInfoVirtServerEntry ::=     SEQUENCE {
    gslbInfoVirtServerIdx            Integer32,
    gslbInfoVirtServerServiceIdx     Integer32,
    gslbInfoVirtServerRserverIdx     Integer32,
    gslbInfoVirtServerDname          DisplayString,
    gslbInfoVirtServerVirtPort       Integer32,
    gslbInfoVirtServerIpAddress      IpAddress,
    gslbInfoVirtServerResponse       Integer32,
    gslbInfoVirtServerSessAvail      Integer32,
    gslbInfoVirtServerSessCur        Integer32,
    gslbInfoVirtServerSessMax        Integer32,
    gslbInfoVirtServerSessUtil       INTEGER,
    gslbInfoVirtServerCpuUtil        INTEGER,
    gslbInfoVirtServerRemSite        Integer32,
    gslbInfoVirtServerWeight         INTEGER,
    gslbInfoVirtServerAvail          INTEGER,
    gslbInfoVirtServerRegion         INTEGER
    }

gslbInfoVirtServerIdx OBJECT-TYPE
    SYNTAX Integer32
    MAX-ACCESS read-only
    STATUS current
    DESCRIPTION
        "The virtual server number that identifies the virtual server."
    ::= { gslbInfoVirtServerEntry 1 }

gslbInfoVirtServerServiceIdx OBJECT-TYPE
    SYNTAX Integer32
    MAX-ACCESS read-only
    STATUS current
    DESCRIPTION
        "The virtual server service number that identifies the virtual service."
    ::= { gslbInfoVirtServerEntry 2 }

gslbInfoVirtServerRserverIdx OBJECT-TYPE
    SYNTAX Integer32
    MAX-ACCESS read-only
    STATUS current
    DESCRIPTION
        "The real server number that identifies a remote real server.
         An index of 0 indicates virtual server."
    ::= { gslbInfoVirtServerEntry 3 }

gslbInfoVirtServerDname OBJECT-TYPE
    SYNTAX DisplayString (SIZE(0..64))
    MAX-ACCESS read-only
    STATUS current
    DESCRIPTION
        "The domain name of the virtual server and remote real server."
    ::= { gslbInfoVirtServerEntry 4 }

gslbInfoVirtServerVirtPort OBJECT-TYPE
    SYNTAX Integer32
    MAX-ACCESS read-only
    STATUS current
    DESCRIPTION
        "The service port of the virtual server and remote real server."
    ::= { gslbInfoVirtServerEntry 5 }

gslbInfoVirtServerIpAddress OBJECT-TYPE
    SYNTAX IpAddress
    MAX-ACCESS read-only
    STATUS current
    DESCRIPTION
        "The IP address of the virtual server or remote real server."
    ::= { gslbInfoVirtServerEntry 6 }

gslbInfoVirtServerResponse OBJECT-TYPE
    SYNTAX Integer32
    MAX-ACCESS read-only
    STATUS current
    DESCRIPTION
        "The health check response time of the virtual server or remote real server."
    ::= { gslbInfoVirtServerEntry 7 }

gslbInfoVirtServerSessAvail OBJECT-TYPE
    SYNTAX Integer32
    MAX-ACCESS read-only
    STATUS current
    DESCRIPTION
        "The available sessions of the virtual server or remote real server."
    ::= { gslbInfoVirtServerEntry 8 }

gslbInfoVirtServerSessCur OBJECT-TYPE
    SYNTAX Integer32
    MAX-ACCESS read-only
    STATUS current
    DESCRIPTION
        "The current sessions of the virtual server or remote real server."
    ::= { gslbInfoVirtServerEntry 9 }

gslbInfoVirtServerSessMax OBJECT-TYPE
    SYNTAX Integer32
    MAX-ACCESS read-only
    STATUS current
    DESCRIPTION
        "The maximum sessions supported by the virtual server or remote real server."
    ::= { gslbInfoVirtServerEntry 10 }

gslbInfoVirtServerSessUtil OBJECT-TYPE
    SYNTAX INTEGER(1..100)
    MAX-ACCESS read-only
    STATUS current
    DESCRIPTION
        "The sessions utilization (current/max) of the virtual server or remote real server."
    ::= { gslbInfoVirtServerEntry 11 }

gslbInfoVirtServerCpuUtil OBJECT-TYPE
    SYNTAX INTEGER(1..100)
    MAX-ACCESS read-only
    STATUS current
    DESCRIPTION
        "The CPU utilization of the virtual server or remote real server."
    ::= { gslbInfoVirtServerEntry 12 }

gslbInfoVirtServerRemSite OBJECT-TYPE
    SYNTAX Integer32
    MAX-ACCESS read-only
    STATUS current
    DESCRIPTION
        "The remote site of the remote real server. For virtual server, the remote site is 0."
    ::= { gslbInfoVirtServerEntry 13 }

gslbInfoVirtServerWeight OBJECT-TYPE
    SYNTAX INTEGER(1..48)
    MAX-ACCESS read-only
    STATUS current
    DESCRIPTION
        "The weight of the virtual server or remote real server."
    ::= { gslbInfoVirtServerEntry 14 }

gslbInfoVirtServerAvail OBJECT-TYPE
    SYNTAX INTEGER(1..48)
    MAX-ACCESS read-only
    STATUS current
    DESCRIPTION
        "The availability of the virtual server or remote real server."
    ::= { gslbInfoVirtServerEntry 15 }

gslbInfoVirtServerRegion OBJECT-TYPE
    SYNTAX INTEGER {
        unknown(0),
        northamerica(1),
        southamerica(2),
        europe(3),
        caribbean(4),
        pacificrim(5),
        subsahara(6),
        japan(7),
        caribbeansubsahara(8),
	africa(9)
        }
    MAX-ACCESS read-only
    STATUS current
    DESCRIPTION
        "The region of the virtual server or remote real server."
    ::= { gslbInfoVirtServerEntry 16 }

-- Global SLB Remote Site Information

gslbInfoRemSiteTable OBJECT-TYPE
    SYNTAX SEQUENCE OF GslbInfoRemSiteEntry
    MAX-ACCESS not-accessible
    STATUS current
    DESCRIPTION
        "The Global SLB remote site information table."
    ::= { gslbInfo 3 }

gslbInfoRemSiteEntry OBJECT-TYPE
    SYNTAX GslbInfoRemSiteEntry
    MAX-ACCESS not-accessible
    STATUS current
    DESCRIPTION
        "A row in the Global SLB remote site information table."
    INDEX { gslbInfoRemSiteIdx }
    ::= { gslbInfoRemSiteTable 1 }

GslbInfoRemSiteEntry ::=     SEQUENCE {
    gslbInfoRemSiteIdx            Integer32,
    gslbInfoRemSitePrimaryIp      IpAddress,
    gslbInfoRemSiteSecondaryIp    IpAddress,
    gslbInfoRemSiteName           DisplayString,
    gslbInfoRemSiteState          INTEGER
    }

gslbInfoRemSiteIdx OBJECT-TYPE
    SYNTAX Integer32
    MAX-ACCESS read-only
    STATUS current
    DESCRIPTION
        "The remote site number that identifies the remote site."
    ::= { gslbInfoRemSiteEntry 1 }

gslbInfoRemSitePrimaryIp OBJECT-TYPE
    SYNTAX IpAddress
    MAX-ACCESS read-only
    STATUS current
    DESCRIPTION
        "The primary IP address of the remote site."
    ::= { gslbInfoRemSiteEntry 2 }

gslbInfoRemSiteSecondaryIp OBJECT-TYPE
    SYNTAX IpAddress
    MAX-ACCESS read-only
    STATUS current
    DESCRIPTION
        "The secondary IP address of the remote site."
    ::= { gslbInfoRemSiteEntry 3 }

gslbInfoRemSiteName OBJECT-TYPE
    SYNTAX DisplayString (SIZE(0..31))
    MAX-ACCESS read-only
    STATUS current
    DESCRIPTION
        "The name of the remote site."
    ::= { gslbInfoRemSiteEntry 4 }

gslbInfoRemSiteState OBJECT-TYPE
    SYNTAX INTEGER {
        running(2),
        failed(3),
        disabled(4)
        }
    MAX-ACCESS read-only
    STATUS current
    DESCRIPTION
        "The state of the remote site."
    ::= { gslbInfoRemSiteEntry 5 }


-- wlm Information

wlmInfo         OBJECT IDENTIFIER ::= { layer4Info 7 }

slbWlmInfoTable OBJECT-TYPE
    SYNTAX SEQUENCE OF SlbWlmInfoEntry
    MAX-ACCESS not-accessible
    STATUS current
    DESCRIPTION
        "The table of workload manager run-time information."
    ::= { wlmInfo 1 }

slbWlmInfoEntry OBJECT-TYPE
    SYNTAX SlbWlmInfoEntry
    MAX-ACCESS not-accessible
    STATUS current
    DESCRIPTION
        "A row in the workload manager information table."
    INDEX { slbWlmInfoIndex }
    ::= { slbWlmInfoTable 1 }

SlbWlmInfoEntry ::= SEQUENCE {
    slbWlmInfoIndex           Integer32,
    slbWlmInfoIpAddr          IpAddress,
    slbWlmInfoPort            INTEGER,
    slbWlmInfoState           INTEGER 
     }

slbWlmInfoIndex OBJECT-TYPE
    SYNTAX  Integer32
    MAX-ACCESS  read-only
    STATUS  current
    DESCRIPTION
        "The workload manager index."
    ::= { slbWlmInfoEntry 1 }

slbWlmInfoIpAddr OBJECT-TYPE
    SYNTAX  IpAddress
    MAX-ACCESS  read-only
    STATUS  current
    DESCRIPTION
        "IP address of the workload manager."
    ::= { slbWlmInfoEntry 2 }

slbWlmInfoPort OBJECT-TYPE
    SYNTAX  INTEGER (0..65534)
    MAX-ACCESS  read-only
    STATUS  current
    DESCRIPTION
        "The port number of the workload manager."
    ::= { slbWlmInfoEntry 3 }

slbWlmInfoState OBJECT-TYPE
    SYNTAX  INTEGER  { connected(1), notconnected(2)}
    MAX-ACCESS  read-only
    STATUS  current
    DESCRIPTION
        "The state of the workload manager."
    ::= { slbWlmInfoEntry 4 }


slbPortInfo         OBJECT IDENTIFIER ::= { layer4Info 8 }

slbPortInfoTable OBJECT-TYPE
    SYNTAX SEQUENCE OF SlbPortInfoEntry
    MAX-ACCESS not-accessible
    STATUS current
    DESCRIPTION
        "The table of port information."
    ::= { slbPortInfo 1 }

slbPortInfoEntry OBJECT-TYPE
    SYNTAX SlbPortInfoEntry
    MAX-ACCESS not-accessible
    STATUS current
    DESCRIPTION
        "A row in the port information table."
    INDEX { slbPortInfoIndex }
    ::= { slbPortInfoTable 1 }

SlbPortInfoEntry ::= SEQUENCE {
    slbPortInfoIndex           Integer32,
    slbPortClientState         INTEGER,
    slbPortSerState            INTEGER,
    slbPortFltState            INTEGER,
    slbPortRTSState            INTEGER,
    slbPortHotStandbyState     INTEGER,
    slbPortInterSWState        INTEGER,
    slbPortProxyState          INTEGER,
    slbPortIdSlbState          INTEGER,
    slbPortSymantecState       INTEGER,
    slbPortFitersAdded         OCTET STRING 
    }

slbPortInfoIndex OBJECT-TYPE
    SYNTAX Integer32
    MAX-ACCESS read-only
    STATUS current
    DESCRIPTION
        "Index of slb port."
    ::= { slbPortInfoEntry 1 }

slbPortClientState OBJECT-TYPE
    SYNTAX INTEGER {
        enabled(1),
        disabled(2)
        }
    MAX-ACCESS read-only
    STATUS current
    DESCRIPTION
        "Client state on the slb port."
    ::= { slbPortInfoEntry 2 }

slbPortSerState OBJECT-TYPE
    SYNTAX INTEGER {
        enabled(1),
        disabled(2)
        }
    MAX-ACCESS read-only
    STATUS current
    DESCRIPTION
        "Server state on the slb port."
    ::= { slbPortInfoEntry 3 }

slbPortFltState OBJECT-TYPE
    SYNTAX  INTEGER {
        enabled(1),
        disabled(2)
        } 
    MAX-ACCESS read-only
    STATUS current
    DESCRIPTION
        " Filter state on the slb port ."
    ::= { slbPortInfoEntry 4 }

slbPortRTSState OBJECT-TYPE
    SYNTAX INTEGER {
        enabled(1),
        disabled(2)
        }
    MAX-ACCESS read-only
    STATUS current
    DESCRIPTION
        "RTS processing state on the slb port."
    ::= { slbPortInfoEntry 5 }

slbPortHotStandbyState  OBJECT-TYPE
    SYNTAX INTEGER {
        enabled(1),
        disabled(2)
        }
    MAX-ACCESS read-only
    STATUS current
    DESCRIPTION
        "Hot standby state on the slb port."
    ::= { slbPortInfoEntry 6 }

slbPortInterSWState OBJECT-TYPE
    SYNTAX INTEGER {
        enabled(1),
        disabled(2)
        }
    MAX-ACCESS read-only
    STATUS current
    DESCRIPTION
        "Inter-switch processing state on the slb port."
    ::= { slbPortInfoEntry 7 }            

slbPortProxyState  OBJECT-TYPE
    SYNTAX INTEGER {
        enabled(1),
        disabled(2)
        }
    MAX-ACCESS read-only
    STATUS current
    DESCRIPTION
        "Proxy state on the slb port."
    ::= { slbPortInfoEntry 8 }

slbPortIdSlbState  OBJECT-TYPE
    SYNTAX INTEGER {
        enabled(1),
        disabled(2)
        }
    MAX-ACCESS read-only
    STATUS current
    DESCRIPTION
        "Intrusion detection server load balancing state on the slb port."
    ::= { slbPortInfoEntry 9 }

slbPortSymantecState  OBJECT-TYPE
    SYNTAX INTEGER {
        enabled(1),
        disabled(2)
        }
    MAX-ACCESS read-only
    STATUS current
    DESCRIPTION
        " Symantec Processing state on the slb port."
    ::= { slbPortInfoEntry 10 }

slbPortFitersAdded   OBJECT-TYPE
    SYNTAX  OCTET STRING (SIZE(0..256))
    MAX-ACCESS read-only
    STATUS current
    DESCRIPTION
        "The filtering rules applied to the port.  The filtering rules are
         presented in bitmap format.

         in receiving order:

             OCTET 1  OCTET 2  .....
             xxxxxxxx xxxxxxxx .....
             ||    || |_ filter 9
             ||    ||
             ||    ||___ filter 8
             ||    |____ filter 7
             ||      .    .   .
             ||_________ filter 2
             |__________ filter 1 

         where x : 1 - The represented filter rule applied to the port
                   0 - The represented filter rule not applied to the port."
    ::= { slbPortInfoEntry 11 }


synAttackInfo         OBJECT IDENTIFIER ::= { layer4Info 9 }

synAtkState OBJECT-TYPE
    SYNTAX INTEGER { on(1), off(2) }
    MAX-ACCESS read-only
    STATUS current
    DESCRIPTION
        "State of the Syn Attack, represents whether it is running or not."
    ::= { synAttackInfo 1}

synAtkInterval OBJECT-TYPE
    SYNTAX Integer32
    MAX-ACCESS read-only
    STATUS current
    DESCRIPTION
        "Specifies interval period of syn attack inspection in seconds,
         it returns 0 if synAtk is OFF."
    ::= { synAttackInfo 2}

synAtkThreshhold OBJECT-TYPE
    SYNTAX Integer32
    MAX-ACCESS read-only
    STATUS current
    DESCRIPTION
        "Specifies threshold of syn attack alram, it returns 0
         if synAtk is OFF ."
    ::= { synAttackInfo 3}

synAtkWarningFired OBJECT-TYPE
    SYNTAX Integer32
    MAX-ACCESS read-only
    STATUS current
    DESCRIPTION
        "Specifies number of times syn attack warnings fired."
    ::= { synAttackInfo 4}


-- Operation Commands

slbOperRealServerTable OBJECT-TYPE
    SYNTAX  SEQUENCE OF SlbOperRealServerEntry
    MAX-ACCESS  not-accessible
    STATUS  current
    DESCRIPTION
        "The table of real servers."
    ::= { layer4Oper 1 }

slbOperRealServerEntry OBJECT-TYPE
    SYNTAX  SlbOperRealServerEntry
    MAX-ACCESS  not-accessible
    STATUS  current
    DESCRIPTION
        "A row in the slbOperRealServerTable "
    INDEX   { slbOperRealServerIndex }
    ::= { slbOperRealServerTable 1 }

SlbOperRealServerEntry ::= SEQUENCE {
    slbOperRealServerIndex              Integer32,
    slbOperRealServerStatus             INTEGER
    }

slbOperRealServerIndex OBJECT-TYPE
    SYNTAX  Integer32
    MAX-ACCESS  read-only
    STATUS  current
    DESCRIPTION
        "The index for the  real server." 
    ::= { slbOperRealServerEntry 1 }

slbOperRealServerStatus OBJECT-TYPE
    SYNTAX  INTEGER {
	enable(1),
	disable(2),
	cookiepersistent(3)
	}
    MAX-ACCESS  read-write
    STATUS  current
    DESCRIPTION
        "This an action object which is used to temporarily enable/disable a
         real server. The real server will be returned to its configured
         operational mode when the switch is reset. Setting the value to 
         'cookiepersistant' allows cookie persistent HTTP 1.0 sessions
         when the real server is offline."
    ::= { slbOperRealServerEntry 2 }

slbOperClearSessionTable OBJECT-TYPE
    SYNTAX  INTEGER {
	ok(1),
	clear(2)
	}
    MAX-ACCESS  read-write
    STATUS  current
    DESCRIPTION
        "This is an action object to clear session binding table.
         ok(1) is returned when read."
    ::= { layer4Oper 2 }

slbOperConfigSync OBJECT-TYPE
    SYNTAX  INTEGER {
	ok(1),
	sync(2)
	}
    MAX-ACCESS  read-write
    STATUS  current
    DESCRIPTION
        "When set to a value of 'sync(2)' it synchronizes the SLB, filter
         and VRRP configuration on a peer switch. To take effect, peers must
         be configured on the switches and the administrator password on the
         switches must be identical. 
         'ok(1)' is returned when the object os read."
    ::= { layer4Oper 3 }

-- Global SLB Operations

gslbOper         OBJECT IDENTIFIER ::= { layer4Oper 4 }

slbOperGroupRealServerTable OBJECT-TYPE
    SYNTAX  SEQUENCE OF SlbOperGroupRealServerEntry
    MAX-ACCESS  not-accessible
    STATUS  current
    DESCRIPTION
        "The table of real server per group."
    ::= { layer4Oper 5 }

slbOperGroupRealServerEntry OBJECT-TYPE
    SYNTAX  SlbOperGroupRealServerEntry
    MAX-ACCESS  not-accessible
    STATUS  current
    DESCRIPTION
        "A row in the Real server group table."
    INDEX   { slbOperRealServGroupIndex, slbOperGroupRealServIndex}
    ::= { slbOperGroupRealServerTable 1 }

SlbOperGroupRealServerEntry ::= SEQUENCE {
    slbOperRealServGroupIndex        Integer32,
    slbOperGroupRealServIndex        Integer32,
    slbOperGroupRealServerState      INTEGER
    }

slbOperRealServGroupIndex OBJECT-TYPE
    SYNTAX  Integer32
    MAX-ACCESS  read-only
    STATUS  current
    DESCRIPTION
        "The real server group index." 
    ::= { slbOperGroupRealServerEntry 1 }

slbOperGroupRealServIndex OBJECT-TYPE
    SYNTAX  Integer32
    MAX-ACCESS  read-only
    STATUS  current
    DESCRIPTION
        "The real server index." 
    ::= { slbOperGroupRealServerEntry 2 }

slbOperGroupRealServerState OBJECT-TYPE
    SYNTAX  INTEGER {
	enable(1),
	disable(2)
	}
    MAX-ACCESS  read-write
    STATUS  current
    DESCRIPTION
        "This an action object which is used to temporarily enable/disable a
         real server in group. The real server will be returned to its configured
         operational mode when the switch is reset."
    ::= { slbOperGroupRealServerEntry 3 }


-- Server load balancing - Inbound Link Load Balancing Table

slbCurCfgLinklbState OBJECT-TYPE
    SYNTAX INTEGER {
        enabled(1),
        disabled(2)
        }
    MAX-ACCESS  read-only
    STATUS  current
    DESCRIPTION
        "Enable or disable Inbound Link load balancing. "
    ::= { linklbCfg 1 }

slbNewCfgLinklbState OBJECT-TYPE
    SYNTAX INTEGER {
        enabled(1),
        disabled(2)
        }
    MAX-ACCESS  read-write
    STATUS  current
    DESCRIPTION
        "Enable or disable Inbound Link load balancing. "
    ::= { linklbCfg 2 }

slbCurCfgLinklbRealGroup OBJECT-TYPE
    SYNTAX  Integer32  
    MAX-ACCESS  read-only
    STATUS  current
    DESCRIPTION
        "The real server group number for Link load balancing."
    ::= { linklbCfg 3 }

slbNewCfgLinklbRealGroup OBJECT-TYPE
    SYNTAX  Integer32  
    MAX-ACCESS  read-write
    STATUS  current
    DESCRIPTION
        "The real server group number for Link load balancing."
    ::= { linklbCfg 4 }

slbCurCfgLinklbTTL OBJECT-TYPE
    SYNTAX  INTEGER (0..65535) 
    MAX-ACCESS  read-only
    STATUS  current
    DESCRIPTION
        "Set Time to Live for DNS resource records."
    ::= { linklbCfg 6 }

slbNewCfgLinklbTTL OBJECT-TYPE
    SYNTAX  INTEGER (0..65535) 
    MAX-ACCESS  read-write
    STATUS  current
    DESCRIPTION
        "Set Time to Live for DNS resource records."
    ::= { linklbCfg 7 }

slbLinklbDrecord   OBJECT IDENTIFIER ::= { linklbCfg 5 }

slbDrecordTableMaxSize OBJECT-TYPE
    SYNTAX  Integer32 
    MAX-ACCESS  read-only 
    STATUS  current 
    DESCRIPTION 
        "The maximum number of entries in Drecord table."
    ::= { slbLinklbDrecord 1 }

slbCurCfgDrecordTable OBJECT-TYPE
    SYNTAX  SEQUENCE OF SlbCurCfgDrecordEntry
    MAX-ACCESS  not-accessible
    STATUS  current
    DESCRIPTION
        "The table of Domain records for Inbound link load balancing
         in the current configuration block."
    ::= { slbLinklbDrecord 2 }

slbCurCfgDrecordEntry OBJECT-TYPE
    SYNTAX  SlbCurCfgDrecordEntry
    MAX-ACCESS  not-accessible
    STATUS  current
    DESCRIPTION
        "A row in the Domain record table for Inbound Link Load
         balancing."
    INDEX   { slbCurCfgDrecordIndex }
    ::= { slbCurCfgDrecordTable 1 }

SlbCurCfgDrecordEntry ::= SEQUENCE {
    slbCurCfgDrecordIndex            INTEGER,
    slbCurCfgDomainRecordState       INTEGER,
    slbCurCfgDomainRecordName        DisplayString
    }

slbCurCfgDrecordIndex OBJECT-TYPE
    SYNTAX  INTEGER (1..64)
    MAX-ACCESS  read-only
    STATUS  current
    DESCRIPTION
        "The index of the Domain record table." 
    ::= { slbCurCfgDrecordEntry 1 }

slbCurCfgDomainRecordState OBJECT-TYPE
    SYNTAX  INTEGER {
	enabled(1),
	disabled(2)
	}
    MAX-ACCESS  read-only
    STATUS  current
    DESCRIPTION
        "Enable/disable a  domain record."
    ::= { slbCurCfgDrecordEntry 2 }

slbCurCfgDomainRecordName OBJECT-TYPE 
    SYNTAX  DisplayString (SIZE(0..34))
    MAX-ACCESS  read-only
    STATUS  current 
    DESCRIPTION 
        "The name of the domain record."  
    ::= { slbCurCfgDrecordEntry 3 }

slbNewCfgDrecordTable OBJECT-TYPE
    SYNTAX  SEQUENCE OF SlbNewCfgDrecordEntry
    MAX-ACCESS  not-accessible
    STATUS  current
    DESCRIPTION
        "The table of Domain records for Inbound link load balancing
         in the new configuration block."
    ::= { slbLinklbDrecord 3 }

slbNewCfgDrecordEntry OBJECT-TYPE
    SYNTAX  SlbNewCfgDrecordEntry
    MAX-ACCESS  not-accessible
    STATUS  current
    DESCRIPTION
        "A row in the Domain record table for Inbound Link Load
         balancing."
    INDEX   { slbNewCfgDrecordIndex }
    ::= { slbNewCfgDrecordTable 1 }

SlbNewCfgDrecordEntry ::= SEQUENCE {
    slbNewCfgDrecordIndex            INTEGER,
    slbNewCfgDomainRecordState       INTEGER,
    slbNewCfgDomainRecordName        DisplayString,
    slbNewCfgDrecordDelete           INTEGER 
    }

slbNewCfgDrecordIndex OBJECT-TYPE
    SYNTAX  INTEGER (1..64)
    MAX-ACCESS  read-only
    STATUS  current
    DESCRIPTION
        "The index of the Domain record table." 
    ::= { slbNewCfgDrecordEntry 1 }

slbNewCfgDomainRecordState OBJECT-TYPE
    SYNTAX  INTEGER {
	enabled(1),
	disabled(2)
	}
    MAX-ACCESS  read-create
    STATUS  current
    DESCRIPTION
        "Enable/disable a  domain record."
    ::= { slbNewCfgDrecordEntry 2 }

slbNewCfgDomainRecordName OBJECT-TYPE 
    SYNTAX  DisplayString (SIZE(0..34))
    MAX-ACCESS  read-create 
    STATUS  current 
    DESCRIPTION 
        "The name of the domain record."  
    ::= { slbNewCfgDrecordEntry 3 }

slbNewCfgDrecordDelete OBJECT-TYPE
    SYNTAX  INTEGER {
        other(1),
        delete(2)
        }
    MAX-ACCESS  read-create
    STATUS  current
    DESCRIPTION
        "By setting the value to delete(2), the entire row is deleted."
    ::= { slbNewCfgDrecordEntry 4 }

slbDrecordVirtRealMappingTableMaxSize OBJECT-TYPE
    SYNTAX  Integer32 
    MAX-ACCESS  read-only 
    STATUS  current 
    DESCRIPTION 
        "The maximum number of entries in Drecord Virtual Real server
         mapping Table." 
    ::= { slbLinklbDrecord 4 }

slbCurCfgDrecordVirtRealMappingTable OBJECT-TYPE
    SYNTAX  SEQUENCE OF SlbCurCfgDrecordVirtRealMappingEntry
    MAX-ACCESS  not-accessible
    STATUS  current
    DESCRIPTION
        "The table of Domain records and virtual server and real
         server mappings."
    ::= { slbLinklbDrecord 5 }

slbCurCfgDrecordVirtRealMappingEntry OBJECT-TYPE
    SYNTAX  SlbCurCfgDrecordVirtRealMappingEntry
    MAX-ACCESS  not-accessible
    STATUS  current
    DESCRIPTION
        "A row in the Domain record and virtual/real server mapping table
         for Inbound Link Load balancing."
    INDEX   { slbCurCfgDomainRecordIndex, slbCurCfgEntryIndex}
    ::= { slbCurCfgDrecordVirtRealMappingTable 1 }

SlbCurCfgDrecordVirtRealMappingEntry ::= SEQUENCE {
    slbCurCfgDomainRecordIndex            INTEGER,
    slbCurCfgEntryIndex                   INTEGER,
    slbCurCfgDrecordVirtServer            Integer32,
    slbCurCfgDrecordRealServer            Integer32,
    slbCurCfgDrecordEntryState            INTEGER
    }

slbCurCfgDomainRecordIndex OBJECT-TYPE
    SYNTAX  INTEGER (1..64)
    MAX-ACCESS  read-only
    STATUS  current
    DESCRIPTION
        "The number of the domain record." 
    ::= { slbCurCfgDrecordVirtRealMappingEntry 1 }

slbCurCfgEntryIndex OBJECT-TYPE
    SYNTAX  INTEGER (1..8)
    MAX-ACCESS  read-only
    STATUS  current
    DESCRIPTION
        "The number of the entry virtual real server mapping." 
    ::= { slbCurCfgDrecordVirtRealMappingEntry 2 }

slbCurCfgDrecordVirtServer OBJECT-TYPE
    SYNTAX  Integer32 
    MAX-ACCESS  read-only
    STATUS  current
    DESCRIPTION
        "The virtual server number."
    ::= { slbCurCfgDrecordVirtRealMappingEntry 3 }

slbCurCfgDrecordRealServer OBJECT-TYPE
    SYNTAX  Integer32 
    MAX-ACCESS  read-only
    STATUS  current
    DESCRIPTION
        "The Real server number."
    ::= { slbCurCfgDrecordVirtRealMappingEntry 4 }


slbCurCfgDrecordEntryState OBJECT-TYPE
    SYNTAX  INTEGER {
	enabled(1),
	disabled(2)
	}
    MAX-ACCESS  read-only
    STATUS  current
    DESCRIPTION
        "Enable/disable a mapping in this table."
    ::= { slbCurCfgDrecordVirtRealMappingEntry 5 }

slbNewCfgDrecordVirtRealMappingTable OBJECT-TYPE
    SYNTAX  SEQUENCE OF SlbNewCfgDrecordVirtRealMappingEntry
    MAX-ACCESS  not-accessible
    STATUS  current
    DESCRIPTION
        "The table of Domain records and virtual server and real
         server mappings."
    ::= { slbLinklbDrecord 6 }

slbNewCfgDrecordVirtRealMappingEntry OBJECT-TYPE
    SYNTAX  SlbNewCfgDrecordVirtRealMappingEntry
    MAX-ACCESS  not-accessible
    STATUS  current
    DESCRIPTION
        "A row in the Domain record and virtual/real server mapping table
         for Inbound Link Load balancing."
    INDEX   { slbNewCfgDomainRecordIndex, slbNewCfgEntryIndex }
    ::= { slbNewCfgDrecordVirtRealMappingTable 1 }

SlbNewCfgDrecordVirtRealMappingEntry ::= SEQUENCE {
    slbNewCfgDomainRecordIndex            INTEGER,
    slbNewCfgEntryIndex                   INTEGER,
    slbNewCfgDrecordVirtServer            Integer32,
    slbNewCfgDrecordRealServer            Integer32,
    slbNewCfgDrecordEntryState            INTEGER,
    slbNewCfgDrecordEntryDelete           INTEGER
    }

slbNewCfgDomainRecordIndex OBJECT-TYPE
    SYNTAX  INTEGER (1..64)
    MAX-ACCESS  read-only
    STATUS  current
    DESCRIPTION
        "The number of the domain record." 
    ::= { slbNewCfgDrecordVirtRealMappingEntry 1 }

slbNewCfgEntryIndex OBJECT-TYPE
    SYNTAX  INTEGER (1..8)
    MAX-ACCESS  read-only
    STATUS  current
    DESCRIPTION
        "The number of the virtual real server mapping." 
    ::= { slbNewCfgDrecordVirtRealMappingEntry 2 }

slbNewCfgDrecordVirtServer OBJECT-TYPE
    SYNTAX  Integer32 
    MAX-ACCESS  read-create
    STATUS  current
    DESCRIPTION
        "The virtual server number."
    ::= { slbNewCfgDrecordVirtRealMappingEntry 3 }

slbNewCfgDrecordRealServer OBJECT-TYPE
    SYNTAX  Integer32 
    MAX-ACCESS  read-create
    STATUS  current
    DESCRIPTION
        "The Real server number."
    ::= { slbNewCfgDrecordVirtRealMappingEntry 4 }

slbNewCfgDrecordEntryState OBJECT-TYPE
    SYNTAX  INTEGER {
	enabled(1),
	disabled(2)
	}
    MAX-ACCESS  read-create
    STATUS  current
    DESCRIPTION
        "Enable/disable a mapping in this table."
    ::= { slbNewCfgDrecordVirtRealMappingEntry 5 }

slbNewCfgDrecordEntryDelete OBJECT-TYPE
    SYNTAX  INTEGER {
        other(1),
        delete(2)
        }
    MAX-ACCESS  read-create
    STATUS  current
    DESCRIPTION
        "By setting the value to delete(2), the entire row is deleted."
    ::= { slbNewCfgDrecordVirtRealMappingEntry 6 }

-- Service Mapping Real Port Table 

slbSmtportTableMaxSize OBJECT-TYPE
    SYNTAX  Integer32 
    MAX-ACCESS  read-only 
    STATUS  current 
    DESCRIPTION 
        "The maximum number of entries in service mapping real port table." 
    ::= { smtportCfg 1 }

slbCurCfgSmtportTable OBJECT-TYPE
    SYNTAX  SEQUENCE OF SlbCurCfgSmtportEntry 
    MAX-ACCESS  not-accessible
    STATUS  current
    DESCRIPTION
        "The service mapping real port table."
    ::= { smtportCfg 2 }

slbCurCfgSmtportEntry OBJECT-TYPE
    SYNTAX  SlbCurCfgSmtportEntry
    MAX-ACCESS  not-accessible
    STATUS  current
    DESCRIPTION
        "A row in the service mapping real port table."
    INDEX   { slbCurCfgSmtportIndex }
    ::= { slbCurCfgSmtportTable 1 }

SlbCurCfgSmtportEntry ::= SEQUENCE {
    slbCurCfgSmtportIndex          Integer32,
    slbCurCfgSmtportNum            INTEGER
    }

slbCurCfgSmtportIndex OBJECT-TYPE 
    SYNTAX  Integer32 
    MAX-ACCESS  read-only 
    STATUS  current 
    DESCRIPTION 
        "The service mapping real port index." 
    ::= { slbCurCfgSmtportEntry 1 }

slbCurCfgSmtportNum OBJECT-TYPE  
    SYNTAX  INTEGER (2..65534)
    MAX-ACCESS  read-only  
    STATUS  current  
    DESCRIPTION 
        "The service mapping real port number."  
    ::= { slbCurCfgSmtportEntry 2 } 

slbNewCfgSmtportTable OBJECT-TYPE
    SYNTAX  SEQUENCE OF SlbNewCfgSmtportEntry 
    MAX-ACCESS  not-accessible
    STATUS  current
    DESCRIPTION
        "The table of real server service ports."
    ::= { smtportCfg 3 }

slbNewCfgSmtportEntry OBJECT-TYPE
    SYNTAX  SlbNewCfgSmtportEntry
    MAX-ACCESS  not-accessible
    STATUS  current
    DESCRIPTION
        "A row in the service mapping real port table."
    INDEX   { slbNewCfgSmtportIndex }
    ::= { slbNewCfgSmtportTable 1 }

SlbNewCfgSmtportEntry ::= SEQUENCE {
    slbNewCfgSmtportIndex          Integer32,
    slbNewCfgSmtportNum            INTEGER,
    slbNewCfgSmtportDelete         INTEGER
    }

slbNewCfgSmtportIndex OBJECT-TYPE 
    SYNTAX  Integer32 
    MAX-ACCESS  read-only 
    STATUS  current 
    DESCRIPTION 
        "The service mapping real port index" 
    ::= { slbNewCfgSmtportEntry 1 }

slbNewCfgSmtportNum OBJECT-TYPE  
    SYNTAX  INTEGER (2..65534)
    MAX-ACCESS  read-create  
    STATUS  current  
    DESCRIPTION 
        "The service mapping real port number."  
    ::= { slbNewCfgSmtportEntry 2 } 

slbNewCfgSmtportDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgSmtportEntry 3 }

slbWlmTableMaxSize OBJECT-TYPE
    SYNTAX Integer32 
    MAX-ACCESS read-only 
    STATUS current 
    DESCRIPTION 
        "The maximum number of entries in Workload Manager table." 
    ::= { wlmCfg 1 }

slbCurCfgWlmTable OBJECT-TYPE
    SYNTAX SEQUENCE OF SlbCurCfgWlmEntry
    MAX-ACCESS not-accessible
    STATUS current
    DESCRIPTION
        "The table of Workload Managers configuration."
    ::= { wlmCfg 2 }

slbCurCfgWlmEntry OBJECT-TYPE
    SYNTAX SlbCurCfgWlmEntry
    MAX-ACCESS not-accessible
    STATUS current
    DESCRIPTION
        "Information about a particular Workload Manager configuration."
    INDEX { slbCurCfgWlmIndex }
    ::= { slbCurCfgWlmTable 1 }
 
SlbCurCfgWlmEntry ::= SEQUENCE {
    slbCurCfgWlmIndex           Integer32,
    slbCurCfgWlmIpAddr          IpAddress,
    slbCurCfgWlmPort            INTEGER
    }

slbCurCfgWlmIndex OBJECT-TYPE
    SYNTAX  Integer32
    MAX-ACCESS  read-only
    STATUS  current
    DESCRIPTION
        "The Workload Manager number" 
    ::= { slbCurCfgWlmEntry 1 }

slbCurCfgWlmIpAddr OBJECT-TYPE
    SYNTAX  IpAddress
    MAX-ACCESS  read-only
    STATUS  current
    DESCRIPTION
        "IP address of the Workload Manager."
    ::= { slbCurCfgWlmEntry 2 }

slbCurCfgWlmPort OBJECT-TYPE
    SYNTAX  INTEGER (0..65534)
    MAX-ACCESS  read-only
    STATUS  current
    DESCRIPTION
        "The port number for the Workload Manager." 
    ::= { slbCurCfgWlmEntry 3 }

slbNewCfgWlmTable OBJECT-TYPE
    SYNTAX SEQUENCE OF SlbNewCfgWlmEntry
    MAX-ACCESS not-accessible
    STATUS current
    DESCRIPTION
        "The table of Workload Managers configuration."
    ::= { wlmCfg 3 }

slbNewCfgWlmEntry OBJECT-TYPE
    SYNTAX SlbNewCfgWlmEntry
    MAX-ACCESS not-accessible
    STATUS current
    DESCRIPTION
        "Information about a particular Workload Manager configuration."
    INDEX { slbNewCfgWlmIndex }
    ::= { slbNewCfgWlmTable 1 }
 
SlbNewCfgWlmEntry ::= SEQUENCE {
    slbNewCfgWlmIndex           Integer32,
    slbNewCfgWlmIpAddr          IpAddress,
    slbNewCfgWlmPort            INTEGER,
    slbNewCfgWlmDelete          INTEGER
    }

slbNewCfgWlmIndex OBJECT-TYPE
    SYNTAX  Integer32
    MAX-ACCESS  read-only
    STATUS  current
    DESCRIPTION
        "The Workload Manager number" 
    ::= { slbNewCfgWlmEntry 1 }

slbNewCfgWlmIpAddr OBJECT-TYPE
    SYNTAX  IpAddress
    MAX-ACCESS  read-create
    STATUS  current
    DESCRIPTION
        "IP address of the Workload Manager."
    ::= { slbNewCfgWlmEntry 2 }

slbNewCfgWlmPort OBJECT-TYPE
    SYNTAX  INTEGER (0..65534)
    MAX-ACCESS  read-create
    STATUS  current
    DESCRIPTION
        "The port number for the Workload Manager." 
    ::= { slbNewCfgWlmEntry 3 }

slbNewCfgWlmDelete OBJECT-TYPE
    SYNTAX  INTEGER {
        other(1),
        delete(2)
        }
    MAX-ACCESS  read-create
    STATUS  current
    DESCRIPTION
        "By setting the value to delete(2), the entire row is deleted."
    ::= { slbNewCfgWlmEntry 4 }

END
