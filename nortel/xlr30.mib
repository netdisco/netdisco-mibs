RAPID-CITY-MIB DEFINITIONS ::= BEGIN

-- Title:       Rapid-City Communications Enterprise MIB
-- Date:        December 4, 1996
-- By:         	Edwin Tsang 
-- Revision:	
--        v1  : 05/28/96 - Initial version from Ian Wallis.
--        v2  : 06/23/96 - VLAN table now has port memberships
--        v3  : 06/27/96 - Added Port table        
--        v4  : 07/03/96 - Rearranged rcSystem group so scalars
--                         are grouped together
--        v5  : 07/29/96 - Modified rcVlan and rcCard groups.
--                         Added rcMirror and rcDipSwitch groups. 
--        v6  : 08/09/96 - Cleaned up rcVlanPortTable and rcTftp 
--                         groups.
--        v7  : 08/21/96 - Added rcTraps group, rcVlanColorCode,
--                         rcSysLastVlanChange, rcError group.
--	  v9  : 09/10/96 - Added rcTblSize group.  
--		           Added rc16x100BaseTX(7) to rcCardType variable. 
--			   Added rcVlanStpTrapEnable to rcVlanEntry.
--			   Added rcStpNewRoot and rcStpTopologyChange traps.
--			   Added rcPortOperation to rcPortEntry.
--			   Added rcSysCpuUtil and rcSysSwitchFabricUtil to
--			   rcSystem.
--			   Added rcVlanHighPriority and rcPortHighPriority.
--	  v10 : 09/23/96 - Changed rcSysNvRam to rcSysNvRamSize.
--			   Added rcVlanRoutingEnable and rcVlanIfIndex.
--			   Added rcIp group.
--	  v11 : 10/01/96 - Added rcSysRmonEnable, rcSysRmonMemSize, and
--                         rcSysLastSaveToNVRam.
-- 	  v12 : 10/16/96 - Added rcSysRmonSaveConfig.
--                         Changed rcIpAdEntBcastAddr to 
--                         rcIpAdEntBcastAddrFormat
--        v13 : 11/1/96  - Added rcTestTypes, rcTestCodesAdded, 
--                         and rcQos.
--	  v14 : 11/12/96 - Added saveToSlaveNVRAM and switchOver to
--			   rcSysAction variable.
--			   Changed range of rcVlanColorCode.
--			   Removed rcPortPerformBridging.
--			   Removed rcPortOperation.
--			   Added rcSysResult.
--			   Added rcSysLastSaveToSlaveNVRam.
--			   Added rcVlanAction and rcVlanResult.
-- 			   Added rcPortAction and rcPortResult.
--	  v15 : 12/04/96 - Added rcSysSupportRouting. 
--			   Changed rcVlanPortMembers.
--			   Added rcVlanMemberType, rcVlanAllowToJoin
--			   	 rcVlanType, rcVlanProtocolId, 
--			         rcVlanSubnetAddr, rcVlanSubnetMask.
--			   Added rcVlanPortType. 
--			   Added rcVlanMacTable.
--			   Added rcChasNumPorts.
--			   Added rcCardPCMCIAType. 
--			   Added rcIpConfTable.
--			   Removed loadFromNVRAM from rcSysAction.
--	  v16 : 12/09/96 - Changed rcVlanProtocolId to an enumeration.
--			   Added rcErrorText.
--			   Maded rcQosProtocol an index in rcQosEntry.
--	  v17 : 12/12/96 - Added rcStgTable and rcStgPortTable.
--			   Changed rcStpNewRoot and rcStpTopologyChange
--			   traps to use rcStgId instead of rcVlanId.
--	  v18 : 12/18/96 - Added rcVlanStgId.
--			   Removed rcVlanStpEnable, rcVlanStpTrapEnable.
--		           Shifted rVlanPortMembers, rcVlanMemberType,
--			   rcVlanNotAllowToJoin.
--		           Added fail(14) to rcPortAction.
--			   Added rcPortDefaultConnector.
--			   Added rcPortActiveConnector.
--			   Renamed all(5) to flushAll(5) to rcPortAction.
--			   Added switchConnector(6) to rcPortAction.
--			   Added types to rcCardType.
--			   Added rcVlanMemberType to rcVlanStaticMembers.
--			   Removed rcVlanPortTrunk
--			   Added rcErrorReturnCode
--			   Added rcTblArVlanByPortAdded
--			   Added rcTblArVlanByPortDeleted
--			   Added rcTblArVlanByProtocolAdded
--			   Added rcTblArVlanByProtocolDeleted
--			   Added rcTblArVlanByIpSubnetAdded
--			   Added rcTblArVlanByIpSubnetDeleted
--			   Added rcTblArIpSubnetsAdded
--			   Added rcTblArIpSubnetsDeleted
--			   Added rcTblArRsvpsAdded
--			   Added rcTblArRsvpsDeleted
--			   Added rcTblArIpMcastAdded
--			   Added rcTblArIpMcastDeleted
--			   Added rcTblArFree
--			   Added rcTblArTblSize
--			   Added rcTblArMcastTblSize
--			   Added rcTblArFreeMcastGroups
--			   Added rcTblBrdgFdbSize
--			   Added rcStgPortMembers
--			   Added rcQosPriority
--			   Added rcStgUnassignedPorts
--	  v19 : 1/6/97  -  Added rcSysTrapRecvVersion
--        v20 : 1/7/97  -  Removed switchConnector(6) from rcPortAction
--                         Added write access to rcPortActiveConnector
--                         Added rcPortStandbyConnectorStatus to 
--                         rcPortTable.
--	  v21 : 1/9/97  -  Renamed rcPortDefaultConnector to
--                         rcPortPrimaryConnector.
--			   Removed write access to rcPortActiveConnector.
--			   Renamed rcPortStandbyConnectorStatus to
--                         rcPortBackupConnectorStatus.
--	                   Renamed rcVlanColorCode to rcVlanColor
--                         Renamed switchOver to cpuSwitchOver.
--                         Changed Access of rcStgId to read-only.
--	  v22 : 1/17/97  - Added rcBoot group
--                         Added rcPing group
--                         Added rcTraceTable
--                         Added rcTrace trap
--                         Added rcBridge Tables
--	  v23 : 1/20/97  - Added rcTraceFeatureId and rcTraceLevel 
--                         objects to rcTraceNotification trap.
--                         Removed rcPingPort from rcPing group.
--                         Added rcBridgeFdbTblSize 
--                         Added rcBridgeStaticTblSize 
--                         Added rcBridgeFilterTblSize 
--                         Removed rcStgPortEnable from 
--                         rcStgPortTable 
--                         Added rcStgPortEnableStg to
--                         rcStgPortTable 
--                         Added rcStgPortInConfigBpdus,
--                         Added rcStgPortInTcnBpdus, 
--                         Added rcStgPortInBadBpdus 
--                         Added rcStgPortOutConfigBpdus,
--                         Added rcStgPortOutTcnBpdus 
--                         Removed ipxAny and snaAny from 
--                         rcVlanProtocolId 
--                         Renamed byMacAddr to bySrcMac in
--                         rcVlanType
--                         Added byDstMcast value to rcVlanType
--	  v24 : 1/23/97  - Added rcSysRmonTrapOption.
--                         Added agent, port, chassis, bridge, ip
--                         to rcTraceFeatureId.
--	  v25 : 1/25/97  - Removed rcTraceRowStatus.
--                         Changed Access of rcTraceFeatureId to Read-only
--                         Added more error codes to rcErrorReturnCode. 
--                         Rearranged the objects in the rcMirrorGroup.
--                         Renamed rcMirrorByPort to rcMirrorByPortEnable
--                         Added rcMirrorSaveConfig to rcMirror.
--                         Added rcWebEnableServer.
--                         Added rcWebAccessTable.
--                         Added rcWebAccessTblSize scalar object.
--                         Added rcVlanAgingTime in rcVlanTable.
--                         Added rcStgPortFastStart in rcStgPortTable.
--                         Added flushDynMemb to rcVlanAction. 
--        v26 : 2/13/97  - Rename downloadSw to downloadSwToFlash 
--                         and added downloadSwToPcmcia to rcTftpAction.
--                         Modified rcIpAdEtReasmMaxSize to be read-only.
--                         Added  "removed" to rcCardOperStatus. 
--                         Added  more featureIds to rcTraceFeatureId. 
--        v27 : 2/19/97  - Added checkSwInFlash and 
--                         checkSwInPcmcia  to rcTftpAction.
--                         Added more result codes to rcTftpResult.
--        v27 : 2/19/97  - Added checkSwInFlash and 
--                         checkSwInPcmcia  to rcSysAction.
--                         Added more result codes to rcSysResult.
--                         Added more result codes to rcTftpResult.
--	  v28 : 2/28/97  - Expanded rcWeb and removed rcWebAccessTbl.
--	  v29 : 3/20/97  - Changed rcCardSerialNum and rcChassisSerialNum
--			   to a DisplayString.
--	  v30 : 3/26/97  - Added rcSysSupportWebServer to rcSystem Group.
--                         Removed rcStgName from rcStgTable.
--                         Changed rcStgId range from 1..50 to 1..25.
--                         Added rcVlanPotentialMembers to rcVlanTable.  
--                         Added rcChasType to rcChassisGroup.
--                         Removed rcChasFanOperStatus from rcChassisGroup.
--                         Added rcChasFanTable.
--                         Modified rcChasPowerSupplyId range.
--                         Added rcErrorSendTrap to rcError group.
--                         Added rcPortType, rcPortAutoNegotiate, rcPortDuplex,
--                         rcPortSetDuplex, rcPortSetSpeed to rcPortTable.
--			   Changed enterprise mib oid from
--			   1024 to 2272.
--	  v31 : 3/31/97  - changed enums for rcChasType.
--                         changed rcF1200 and rcF600 OID. 
--	  v32 : 4/01/97  - renamed rcPortSetSpeed to rcPortAdminSpeed 
--	                 - renamed rcPortSetDuplex to rcPortAdminDuplex 
--	                 - renamed rcPortDuplex to rcPortOperDuplex 
--	                 - Added rcPortOperSpeed to rcPortTable. 
--	                 - Added rcIpFlowTable.
--			 - Removed "both" from trap version.
--			 - Added rcStatGigTable.
--        v33 : 4/21/97  - Added default value for rcStgTaggedBpduAddress.
--                         Removed rcStgTagAccessPortBpdus.
--			   Added rcVlanMacAddress.
--			   Added additional enums to rcErrorReturnCode.
--			   Removed rcStatGigRxFlowControlFrames and
--			   rcStatGigRxRuntFrames.
--                         Added rcStatTbl.
--	  v34 : 5/08/97  - Added a bunch of bridging and routing
--                         counters to the rcStat group.
--	  v35 : 6/09/97  - Added a bunch of bridging and routing
--                         Added rcPortRipEnable, rcPortOspfEnable,
--                         rcPortOspfRtrPriority, rcPortOspfMetric,
--                         rcPortOpsfAuthKey to rcPortTable.
--                         Added additional error codes for ospf.
--                         Added rcStatOspf group.
--                         Added rcStatOspfIfTable.
--                         Added error codes for Ospf.
--                         Added rcIpRoutingRedistributeRipToOspf group.
--                         Added rcIpRoutingRedistributeOspfToRip group.
--                         Added rcIpRoutingRedistributeRipToOspfRouteTable
--                         Added rcIpRoutingRedistributeOspfToRipRouteTable.
--                         Added counters for mismatches in rcStatOspfIfTable.
--                         Added rcIpConfAddrAssigned in rcIpConfTable.
--                         Added rcSysOspfTrapEnable in rcSystem group.
--                         Added rcIpConfOspfTable.
--                         Moved rcIpConfOspfMetric, rcIpConfOspfRtrPriority,
--                         and rcIpOspfAuthKey to rcIpConfOspfTable.
--	  v36 : 6/16/97  - Added rc2x1000BaseFF200, rc8x100BaseTXF200, 
--			   rc16x100BaseTXF200 to rcCardType.
--                         Misc. syntax changes to rcStatEntry group.
--			   Changed all variables that are used as
--			   ifIndex to the InterfaceIndex variable
-- 			   type.
--	  v37 : 6/30/97  - changed range for FanId values.
--			   added additional error codes.
--			   renamed the following variables:
--			   rcMirrorDstPort to rcMirrorByPortMirrorPort
--			   rcMirrorEnableSrcPortOne to rcMirrorByPortEnableMirroredPortOne
--		 	   rcMirrorSrcPortOne to rcMirrorByPortMirroredPortOne.
--			   rcMirrorEnableSrcPortTwo to rcMirrorByPortEnableMirroredPortTwo
--		 	   rcMirrorSrcPortTwo to rcMirrorByPortMirroredPortTwo.
--			   removed rcPing group
--			   removed rcTrace group
--        v38 : 7/09/97  - added new error codes
--			   added new enums to rcTftpResult
--			   added rcStgFastStart to rcStgTable.
--        v39 : 7/15/97  - added InFlowCtrlPkts, OutFlowCtrlPkts to
--                         rcStatGigTable.
--                         removed enum "removed" from rcCardOperStatus.
--                         Added enum "mbps1000" to  rcPortAdminSpeed.
--                         Added new error codes.
--	  v40 : 7/10/97  - added rcIpConfOspfCost group.
--                         added rcIpRoutingRedistributeRipToOspfRouteMetric
--                         and rcIpRoutingRedistributeOspfToRipRouteMetric
--                         removed LeakAllSubnets from 
--                         rcIpRoutingRedistributeRipToOspfTable.
--                         removed Internal, External1 and External2 
--                         from rcIpRoutingRedistributeRipToOspfTable.
--                         Added rcIpRoutingRedistributeOspfToRipUseDefaultMetric
--                         Added rcIpRoutingRedistributeRipToOspfUseDefaultMetric
--                         Added ospf error codes.
--                         Added rcCardPartNumber in rcCardEntry.
--			   Changed saveToSlaveNVRAM to saveToStandbyNVRAM.
--        		   Added rc2x1000BaseDualFF200 to rcCardType. 
--	  v41 : 8/28/97  - Changed rcCardType to new format.
--                         Changed rcChasType to new format.
--			   Removed mbps1000 enumeration.
--			   Removed rcStgFastStart variable.
--	  vigmp : 6/07/97  - Added rcIpConfIgmpTable, rcIgmpGroupTable.
--                         Added rcStatIgmp group.
--                         Added new card types for rcCardType.
--	  v42 : 09/09/97 - Made rcIpAdEntBcastAddrFormat read-only.
--	  v43 : 9/15/97  - added rcIpConfOspfHelloInterval and 
--                         rcIpConfOspfRtrDeadInterval to rcIpConfOspfTable
--                         added rcIpConfOspf group.
--                         moved rcSysOspfTrapEnable to rcIpConfOspf group.
--                         added LsdbTblSize to rcStatOspf group.
--	  v44 : 09/16/97 - Added rcPortIndex to rcStpTopologyChange trap.
--			   Added additional error codes.
--	  v45 : 09/18/97 - Added rcChasPowerSupplyDown rcChasFanDown
--                         traps.
--	  v46 : 09/26/97 - Changed rcSysIpAddr, rcSysNetMask, and rcSysBroadcast
--			   from read-write to read-only.
--	  v47 : 10/28/97 - Added rcSysTrapRecvSrcAddress to rcSysTrapRecvTable. 
--			 - Added enums to rcTftpResult.
--			 - Added "other(n)" enum to rcPortPrimaryConnector,
--		           rcPortActiveConnector, rcPortBackupConnectorStatus,
--                         rcPortAdminSpeed.
--	  v48 : 10/24/97 - Removed rcIpConfOspfExternalMetricType.
--                         Renamed UseDefaultMetric to UseExplicitMetric
--                         and DefaultMetric to ExplicitMetric in
--                         RedistributeRipToOspf and RedistributeOspfToRip
--                         Added ExternalMetricType to RedistributeRipToOspf 
--                         Added rcIpRoutingRedistributeDirectToOspf
--                         and rcIpRoutingRedistributeStaticToOspf grps
--                         removed un used error codes (148, 153, 158).
--                         Added rcIpRoutingRedistributeDirectToRip
--                         and rcIpRoutingRedistributeStaticToRip grps.
--                         Added new error codes for ip addr.
--        v49 : 11/24/97 - Added rcIpRouteTable group. 
--	  v50 : 11/24/97 - Modified the value of rcIpConfOspfMetric 
--	                   Modified the default value of 
--                         rcIpRoutingRedistributeDirectToOspfExplicitMetric. 
--        v51 : 12/01/97 - Changed rcSysTrapRecvVersion to v1.
--                         Added enums to rcTftpAction and rcTftpResult.
--        v52 : 12/03/97 - Added rcHighPriorityMode.  
--	  v53 : 12/18/97 - Added rcIpConfDhcpTable and rcIpDhcpForwardTable.
--        v54 : 12/29/97 - Changed rcVlanPotentialMembers to rcVlanActiveMembers.
--                         Added rcVlanPortDiscardTaggedFrames, 
--                               rcVlanPortDiscardUntaggedFrames, 
--                               rcVlanPortDefaultVlanId.
--                         Added rcSysLastIpAddrChange.
--        v55 : 12/31/97 - Added rcDevice group.
--	  v56 : 01/09/97 - Fixed compiler warning messages and added
--                         default values to some DHCP variables.
--	  v57 : 01/12/97 - Added enums to rcErrorReturnCode.
--			   Changed Max VLAN IDs from 4095 to 4094.
--        v58 : 01/21/98 - Obsoleted rcBoot.
--                         Took rcDeviceLastBootSourceFileNum off from rcDevice.
--                         Added rcDeviceFlashNumFiles, rcDevicePcmciaNumFiles
--                         into rcDevice.
--                         For rcDevice, added invalidDeviceFileNumber(179),
--                         notExecutableDeviceFile(180), deletedDeviceFile(181)
--                         into rcError.
--                         Changed rcDeviceFlashFileMod to rcDeviceFlashFileMode.
--                         For rcDeviceAction, changed squeezePcmica(3) to
--                         squeezePcmcia(3).
--	  v59 : 01/28/98 - Added enums to rcCardType.  
--			   Added vines(13) to rcVlanProtocolId.
--	  v60 : 01/26/98 - Modified enum for rcPortAdminSpeed.
--			   Added enums to rcCardType.
--	  v61 : 02/02/98 - Added rcTestTypesExtLoopBack.
--	  v62 : 02/06/98 - Changed IpDhcpForwardMode enum value.
--		           Added rcDeviceConfigSource and rcDeviceConfigSourceFileNum.
--	  v63 : 02/09/98 - Changed FileNum variables in rcDevice to be FileNames.
--	  v64 : 02/19/97 - Added rcIpFilter group and rcMlt group.
--      v64.1 : 04/09/98 - Modify the two "FIXME" field in rcIpFilter group.
--	  v65 : 02/27/98 - Added more error codes.
--			   Added rcPortLock group.
--			   Added rcPortLocked.
--        v66 : 02/25/98 - Added recoverFlash and recoverPcmcia to rcDeviceAction.
--        v66 : 04/16/98 - Added snoopIpMcastAddrExist, error code 215.
--	v66.1 : 04/02/98 - Added rc2x1000BaseXDWG and rc2x1000BaseXDBB card types.
--      v66.2 : 04/16/98 - Changed snoopIpMcastAddrExist to snoopStaticGroupExist.
--	  v67 : 03/05/98 - Added rcCli group.
--	  v68 : 03/09/98 - Changed all read-write variables that have none(1)
--			   to none(0). 
--			   Added IdList data type.
--			   Added rcSysCommReadWriteLayer3 and rcSysCommReadWriteLayer2. 
--	  v69 : 03/18/98 - Added rcSysAccessPolicyEnable and 
--			   rcSysAccessPolicyTable.
--        v70 : 03/18/98 - Added error code invalidDeviceFileLength
--	  v71 : 03/23/98 - Backed out changes to xxxAction variables that made
--			   none(1) to none(0).
--			 - Added flushSnoopMembers to rcVlanAction.
--	  v72 : 04/21/98 - Added rcIpPolicyAddrTable, 
--                         rcIpPolicyNetTable, rcIpPolicyListTable,
--                         rcIpPolicyRipAnnounceTable, rcIpPolicyOspfAnnounceTable,
--                         rcIpPolicyRipAcceptTable, rcIpPolicyOspfAcceptTable
--	  v73 : 04/29/98 - obsoleted rcIpRoutingRedistribute groups.
--                         added additional error codes.
--	  v74 : 04/30/98 - added "none" to rcIpFilterPortMode. 
--	v74.1 : 05/01/98 - changed the choice order of rcIpFilterPortMode. 
--	  v75 : 05/08/98 - added "resetConsole" and "resetModem" to rcSysAction.
--	  v76 : 05/08/98 - added "rcMltPortType" to rcMltTable. 
--	  v77 : 05/11/98 - Added rcVlanUserDefinedPid. 
--			   Added new enums for rcVlanProtocolId.
--			   Added rcIpConfGlobal group.
--	  v78 : 05/19/98 - Added error codes for rcip accept policies and filters.
--	  v79 : 05/20/98 - Added rcPortAutoNegotiationSupported.
--			   Added rcIpConfGlobalRipHoldDownTime
--	  v80 : 05/11/98 - modified ospfIfAuthKey SYNTAX in rcIpConfOsptTable.
--                         added rcIpConfOspfSpfHoldDownTime to rcIpConfOspf grp
--                         added rcIpConfOspfIfAreaId to rcIpConfOspfTable.
--	  v81 : 05/27/98 - Added rcChasAruMode.
--			   Added rcPortSingleRoutablePort.
-- 			   Deprecated rcPortPerformRouting.
-- 			   Deprecated rcVlanRoutingEnable.
--	  v82 : 05/29/98 - Added error codes for mlt.
--                         Added Default values in rcRipExtEntry & rcArpExtEntry.
--	  v83 : 06/01/98 - Added rcIpConfDhcpAlwaysBroadcast.
--	  v84 : 06/03/98 - Added rcIpVrrp group.
--	  v85 : 06/03/98 - Added rcIpConfOspfAreaTable.
--	  v86 : 06/04/98 - Enhancement in rcVlanTable and
--                         rcVlanIgmpSnoopStaticTable.
-- 	  v87 : 06/05/98 - Removed rcIpVrrp group.
--        v88 : 06/12/98 - Added rcVlanSnoopActiveQuerier,
--                         rcVlanSnoopMRouterExpiration in rcVlan table.
--                         Added rcMltEnable, rcMltLoadBalance,
--                         rcMltDistributionAlgorithm in rcMlt table.
--        v89 : 06/17/98 - Changed rcVlanSnoopActiveMRouterPorts,
--                         rcVlanSnoopActiveQuerier, and
--                         rcVlanSnoopMRouterExpiration to
--                         rcVlanIgmpSnoopActiveMRouterPorts,
--                         rcVlanIgmpSnoopActiveMRouterPorts, and
--                         rcVlanIgmpSnoopMRouterExpiration respectively.
--        v90 : 06/12/98 - Added rcIpConfRipAutoAggrerateEnable,
--                         added additional error codes for route aggregation.
--        v91 : 06/29/98 - Added new trap rcLinkOscillation.
--        v92 : 07/01/98 - Added rcSyslog.
--        v93 : 07/08/98 - Added rcVlanIgmpSnoopAccessTable.
--	  v94 : 07/09/98 - Added rcChasPowerSupplyDetailTable. 
--	  v95 : 07/14/98 - Added rcVlanIgmpSnoopQuerierPort.
--	  v96 : 07/17/98 - Added additional error codes.
--	  v97 : 07/20/98 - Added rcIpFilterMode and rcIpFilterPortDefaultAction.
--			   Added rcMltIfIndex.
--			   Obsoleted rcIpFilterPortMode. 
--			   Added rcDiag group.
--	  v98 : 07/21/98 - Modified the rcIpPolicy group.
--	  v99 : 07/24/98 - Added description for Syslog group.
--	 v100 : 07/24/98 - Added a new card type rc8x10BaseFBB.
--       v101 : 07/29/98 - Added rcIpConfRipGenerateDefaultRoute.
--		         - Added triggerRipUpdate to rcVlanAction.
--	 v102 : 07/30/98 - Changed rcSysAccessPolicyActive to
--                         rcSysAccessPolicyPolicyEnable.
--	 v103 : 07/30/98 - modified the policy table index variable MAX-ACCESS
--                         to read-only.
--	 v104 : 08/04/98 - Added rc10BaseF to rcPortType.
--	 v105 : 08/11/98 - Changed range of rcMltId.
--	 v106 : 08/24/98 - Changed the option definition of rcSyslogHostModuleId
--                         in hexdecimal.
--       v107 : 08/28/98 - Added flushSnoopMRtr to rcVlanAction.
--       v108 : 08/28/98 - Backed out changes made in v106.
--	 v109 : 08/25/98 - Changed name size in policy & ip filter tables.
--       v110 : 09/01/98 - Added rcStgNotAllowedPorts to rcStg group.
--	 v111 : 09/28/98 - Changed rcVlanIgmpSnoopAccessMode options.
--                         Added rcPortPerformMacLearning for rcPortTable.
--       v112 : 10/01/98 - Add rcIpxAddrTbl
--       v113 : 10/06/98 - Added rcIpDvmrp.  Added rcIpConfIgmpRobustness 
--                         and rcIpConfIgmpLastMemberQueryInterval
--	 v114 : 10/06/98 - Added rc4xOC3, rc1xOC12, and rcRMON card types.
--	 v115 : 10/06/98 - Changed rcIpDvmrp table to rcIpConfDvmrpTable.
--       v116 : 09/29/98 - Added new items to rcIpFilter group.
--       v117 : 10/01/98 - Changed rcPortPerformMacLearning to read-write.
--       v118 : 10/07/98 - Changed rcPortPerformMacLearning to
--                         rcPortUnknownMacDiscard.
--       v119 : 09/29/98 - Merged rcIpFilter group from rel1.3.
--                         Added more rcError items.
--	 v120 : 10/15/98 - Added to "rarp" to rcVlanProtocolId.
--       v121 : 10/15/98 - Add rcIpDvmrpEnable into rcIpDvmrp.
--       v122 : 10/15/98 - Changed the range of rcIpConfIgmpRobustness.
--       v123 : 10/20/98 - Added rcStatMlt group.
--       v124 : 10/21/98 - Removed rcIpConfIgmp group.
--       v125 : 10/27/98 - Added rcChasEnableEOCMode, rcPortPerformMacLearning
--                         and rcError 323.
--       v126 : 10/12/98 - added rcIpUdpProtocolTable,  rcIpUdpPortFwdTable,
--                         rcIpUdpPortFwdListTable, rcIpUdpConfBroadcastIntfTable.
--       v127 : 10/30/98 - Added rcVlanIgmpSnoopSenderTable.
--       v128 : 11/02/98 - Added AuthType field to rcIpConfOspfTable.
--       v129 : 11/03/98 - Changed the index keys of rcipIgmpGroupTable.
--       v130 : 11/05/98 - Added enum none(0) to rcVlanIgmpSnoopSenderAction.
--       v131 : 11/05/98 - Added rcChasEocModeAdminStatus and
--                         rcChasEocModeOperStatus. Deleted rcChasEnableEOCMode.
--       v132 : 11/10/98 - Changed rcChasEocModeAdminStatus to read-write and
--                         rcChasEocModeOperStatus to read-only.
--                         Changed aruMixed of rcChasAruMode to aruThree.
--       v133 : 11/11/98 - Added PerformTagging into rcVlanPortTable.
--       v134 : 11/12/98 - Added range limit for rcIpConfigDvmrpTableMetric.
--       v135 : 11/16/98 - Added rcPortNumStateTransition in rcPort.
--       v136 : 11/20/98 - added rcIpConfAdvertiseWhenDown to rcIpConfTable.
--                         added additional error codes.
--       v137 : 11/23/98 - Added new items in rcIpDvmrp and rcIpConfIgmpTable.
--       v138 : 11/24/98 - Added interger range for UpdateInterval, 
--                         TriggeredUpdateInterval, LeafTimeout, NbrTimeout,
--                         and NbrProbeInterval in rcIpConfIgmpTable.
--       v139 : 12/03/98 - Re-built rcIpDvmrp, rcIpDvmrpGlobal & rcIpDvmrpTable.
--       v140 : 12/08/98 - Added IpTosRule under rcIpFilterTable. Added 
--                         rcIpRosRule group with AndMask, OrRule1, OrRule2, 
--                         OrRule3. 
--       v141 : 01/13/99 - Added return code 345 to 364 into rcErrorReturnCode.
--       v142 : 02/01/99 - modified udp protocol port number range.
--       v143 : 03/02/99 - Added static routing group.
--       v144 : 03/04/99 - Added rcPos group.
--       v145 : 03/04/99 - Fixed access error for rcPosPppIpxIfIndex.
--       v146 : 03/08/99 - New return error message for rcDiag.
--       v147 : 03/08/99 - New return error message for static routing.
--       v148 : 03/09/99 - Added rcHprm group.
--       v149 : 03/16/99 - Added rcIpPim group.
--       v150 : 03/16/99 - Removed rcIpPimGlobalJoinPruneInterval.
--       v151 : 04/12/99 - modified rcHprm group.
--       v152 : 04/13/99 - Added Accelar740 and Accelar750 devices.
--       v153 : 04/14/99 - Added rmon history utilization ccalculation ontrol.
--       v154 : 04/20/99 - Added rcLinkFlapDetect, rcPortAllowOverSizeFrame,
--                         rcIpTosRule, rcBridgeUnknownMacDiscard,
--                         rcBridgeManualEdit and rcBridgeAutoLearn.
--       v155 : 04/26/99 - Added Accelar790.
--       v156 : 04/27/99 - Modified rcHprm.
--       v157 : 05/17/99 - Added rcIpConfDirectBroadcastEnable.
--                         Added rcMacViolation trap.
--       v158 : 05/17/99 - Added rcAgentTable.
--       v159 : 05/17/99 - Added rcBridgeStaticMulticastTable.
--       v160 : 05/19/99 - Added rcSysCommReadWriteLayer1.
--       v161 : 06/17/99 - Changed rcBridgeStaticMulticastForwardingPorts
--                         to writable.
--       v162 : 06/29/99 - Added OC3 and OC12 card types to A1200.
--       v163 : 06/30/99 - Added rcIpMulticastArpTable. Removed
--                         rcBridgeStaticMulticastForwardingPorts from
--                         rcBridgeStaticMulticastTable index.
--       v164 : 07/08/99 - Added rcSysDiagnosticsEnable.
--       v165 : 07/12/99 - Added Mib descriptions for the unknown mac discard table, the Auto
--                         Learn table, and the Manual Edit table.
--       v166 : 08/29/99 - Added rcV1Traps group (for BayStack).
--       v167 : 08/30/99 - Added rcSysDramSize, DramUsed, DramFree,
--                         DramMaxBlockFree.
--       v168 : 08/30/99 - Added Radius Global group and Radius Server Table.
--       v169 : 08/30/99 - Added rcPos group.
--                         Added rcIpConfV2Table, rcIpConfOspfV2Table,
--                         rcArpExtV2Table, rcRipExtV2Table,
--                         rcStatOspfIfV2Table, and rcIpMulticastTable.
--
-- 
--       v260 : 11/03/98 - Added changes to support Raptillion (Accelar2k)
--                         Added rc2k24x100BaseTX and rc2k24x100BaseFX cards.
--                         Added rcAccelar2kChasPortOperStatus.
--       v261 : 12/09/98 - Updated rcCardType to use Accelar2k card encoding
--                         scheme.
--       v262 : 12/11/98 - Updated rcChasType to use Accelar2k encoding.
--       v263 : 01/05/99 - Renamed rcAccelar2k group to rc2k.
--       v264 : 01/28/99 - Added rc2kCpuEthernetPortTable,
--                         rc2kCpuSerialPortTable, rc2kDevice,
--                         rc2kBootConfig, and rc2kCardTable.
--	 v265 : 02/01/99 - Added more items in rc2kBootConfig.
--	 v266 : 02/25/99 - Changed the value range of rcChasPowerSupplyId.
--	 v267 : 03/03/99 - Added rc2kDevicePcmciaPresent.
--	 v268 : 03/05/99 - Added static route table.
--	                   Modified rcIpUpdPortFwdListId range.
--	 v269 : 03/15/99 - Changed rcStgPortMembers to allow more ports.
--	 v270 : 03/18/99 - Added more variables in rc2kCardBackType.
--	 v271 : 03/25/99 - Added rc2kChassisAmbientLowerTemperature and
--			   rc2kChassisAmbientUpperTemperature.
--	 v272 : 03/26/99 - Added rc2kTemperature trap. 
--	 v273 : 04/07/99 - Added error return messages for static routing
--                         and 2k copy file. 
--	 v274 : 04/07/99 - Added err rtrn msg copyFileInvalidMultipleCopying
--	 v275 : 04/08/99 - Changed QosLevel to UserPriority.
--	 v276 : 04/30/99 - Changed UserPriority back to QosLeve.  
--                         Added more items in rcIpFilterTable.
--                         Added rc2kQos group.
--	 v277 : 05/13/99 - Updated rc2k mibs to support multiple CPUs.
--			   Updated all QosLevel variables to be (1..8).
--			   Added rcVlanTosValue to rcVlan group.
--	 v278 : 05/14/99 - Merged the rcLinkFlapDetect group from accelar1k.
--	 v279 : 05/26/99 - Added rc2kMdaCardTable.
--	 v280 : 05/26/99 - Changed rcVlanPortVlanIds and rcMltVlanIds to 4096.
--	 v281 : 06/07/99 - Changed in rc2kQosQosTable.
--	 v282 : 07/13/99 - Removed resetWebCounters from rcSysAction.
--                         Modified rcWeb group.
--	 v283 : 07/15/99 - Added default values for rcIpFilterTable and
--			   rc2kQosTrafficProfileTable.
--			   Changed rcVlanPortDefaultVlanId to (0..4094).
--			   Added rcIpFilterStopOnMatch.
--			   Deprecated rcVlanHighPriority, rcVlanRoutingEnable,
--			   rcPortHighPriority, rcPortUserPriority,
--			   rcBridgeFdbPriority, rcBridgeStaticPriority,
--			   rcIpTosRule, rcIpFilterHighPriority
--			   rcIpFilterCopyToCpu, rcIpFilterUsePktLimit
--			   rcIpFilterPktLimit, rcIpFilterIpTosRule. 
--       v284 : 07/16/99   Added rcDiagDiagnosticsEnable in rcDiag group.
--       v285 : 07/16/99   Made DisplayString range and integer range for
--			   rcWeb objects.
--                         Excluded rc2kCardFrontMacAddr. 
--	 v286 : 07/29/99   Increased rcMltId from 8 to 32.
--	 v287 : 08/02/99   Changed number for rcMdaCardType.
--			   Changed chassis type from 2400/2450 to 8010/8006.
--	 v288 : 08/10/99   Added rc2kMGSFM.
--	 v289 : 08/20/99   Added rcChasGlobalFilterEnable, rcChasVlanBySrcMacEnable.
--	   		   Added rc2kBootConfigSwVersion. 
--	 v290 : 09/07/99   Added rc2k8x1000BaseIC, rc2k8x1000BaseTX,
--                         rc2k16x1000BaseSXBB in rc2kCardFrontType.
--	 v291 : 09/10/99   Added rc2k8xATM in rc2kCardFrontType.
--	 v292 : 09/22/99   Added rcPortVendorDescr, and rcGbicLx, rcGbicSx,
--                         rcGbicXd, rcGbicCu, rcGbicOther to rcPortType.
--	 v293 : 09/23/99   Changed trap numbering.
--	 v294 : 09/23/99   Added rcA8600, rcA8650, rcA8100, rcA8150. 
--			   Added rcChasFanAmbientTemperature.
--	 v295 : 10/11/99   Increased rcStatMltxxx ranges from (1..8) to (1..32).
--	 v296 : 10/15/99   Added rc2kQosQosName in rc2kQosTable.
--                         Changed rcIpFilterId ranges fr (1..1024) to (1..4096).
--	 v297 : 10/11/99   Changed rc2kQosQosName to read-only.
--       v298 : 10/06/99   Removed rcDiagDiagnosticsEnable and rcDiagSaveConfig
--                         from rcDiag group.
--	 v299 : 10/20/99   Changed QosLevel to (0..7) from (1..8). Added QosRow
--                         to QOS tables as index.  Changed rcVlanQosLevel,
--                         rcPortQosLevel, rcBridgeFdbQosLevel, and
--                         rcBridgeStaticQosLevel to (0..7). Added new Enable
--                         variables for rcIpFilterDiffServMatch and
--                         rcIpFilterDiffServModify variables.  Changed range of
--                         rcIpFilterDiffServMatch and rcIpFilterDiffServModify
--                         to (0..7).
--	 v300 : 10/22/99   Added new rcErrorReturnCode from 397 to 404. 
--	 v301 : 11/05/99   Added rcStatBridgeOutFrames. 
--	 v302 : 11/10/99   Added rcA750S sysObjectID. 
--			   Changed all default values for QosLevel from
--			   'level2' to 'level1'. 
--	 v303 : 11/07/99   Added more rcPortType for oc3c, oc12c, ds3, and e3. 
--	 v304 : 12/02/99   Changed group name rcHprm to rcOrna. 
--	 v305 : 12/15/99   Added rc2kChassisMgmtMacAddr. 
--	 v306 : 12/17/99   Added rcGbicNone(22) to the rcPortType. 
--	 v307 : 12/20/99   Changed rc2kChassisMgmtMacAddr to
--                         rc2kCpuEthernetPortMgmtMacAddr. 
--	 v308 : 12/21/99   Removed  rcSysGlobalFilterEnable and
--                         rcSysVlanBySrcMacEnable.
--                         Added nre error return code 405 and 406.
--	                   Added rc2kMg8x1000BaseIC in rc2kCardFrontType.
--	 v309 : 12/24/99   Added mltMoreThan4PortsInMgMlt(408),
--                         protocolRulesForThePortHasExceeded16(409) in
--                         rcErrorReturnCode.
--	 v310 : 12/26/99   Added 9 more variables in rc2kAtm1483ElanTable.
--	 v311 : 12/29/99   Added ATM MDA card types.
--			   Added rc2kCardFrontMasterIO.
--


-- ISSUES
--
-- None outstanding

IMPORTS
	MODULE-IDENTITY				FROM SNMPv2-SMI
--	TEXTUAL-CONVENTION                  	FROM SNMPv2-TC
	enterprises,  IpAddress, TimeTicks	FROM RFC1155-SMI
	OBJECT-TYPE 				FROM RFC-1212
	DisplayString		 		FROM RFC1213-MIB
	RowStatus, TruthValue, MacAddress 	FROM SNMPv2-TC
	Gauge32, NOTIFICATION-TYPE		FROM SNMPv2-SMI
	Counter32, Counter64			FROM SNMPv2-SMI
        InterfaceIndex                          FROM IF-MIB
	AtmAddr             			FROM ATM-TC-MIB; 

rapidCity MODULE-IDENTITY
       LAST-UPDATED 	"9701010000Z"
       ORGANIZATION 	"Bay Networks, Rapid-City Group"
       CONTACT-INFO 	"
				 	Edwin Tsang
                	 Postal: 	Bay Networks, Inc. 
                       			4401 Great America Parkway 
                       			Santa Clara, CA 95052-8185 

                   	 Tel: 		408-495-6159
                   	 Fax: 		408-495-5215 
                	 E-mail:	edwin_tsang@baynetworks.com 
			"
       DESCRIPTION 	"Enterprise MIB for the Accelar product family."
       ::= { enterprises 2272 }

-- 
-- Local defines to avoid having to pull-in other RFC's.
--
BridgeId	::= OCTET STRING (SIZE (8))
Timeout		::= Integer32
EnableValue     ::= INTEGER { enable(1), disable(2) }

--
-- This variable type is used through out the Rapid-City enterprise
-- MIB to denote the standard ifIndex in mib-2. 
--
-- InterfaceIndex	::= INTEGER

--
-- The string is 88 octets long, for a total of 704 bits. Each bit
-- corresponds to a port, as represented by its ifIndex value . When a
-- bit has the value one(1), the corresponding port is a member of the
-- set. When a bit has the value zero(0), the corresponding port is not
-- a member of the set. The encoding is such that the most significant
-- bit of octet #1 corresponds to ifIndex 0, while the least significant
-- bit of octet #88 corresponds to ifIndex 703."
--
PortSet 	::= OCTET STRING (SIZE (88))
IdList 		::= OCTET STRING (SIZE (0..4096))


--
-- Additions to resolve some SNMP V2 dependencies so we don't
-- have to pull-in a lot of mib modules.
--                  
internet  	OBJECT IDENTIFIER ::= { iso org(3) dod(6) 1 }
snmpV2 		OBJECT IDENTIFIER ::= { internet 6 }
snmpModules 	OBJECT IDENTIFIER ::= { snmpV2 3 }
snmpMIB 	OBJECT IDENTIFIER ::= { snmpModules 1 }
snmpMIBObjects 	OBJECT IDENTIFIER ::= { snmpMIB 1 }
snmpTraps 	OBJECT IDENTIFIER ::= { snmpMIBObjects 5 }


--
-- Enterprise specific MIB groups
--
rcMgmt 			OBJECT IDENTIFIER ::= { rapidCity 1 }
rcA1100			OBJECT IDENTIFIER ::= { rapidCity 2 }
rcA1250    		OBJECT IDENTIFIER ::= { rapidCity 6 }
rcA1150    		OBJECT IDENTIFIER ::= { rapidCity 7 }
rcA1200    		OBJECT IDENTIFIER ::= { rapidCity 8 }
rcA1050    		OBJECT IDENTIFIER ::= { rapidCity 9 }
rcA740                  OBJECT IDENTIFIER ::= { rapidCity 20 }
rcA750                  OBJECT IDENTIFIER ::= { rapidCity 21 }
rcA790                  OBJECT IDENTIFIER ::= { rapidCity 22 }
rcA750S                 OBJECT IDENTIFIER ::= { rapidCity 23 }
rcA8006    		OBJECT IDENTIFIER ::= { rapidCity 280887558 }
rcA8010    		OBJECT IDENTIFIER ::= { rapidCity 280887562 }
rcA8610    		OBJECT IDENTIFIER ::= { rapidCity 30 }
rcA8606    		OBJECT IDENTIFIER ::= { rapidCity 31 }
rcA8110    		OBJECT IDENTIFIER ::= { rapidCity 32 }
rcA8106    		OBJECT IDENTIFIER ::= { rapidCity 33 }
rcBayStack        OBJECT IDENTIFIER ::= { rapidCity 40 }


rcSystem  		OBJECT IDENTIFIER ::= { rcMgmt 1 }
rcTftp 	  		OBJECT IDENTIFIER ::= { rcMgmt 2 }
rcVlan 	  		OBJECT IDENTIFIER ::= { rcMgmt 3 }
rcChassis 		OBJECT IDENTIFIER ::= { rcMgmt 4 }
rcMirror		OBJECT IDENTIFIER ::= { rcMgmt 5 }
rcDipSwitch		OBJECT IDENTIFIER ::= { rcMgmt 6 }
rcTblSize		OBJECT IDENTIFIER ::= { rcMgmt 7 }
rcIp			OBJECT IDENTIFIER ::= { rcMgmt 8 }
rcArp			OBJECT IDENTIFIER ::= { rcMgmt 9 }
rcRip			OBJECT IDENTIFIER ::= { rcMgmt 10 }
rcTest			OBJECT IDENTIFIER ::= { rcMgmt 11 }
rcStat			OBJECT IDENTIFIER ::= { rcMgmt 12 }
rcStg			OBJECT IDENTIFIER ::= { rcMgmt 13 }
rcBridge		OBJECT IDENTIFIER ::= { rcMgmt 14 }
rcBoot			OBJECT IDENTIFIER ::= { rcMgmt 15 }
rcDevice		OBJECT IDENTIFIER ::= { rcMgmt 16 }
rcMlt			OBJECT IDENTIFIER ::= { rcMgmt 17 }
rcWeb			OBJECT IDENTIFIER ::= { rcMgmt 18 }
rcCli			OBJECT IDENTIFIER ::= { rcMgmt 19 }
rcError			OBJECT IDENTIFIER ::= { rcMgmt 20 }
rcTraps			OBJECT IDENTIFIER ::= { rcMgmt 21 }
rcSyslog		OBJECT IDENTIFIER ::= { rcMgmt 22 }
rcDiag          	OBJECT IDENTIFIER ::= { rcMgmt 23 }
rcIpx 			OBJECT IDENTIFIER ::= { rcMgmt 24 }
rcOrna                  OBJECT IDENTIFIER ::= { rcMgmt 25 }
rcPos                   OBJECT IDENTIFIER ::= { rcMgmt 26 }
rcLinkFlapDetect        OBJECT IDENTIFIER ::= { rcMgmt 27 }
rcV1Traps               OBJECT IDENTIFIER ::= { rcMgmt 28 }
rcRadius                OBJECT IDENTIFIER ::= { rcMgmt 29 }
rcSsh                   OBJECT IDENTIFIER ::= { rcMgmt 34 }
rc2k			OBJECT IDENTIFIER ::= { rcMgmt 100 }


-- LOGICAL (System) Elements

rcSysIpAddr OBJECT-TYPE
        SYNTAX        IpAddress
        MAX-ACCESS        read-only
        STATUS        current
        DESCRIPTION   "This entity's IP address."
        ::= { rcSystem 1 }

rcSysNetMask OBJECT-TYPE
        SYNTAX        IpAddress
        MAX-ACCESS        read-only
        STATUS        current
        DESCRIPTION   "This entity's subnet mask."
        ::= { rcSystem 2 }

rcSysBroadcast OBJECT-TYPE
        SYNTAX        IpAddress
        MAX-ACCESS        read-only
        STATUS        current
        DESCRIPTION   "This entity's broadcast address."
        ::= { rcSystem 3 }

-- Community Strings

rcSysCommReadWriteAll OBJECT-TYPE
        SYNTAX        DisplayString (SIZE (0..20))
        MAX-ACCESS        read-write
        STATUS        current
        DESCRIPTION   "When an SNMP message is received by this entity, the
                      community string in the message is compared with this
                      string first.  If it matches, read-write access is
                      granted to all items in the MIB.  If it doesn't
                      match, the rcSysCommReadWrite string is compared next."
        ::= { rcSystem 4 }

rcSysCommReadWrite OBJECT-TYPE
        SYNTAX        DisplayString (SIZE (0..20))
        MAX-ACCESS        read-write
        STATUS        current
        DESCRIPTION   "When an SNMP message is received by this entity, the
                      community string in the message is compared with this
                      string second.  If it matches, read-write access is
                      granted to all items in the MIB except community
                      strings.  (Community strings appear empty when read
                      and return a no such name error when an attempt is
                      made to write them.)  If it doesn't match, the
                      rcSysCommReadWriteLayer3 string is compared next."
        ::= { rcSystem 5 }

rcSysCommReadOnly OBJECT-TYPE
        SYNTAX        DisplayString (SIZE (0..20))
        MAX-ACCESS        read-write
        STATUS        current
        DESCRIPTION   "When an SNMP message is received by this entity, the
                      community string in the message is compared with this
                      string third.  If it matches, read-only access is
                      granted to all items in the MIB except community
                      strings.  (Community strings appear empty when read.)
                      If it doesn't match, no access is granted, no
                      response is sent back to the SNMP requester, and
                      SNMP traps are sent to the SNMP trap receiver(s) if
                      configured."
        ::= { rcSystem 6 }

-- Other

rcSysVersion OBJECT-TYPE
	SYNTAX 		DisplayString (SIZE (0..20))
	MAX-ACCESS 		read-only
	STATUS 		current
	DESCRIPTION	"Software version running on device"
	::= { rcSystem 7 }

rcSysAction OBJECT-TYPE
        SYNTAX       INTEGER {
                         none(1),               -- none of the following
                         hardReset(2),          -- power on tests
                         softReset(3),          -- reset w/o power on tests
                         saveToNVRAM(4),        -- save current config to NVRAM
                         resetCounters(5),      -- reset all statistic counters
                         saveToStandbyNVRAM(6), -- save config to slave NVRAM
                         cpuSwitchOver(7),      -- CPU board switch-over
		         checkSwInFlash(8),       
		         checkSwInPcmcia(9),
			 resetConsole(10),
			 resetModem(11),
			 flushIpRouteTbl(12),
			 saveRuntimeConfig(13),		-- 8k only
			 saveRuntimeConfigToSlave(14),	-- 8k only
			 saveBootConfig(15),		-- 8k only
			 saveSlaveBootConfig(16) 	-- 8k only
--			 reserve(17)
--			 reserve(18)
--			 reserve(19)
--			 reserve(20)
--			 reserve(21)
 	              }
        MAX-ACCESS        read-write
        STATUS        current
	DESCRIPTION   "Initiate a system action."
	DEFVAL 	      { none }
        ::= { rcSystem 8 }

rcSysResult OBJECT-TYPE
	SYNTAX       INTEGER {
		         none(1),		-- none of the following
		         inProgress(2),		-- in progress
		         success(3),		-- success
		         fail(4),		-- failure
		         flashReadFailed(5),	-- could not read from flash
		         pcmciaReadFailed(6),	-- could not read from pcmcia
		         crcCheckFailed(7),
                         noStandbyCpu(8)
	              }
        MAX-ACCESS        read-only
        STATUS        current
	DESCRIPTION   "Result from the last system action."
	DEFVAL 	      { none }
        ::= { rcSystem 9 }

rcSysLastChange OBJECT-TYPE
        SYNTAX        TimeTicks
        MAX-ACCESS        read-only
        STATUS        current
        DESCRIPTION   "Last management initiated configuration 
		      change since sysUpTime."
        ::= { rcSystem 10 }

rcSysLastVlanChange OBJECT-TYPE
        SYNTAX        TimeTicks
        MAX-ACCESS        read-only
        STATUS        current
        DESCRIPTION   "Last management initiated VLAN configuration 
		      change since sysUpTime."
        ::= { rcSystem 11 }

rcSysLastStatisticsReset OBJECT-TYPE
        SYNTAX        TimeTicks
        MAX-ACCESS        read-only
        STATUS        current
        DESCRIPTION   "Last management initiated statistics reset 
		      since sysUpTime."
        ::= { rcSystem 12 }

-- Global Statistics

rcSysBufferUtil OBJECT-TYPE
	SYNTAX        INTEGER (0..100)
	MAX-ACCESS        read-only
	STATUS        current
	DESCRIPTION   "Buffer utilization as a percentage of the
                      total amount of buffer space in the system.  
                      A high value indicates congestion."
	::= { rcSystem 13 }

rcSysBufferUtilPeak OBJECT-TYPE
	SYNTAX        INTEGER (0..100)
	MAX-ACCESS        read-only
	STATUS        current
	DESCRIPTION   "The largest buffer utilization since sysUpTime"
	::= { rcSystem 14 }

rcSysBufferUtilPeakTime OBJECT-TYPE
	SYNTAX        TimeTicks
	MAX-ACCESS        read-only
	STATUS        current
	DESCRIPTION   "Timestamp for rcSysPeakBandwidth"
	::= { rcSystem 15 }

rcSysNVRamSize OBJECT-TYPE
	SYNTAX        Gauge32
	MAX-ACCESS        read-only
	STATUS        current
	DESCRIPTION   "Total Non-volatile RAM in Kbytes"
	::= { rcSystem 16 }

rcSysNVRamUsed OBJECT-TYPE
	SYNTAX        Gauge32
	MAX-ACCESS        read-only
	STATUS        current
	DESCRIPTION   "Non-volatile RAM in use in Kbytes"
	::= { rcSystem 17 }

rcSysLastSaveToNVRam    OBJECT-TYPE
        SYNTAX        TimeTicks
        MAX-ACCESS        read-only
        STATUS        current
        DESCRIPTION   "SysUpTime of the last time when NVRAM was
                      written to.  This could be a save of the system
                      configuration or via a file transfer of a
                      configuration file."
        ::= { rcSystem 18 }

rcSysLastSaveToStandbyNVRam OBJECT-TYPE
        SYNTAX        TimeTicks
        MAX-ACCESS        read-only
        STATUS        current
        DESCRIPTION   "SysUpTime of the last time when the standby NVRAM
                      (on the back-up CPU board) was written to."
        ::= { rcSystem 19 }

rcSysCpuUtil OBJECT-TYPE
        SYNTAX        Gauge32
        MAX-ACCESS        read-only
        STATUS        current
        DESCRIPTION   "Percentage of CPU utilization"
        ::= { rcSystem 20 }

rcSysSwitchFabricUtil OBJECT-TYPE
        SYNTAX        Gauge32
        MAX-ACCESS        read-only
        STATUS        current
        DESCRIPTION   "Percentage of Switching Fabric utilization"
        ::= { rcSystem 21 }

rcSysRmonMemSize OBJECT-TYPE
        SYNTAX        INTEGER (250000..4000000)
        MAX-ACCESS        read-write
        STATUS        current
        DESCRIPTION   "Amount of RAM in bytes to allocate for RMON
                      to use when rcSysRmonEnable is TRUE."
        ::= { rcSystem 22 }

rcSysRmonEnable OBJECT-TYPE
        SYNTAX        TruthValue
        MAX-ACCESS        read-write
        STATUS        current
        DESCRIPTION   "Control whether the RMON feature should be
                      enabled.

		      To enable the RMON feature, set this variable to
		      true.  The RMON agent in the device will get 
                      started immediately if the amount of memory
		      specified by rcSysRmonMemSize is currently
		      available in the device.

		      To disable the RMON feature, set this variable to
		      false, save the new setting to NVRAM, and reboot
		      the device.  After the device is rebooted the
		      RMON agent will not be operational." 
        ::= { rcSystem 23 }

rcSysRmonSaveConfig OBJECT-TYPE
        SYNTAX        TruthValue
        MAX-ACCESS        read-write
        STATUS        current
        DESCRIPTION   "Control whether RMON configuration information 
                      should be saved to NVRAM so RMON settings can 
                      be automatically reinstalled after a system
                      reboot. 

		      Setting rcSysRmonSaveConfig to true does not 
		      immediately save the configuration information.
		      The save happens when the rcSysAction variable 
		      is set to 'saveToNVRAM(4)'.

                      This option is only meaningful when the 
                      rcSysRmonEnable variable is set to true."
        ::= { rcSystem 24 }

rcSysRmonTrapOption OBJECT-TYPE
        SYNTAX        INTEGER {
		 	 toOwner(1),
			 toAll(2)
		      }
        MAX-ACCESS        read-write
        STATUS        current
        DESCRIPTION   "Used to indicate whether RMON traps should be
		      sent to only the owner of the RMON alarm (i.e.,
		      the manager that created the alarm entry) or 
		      all trap recipients in the system trap receiver
		      table."
	DEFVAL	      { toOwner }
        ::= { rcSystem 25 }

rcSysSupportRouting OBJECT-TYPE
        SYNTAX        TruthValue
        MAX-ACCESS        read-only
        STATUS        current
        DESCRIPTION   "Used to indicate whether routing is supported
                      in this product."
        ::= { rcSystem 26 }

rcSysSupportWebServer OBJECT-TYPE
        SYNTAX        TruthValue
        MAX-ACCESS        read-only
        STATUS        current
        DESCRIPTION   "Used to indicate whether WebServer is supported
                      in this product."
        ::= { rcSystem 27 }

rcSysLastIpAddrChange OBJECT-TYPE
        SYNTAX        TimeTicks
        MAX-ACCESS        read-only
        STATUS        current
        DESCRIPTION   "Last management initiated IP address change 
                       since sysUpTime.  Any addition or deletion of
                       an IP address to a single routable port or
                       a VLAN is time-stamped by this variable."
        ::= { rcSystem 28 }

rcSysCommReadWriteLayer3 OBJECT-TYPE
        SYNTAX        DisplayString (SIZE (0..20))
        MAX-ACCESS        read-write
        STATUS        current
        DESCRIPTION   "When an SNMP message is received by this entity, the
                      community string in the message is compared with this
                      string third.  If it matches, read-write access is 
		      granted to all Layer-3 items in the MIB except community
                      strings.  (Community strings appear empty when read
                      and return a no such name error when an attempt is
                      made to write them.)  If it doesn't match, the
                      rcSysCommReadWriteLayer2 string is compared next."
        ::= { rcSystem 29 }

rcSysCommReadWriteLayer2 OBJECT-TYPE 
        SYNTAX        DisplayString (SIZE (0..20)) 
        MAX-ACCESS        read-write 
        STATUS        current 
        DESCRIPTION   "When an SNMP message is received by this entity, the 
                      community string in the message is compared with this 
                      string fourth.  If it matches, read-write access is 
                      granted to all Layer-2 items in the MIB except community
                      strings.  (Community strings appear empty when read 
                      and return a no such name error when an attempt is
                      made to write them.)  If it doesn't match, the
                      rcSysCommReadOnly string is compared next." 
        ::= { rcSystem 30 }

rcSysAccessPolicyEnable OBJECT-TYPE
        SYNTAX        TruthValue
        MAX-ACCESS        read-write
        STATUS        current
        DESCRIPTION   "Used to configure the system access policy feature.
		      if 'true', the rcSysAccessPolicyTable is examined to
		      determine which packets should be allowed or denied
                      access to this device." 
	DEFVAL	      { false }
        ::= { rcSystem 31 }

rcSysDefaultRuntimeConfigFileName OBJECT-TYPE
        SYNTAX        DisplayString
        MAX-ACCESS        read-only
        STATUS        current
        DESCRIPTION   "default config."
        ::= { rcSystem 32 }
 
rcSysDefaultBootConfigFileName OBJECT-TYPE
        SYNTAX        DisplayString
        MAX-ACCESS        read-only
        STATUS        current
        DESCRIPTION   "default boot config."
        ::= { rcSystem 33 }
 
rcSysConfigFileName OBJECT-TYPE
        SYNTAX        	DisplayString (SIZE(0..64))
        MAX-ACCESS        	read-write
        STATUS        	current
        DESCRIPTION   	"File name used in conjunction with rcSysAction.

			If rcSysAction is set to 'saveRuntimeConfig' or
			'saveRuntimeConfigToSlave' then this file name
			will be used instead of the file name specified
			in rcSysDefaultRuntimeConfigFileName.  

			If rcSysAction is set to 'saveBootConfig' or
			'saveBootConfigToSlave' then this file name will
			be used insteaad of the file name specified in
			rcSysDefaultBootConfigFileName.

			If the file name is blank (i.e., nothing is
			entered) then the default file name will be
			used."
        ::= { rcSystem 34 }
 
rcSysLastRunTimeConfigSave OBJECT-TYPE
        SYNTAX        TimeTicks
        MAX-ACCESS        read-only
        STATUS        current
        DESCRIPTION   "SysUpTime of the last time when the run time
                      configuration was written to."
        ::= { rcSystem 35 }

rcSysLastRunTimeConfigSaveToSlave OBJECT-TYPE
        SYNTAX        TimeTicks
        MAX-ACCESS        read-only
        STATUS        current
        DESCRIPTION   "SysUpTime of the last time when the run time
                      configuration was written to slave NVRAM."
        ::= { rcSystem 36 }

rcSysLastBootConfigSave OBJECT-TYPE
        SYNTAX        TimeTicks
        MAX-ACCESS        read-only
        STATUS        current
        DESCRIPTION   "SysUpTime of the last time when the boot
                      configuration was written to."
        ::= { rcSystem 37 }

rcSysLastBootConfigSaveOnSlave OBJECT-TYPE
        SYNTAX        TimeTicks
        MAX-ACCESS        read-only
        STATUS        current
        DESCRIPTION   "SysUpTime of the last time when the boot
                      configuration was written on the slave NVRAM."
        ::= { rcSystem 38 }

rcSysRmonUtilizationMethod OBJECT-TYPE
        SYNTAX        INTEGER {
                         halfDuplex(1),
                         fullDuplex(2)
                      }
        MAX-ACCESS        read-write
        STATUS        current
        DESCRIPTION   "Used to control whether RMON should use a half-duplex
                       or full-duplex formula to calculate port utilization.
                       When set to 'halfDuplex', RMON will use InOctets and
                       the port's speed to calculate port utilization (this
                       is the standard RMON rfc1271 convention).
                       When set to 'fullDuplex', RMON will use InOctets and
                       OutOctets and 2X the port's speed to calculate port
                       utilization. Furthermore, if this variable is set to
                       'fullDuplex', but the port is operating in a
                       half-duplex mode, the calculation defaults back to
                       the rfc1271 convention."
        DEFVAL        { halfDuplex }
        ::= { rcSystem 39 }
 
rcSysCommReadWriteLayer1 OBJECT-TYPE
        SYNTAX        DisplayString (SIZE (0..20))
        MAX-ACCESS        read-write
        STATUS        current
        DESCRIPTION   "read-write L1 access"
        ::= { rcSystem 40 }

rcSysOtherBufferUtil OBJECT-TYPE
        SYNTAX        Gauge32
        MAX-ACCESS        read-only
        STATUS        current
        DESCRIPTION   "bw currently consumed"
        ::= { rcSystem 41 }
 
rcSysOtherBufferUtilPeak OBJECT-TYPE
        SYNTAX        Gauge32
        MAX-ACCESS        read-only
        STATUS        current
        DESCRIPTION   "peak bw since reset"
        ::= { rcSystem 42 }

rcSysOtherBufferUtilPeakTime OBJECT-TYPE
        SYNTAX        TimeTicks
        MAX-ACCESS        read-only
        STATUS        current
        DESCRIPTION   "timestamp for rcSysPeakBw"
        ::= { rcSystem 43 }
 
rcSysOtherCpuUtil OBJECT-TYPE
        SYNTAX        Gauge32
        MAX-ACCESS        read-only
        STATUS        current
        DESCRIPTION   "% cpu utilization"
        ::= { rcSystem 44 }

rcSysOtherSwitchFabricUtil OBJECT-TYPE
        SYNTAX        Gauge32
        MAX-ACCESS        read-only
        STATUS        current
        DESCRIPTION   "% switch fabric util"
        ::= { rcSystem 45 }

rcSysDramSize OBJECT-TYPE
        SYNTAX        Integer32
        MAX-ACCESS        read-only
        STATUS        current
        DESCRIPTION   "Dram size in mega-bytes"
        ::= { rcSystem 46 }
 
rcSysDramUsed OBJECT-TYPE
        SYNTAX        Gauge32
        MAX-ACCESS        read-only
        STATUS        current
        DESCRIPTION   "Dram used in percentage"
        ::= { rcSystem 47 }
 
rcSysDramFree OBJECT-TYPE
        SYNTAX        Integer32
        MAX-ACCESS        read-only
        STATUS        current
        DESCRIPTION   "Dram free size in kilo-bytes"
        ::= { rcSystem 48 }
 
rcSysDramMaxBlockFree OBJECT-TYPE
        SYNTAX        Integer32
        MAX-ACCESS        read-only
        STATUS        current
        DESCRIPTION   "Dram max block free size in kilo-bytes"
        ::= { rcSystem 49 }
 

-- Trap Receiver Table
 
rcSysTrapRecvTable OBJECT-TYPE
        SYNTAX        SEQUENCE OF RcSysTrapRecvEntry
        MAX-ACCESS        not-accessible
        STATUS        current
        DESCRIPTION   "The trap receiver table (0 to 25 entries).  This
                      table lists the addresses of Network Management
                      Stations that should receive trap messages from 
                      this entity when an exception condition occurs."
        ::= { rcSystem 60 }

rcSysTrapRecvEntry OBJECT-TYPE
        SYNTAX        RcSysTrapRecvEntry
        MAX-ACCESS        not-accessible
        STATUS        current
        DESCRIPTION   "A trap receiver table entry."
        INDEX         { rcSysTrapRecvAddress }
        ::= { rcSysTrapRecvTable 1 }
 
RcSysTrapRecvEntry ::=
        SEQUENCE {
                rcSysTrapRecvAddress IpAddress,
                rcSysTrapRecvVersion INTEGER,
                rcSysTrapRecvCommunity DisplayString,
                rcSysTrapRecvSrcAddress IpAddress,
                rcSysTrapRecvRowStatus RowStatus
        }
 
rcSysTrapRecvAddress OBJECT-TYPE
        SYNTAX        IpAddress
        MAX-ACCESS        read-only
        STATUS        current
        DESCRIPTION   "IP address for trap receiver."
        ::= { rcSysTrapRecvEntry 1 }
 
rcSysTrapRecvVersion OBJECT-TYPE
        SYNTAX        INTEGER {
		         v1(1),          
		         v2c(2)
	              }
        MAX-ACCESS        read-write
        STATUS	      current
	DESCRIPTION ""
	DEFVAL 	      { v1 }
	::= { rcSysTrapRecvEntry 2 }

rcSysTrapRecvCommunity OBJECT-TYPE
        SYNTAX        DisplayString (SIZE (0..20))
        MAX-ACCESS        read-write
        STATUS        current
        DESCRIPTION   "Community string used for trap messages to this
                       trap receiver."
        ::= { rcSysTrapRecvEntry 3 }

rcSysTrapRecvSrcAddress OBJECT-TYPE 
        SYNTAX        IpAddress
        MAX-ACCESS        read-write
        STATUS        current
        DESCRIPTION   "Source IP address to use when sending traps.
		       This IP address will be inserted into the
		       source IP address field in the UDP trap packet."
        ::= { rcSysTrapRecvEntry 4 } 
 
rcSysTrapRecvRowStatus OBJECT-TYPE
        SYNTAX        RowStatus
        MAX-ACCESS        read-write
        STATUS        current
        DESCRIPTION   "Used to create/delete entries"
        ::= { rcSysTrapRecvEntry 5 }


-- Access Policy Table
 
rcSysAccessPolicyTable OBJECT-TYPE
        SYNTAX        SEQUENCE OF RcSysAccesspolicyEntry
        MAX-ACCESS        not-accessible
        STATUS        current
        DESCRIPTION   "Management access policy table.  This table is 
		       used to permit or deny access to this device via
		       the specified source Id."
        ::= { rcSystem 61 }

rcSysAccessPolicyEntry OBJECT-TYPE
        SYNTAX        RcSysAccesspolicyEntry
        MAX-ACCESS        not-accessible
        STATUS        current
        DESCRIPTION   "An access policy table entry."
        INDEX         { rcSysAccessPolicyId }
        ::= { rcSysAccessPolicyTable 1 }
 
RcSysAccesspolicyEntry ::=
        SEQUENCE {
                rcSysAccessPolicyId INTEGER,
                rcSysAccessPolicyName DisplayString,
                rcSysAccessPolicyPolicyEnable TruthValue,
                rcSysAccessPolicyMode INTEGER,
                rcSysAccessPolicyService INTEGER,
                rcSysAccessPolicyPrecedence INTEGER,
                rcSysAccessPolicyNetAddr IpAddress,
                rcSysAccessPolicyNetMask IpAddress,
                rcSysAccessPolicyTrustedHostAddr IpAddress,
                rcSysAccessPolicyTrustedHostUserName DisplayString,
                rcSysAccessPolicyAccessLevel INTEGER,
                rcSysAccessPolicyLog TruthValue,
                rcSysAccessPolicyUsage Counter32,
                rcSysAccessPolicyRowStatus RowStatus
        }
 
rcSysAccessPolicyId OBJECT-TYPE 
        SYNTAX        INTEGER (1..65535)
        MAX-ACCESS        read-only
        STATUS        current
        DESCRIPTION   "Policy Id."
        ::= { rcSysAccessPolicyEntry 1 } 

rcSysAccessPolicyName OBJECT-TYPE
        SYNTAX        DisplayString (SIZE (0..15))
        MAX-ACCESS        read-write
        STATUS        current
        DESCRIPTION   "Name of this policy."
        ::= { rcSysAccessPolicyEntry 2 }

rcSysAccessPolicyPolicyEnable OBJECT-TYPE
        SYNTAX        TruthValue
        MAX-ACCESS        read-write
        STATUS        current
        DESCRIPTION   "Indicate whether this policy is currently 
                       active."
	DEFVAL	      { true }
        ::= { rcSysAccessPolicyEntry 3 }

rcSysAccessPolicyMode OBJECT-TYPE
        SYNTAX        INTEGER {
                        allow(1), 
                        deny(2)
                      }          
        MAX-ACCESS        read-write
        STATUS        current
        DESCRIPTION   "Used to indicate whether a packet having a
		       source IP address that matches this entry
		       should be permitted to enter the device or
 		       denied access." 
	DEFVAL	      { allow }
        ::= { rcSysAccessPolicyEntry 4 }

rcSysAccessPolicyService OBJECT-TYPE
        SYNTAX        INTEGER {
			telnet(1),
			snmp(2),
			tftp(4),
			ftp(8),
			http(16),
			rlogin(32)
	    	      }		
        MAX-ACCESS        read-write
        STATUS        current
        DESCRIPTION   "Is represented as bitset to indicate which protocol
                      this entry should be applied to."
	DEFVAL	      { snmp }
        ::= { rcSysAccessPolicyEntry 5 }

rcSysAccessPolicyPrecedence OBJECT-TYPE
        SYNTAX        INTEGER (1..128)
        MAX-ACCESS        read-write
        STATUS        current
        DESCRIPTION   "Used to indicate the precedence of this policy.
		       The Lower the number the higher the precedence."
	DEFVAL	      { 10 }
        ::= { rcSysAccessPolicyEntry 6 }

rcSysAccessPolicyNetAddr OBJECT-TYPE
        SYNTAX        IpAddress
        MAX-ACCESS        read-write
        STATUS        current
        DESCRIPTION   "Source network IP address."
        ::= { rcSysAccessPolicyEntry 7 }
 
rcSysAccessPolicyNetMask OBJECT-TYPE
        SYNTAX        IpAddress
        MAX-ACCESS        read-write
        STATUS        current
        DESCRIPTION   "Source network mask."
        ::= { rcSysAccessPolicyEntry 8 }
 
rcSysAccessPolicyTrustedHostAddr OBJECT-TYPE
        SYNTAX        IpAddress
        MAX-ACCESS        read-write
        STATUS        current
        DESCRIPTION   "Trusted IP address of host performing a rlogin
		       into the device."
        ::= { rcSysAccessPolicyEntry 9 }
 
rcSysAccessPolicyTrustedHostUserName OBJECT-TYPE
        SYNTAX        DisplayString (SIZE (0..30))
        MAX-ACCESS        read-write
        STATUS        current
        DESCRIPTION   "User name on the trusted host performing a rlogin
                       into the device."
        ::= { rcSysAccessPolicyEntry 10 }

rcSysAccessPolicyAccessLevel OBJECT-TYPE
        SYNTAX        INTEGER {
                        readOnly(1), 
                        readWrite(2),
                        readWriteAll(3)
                      }          
        MAX-ACCESS        read-write
        STATUS        current
        DESCRIPTION   "Access level of trusted host." 
	DEFVAL	      { readWrite }
        ::= { rcSysAccessPolicyEntry 11 }

rcSysAccessPolicyLog OBJECT-TYPE
        SYNTAX        TruthValue
        MAX-ACCESS        read-write
        STATUS        current
        DESCRIPTION   "Used to indicate whether logging should be 
		       performed if this policy was applied."
	DEFVAL	      { false }
        ::= { rcSysAccessPolicyEntry 12 }

rcSysAccessPolicyUsage OBJECT-TYPE
        SYNTAX  	Counter32
        MAX-ACCESS  	read-only
        STATUS  	current
        DESCRIPTION 	"Usage counter"
        ::= { rcSysAccessPolicyEntry 13 }

rcSysAccessPolicyRowStatus OBJECT-TYPE
        SYNTAX        RowStatus
        MAX-ACCESS        read-write
        STATUS        current
        DESCRIPTION   "Used to create/delete an entry"
        ::= { rcSysAccessPolicyEntry 14 }


-- TFTP Upload/Download

rcTftpHost OBJECT-TYPE
        SYNTAX        IpAddress
        MAX-ACCESS        read-write
        STATUS        current
        DESCRIPTION   "Name of source/destination host for the TFTP
                      transfer."
        ::= { rcTftp 1 }

rcTftpFile OBJECT-TYPE
        SYNTAX        DisplayString (SIZE (0..64))
        MAX-ACCESS        read-write
        STATUS        current
        DESCRIPTION   "Name of file for the TFTP transfer."
        ::= { rcTftp 2 }

rcTftpAction OBJECT-TYPE
        SYNTAX        INTEGER {
		         none(1),          -- none of the following
		         downloadConfig(2),
		         uploadConfig(3),
		         downloadSwToFlash(4),
                         downloadSwToPcmcia(5),
                         uploadSw(6),
                         downloadSwToDram(7)
	              }
        MAX-ACCESS	      read-write
        STATUS	      current
	DESCRIPTION ""
	DEFVAL 	      { none }
	::= { rcTftp 3 }

rcTftpResult OBJECT-TYPE
        SYNTAX        INTEGER {
		         none(1),
		         inProgress(2),
		         noResponse(3),
		         fileAccessError(4),
		         badFlash(5),
		         flashEraseFailed(6),
		         pcmciaEraseFailed(7),
		         success(8),
		         fail(9),
                         writeToNvramFailed(10),
		         flashWriteFailed(11),
		         pcmciaWriteFailed(12),
                         configFileTooBig(13),
                         imageFileTooBig(14),
			 noPcmciaDetect(15),
			 pcmciaNotSupported(16),
			 invalidFile(17),
			 noMemory(18),
			 xferError(19),
			 crcError(20),
                         readNvramFailed(21),
                         pcmciaWriteProtect(22)
	              }
        MAX-ACCESS        read-only
        STATUS        current
        DESCRIPTION   "Contains result of the last Tftp action request."
        ::= { rcTftp 4 }


-- VLAN Table

rcVlanNumVlans OBJECT-TYPE
        SYNTAX        INTEGER (1..128)
        MAX-ACCESS        read-only
        STATUS        current
        DESCRIPTION   "The number of VLANs currently defined in the switch."
        ::= { rcVlan 1 }

rcVlanTable OBJECT-TYPE
        SYNTAX        SEQUENCE OF RcVlanEntry
        MAX-ACCESS        not-accessible
        STATUS        current
        DESCRIPTION   "A list of Virtual LAN entries. The number of entries
                      is given by rcVlanNumVlans."
        ::= { rcVlan 2 }

rcVlanEntry OBJECT-TYPE
        SYNTAX        RcVlanEntry
        MAX-ACCESS        not-accessible
        STATUS        current
        DESCRIPTION   "Entry containing configuration information for a 
                      particular Virtual LAN.

                      The relationship between the various port sets in a 
                      VLAN Entry are :

                      o The set of ports defined by PortMembers must be a 
                        subset of the set of ports in the underlying STG of 
                        the VLAN.

                      o The bitwise AND of PortMembers and NotAllowToJoin must 
                        be the empty set.

                      o The bitwise OR of PortMembers and NotAllowToJoin must 
                        be the set of ports in the underlying STG of the VLAN.

                      o The set of ports defined by StaticMembers must be a 
                        subset of the set of ports defined by PortMembers.

                      o The bitwise XOR of PortMembers and StaticMembers defines 
                        the set of dynamic (potential) members of the VLAN.

                      o The set of ports defined by ActiveMembers must be a subset 
                        of the set of ports defined by PortMembers.
                      "
        INDEX         { rcVlanId }
        ::= { rcVlanTable 1 }

RcVlanEntry ::= SEQUENCE {
                rcVlanId INTEGER,
                rcVlanName DisplayString,
                rcVlanColor INTEGER,
                rcVlanHighPriority TruthValue,
                rcVlanRoutingEnable TruthValue,
                rcVlanIfIndex InterfaceIndex,
                rcVlanAction INTEGER,
                rcVlanResult INTEGER,
                rcVlanStgId INTEGER,
                rcVlanType INTEGER,
                rcVlanPortMembers PortSet,
                rcVlanActiveMembers PortSet,
                rcVlanStaticMembers PortSet,
                rcVlanNotAllowToJoin PortSet,
                rcVlanProtocolId INTEGER,
                rcVlanSubnetAddr IpAddress,
                rcVlanSubnetMask IpAddress,
                rcVlanAgingTime  INTEGER,
                rcVlanMacAddress MacAddress,
                rcVlanRowStatus RowStatus,
                rcVlanIgmpSnoopEnable TruthValue,
                rcVlanIgmpSnoopReportProxyEnable TruthValue,
                rcVlanIgmpSnoopRobustness INTEGER,
                rcVlanIgmpSnoopQueryInterval INTEGER,
                rcVlanIgmpSnoopMRouterPorts PortSet,
		rcVlanUserDefinedPid INTEGER,
		rcVlanIgmpSnoopActiveMRouterPorts PortSet,
		rcVlanProtocolIds INTEGER,
		rcVlanIgmpSnoopActiveQuerier IpAddress,
		rcVlanIgmpSnoopMRouterExpiration INTEGER,
		rcVlanIgmpSnoopQuerierPort InterfaceIndex,
		rcVlanUserPriority INTEGER,
		rcVlanQosLevel INTEGER,
		rcVlanTosValue INTEGER
        }

rcVlanId OBJECT-TYPE
        SYNTAX        INTEGER (1..4094)
        MAX-ACCESS        read-only
        STATUS        current
        DESCRIPTION   "A value that uniquely identifies the Virtual LAN 
                      associated with this entry. This value corresponds
                      to the lower 12 bits in the IEEE 802.1Q VLAN Tag."
        ::= { rcVlanEntry 1 }

rcVlanName OBJECT-TYPE
        SYNTAX        DisplayString (SIZE (0..20))
        MAX-ACCESS        read-write
        STATUS        current
        DESCRIPTION   "An administratively-assigned name for this VLAN."
        ::= { rcVlanEntry 2 }

rcVlanColor OBJECT-TYPE
        SYNTAX        INTEGER (0..32)
        MAX-ACCESS        read-write
        STATUS        current
        DESCRIPTION   "An administratively-assigned color code for this
                      VLAN. The value of this object is used by the VLAN
                      Manager GUI tool to select a color when it draws
                      this VLAN on the screen."
        ::= { rcVlanEntry 3 }

rcVlanHighPriority OBJECT-TYPE
        SYNTAX        TruthValue
        MAX-ACCESS        read-write
        STATUS        deprecated
        DESCRIPTION   "A flag to note whether frames in this VLAN should 
                      be assigned a high switching priority."
        DEFVAL        { false }
        ::= { rcVlanEntry 4 }

rcVlanRoutingEnable OBJECT-TYPE
        SYNTAX        TruthValue
        MAX-ACCESS        read-write
        STATUS        deprecated
        DESCRIPTION   "A flag to note whether IP routing is enabled in
                      this VLAN." 
        DEFVAL        { false }
        ::= { rcVlanEntry 5 }

rcVlanIfIndex OBJECT-TYPE
        SYNTAX        InterfaceIndex 
        MAX-ACCESS        read-only
        STATUS        current
        DESCRIPTION   "When rcVlanRoutingEnable is set to true(1), this 
                      value indicates the 'logical' ifIndex assigned to
                      this VLAN.  Otherwise, this value is meaningless
                      and should be set to zero."
        ::= { rcVlanEntry 6 }

rcVlanAction OBJECT-TYPE
        SYNTAX        INTEGER {
                         none(1),             -- none of the following
                         flushMacFdb(2),      -- flush MAC forwarding table
                         flushArp(3),         -- flush ARP table
                         flushIp(4),          -- flush IP route table
                         flushDynMemb(5),     -- flush Dynamic Members
                         all(6),              -- flush all tables 
			 flushSnoopMemb(7),   -- flush IGMP Snoop Members
                         triggerRipUpdate(8), -- manually trigger rip update
			 flushSnoopMRtr(9)    -- flush snoop multicast router
                      }
        MAX-ACCESS        read-write
        STATUS        current
        DESCRIPTION   "VLAN related actions."
        DEFVAL        { none }
        ::= { rcVlanEntry 7 }

rcVlanResult OBJECT-TYPE
        SYNTAX        INTEGER {
                         none(1),        -- none of the following
                         inProgress(2),  -- in progress
                         success(3),     -- success
                         fail(4)         -- failure
                      }
        MAX-ACCESS        read-only
        STATUS        current
        DESCRIPTION   "The result from the last VLAN action."
        DEFVAL        { none }
        ::= { rcVlanEntry 8 }

rcVlanStgId OBJECT-TYPE
        SYNTAX        INTEGER (0..128)
        MAX-ACCESS        read-write
        STATUS        current
        DESCRIPTION   "Indicates the Spanning Tree Group (STG) used by
                      this VLAN to determine the state of its ports.
                      If this VLAN is not associated with any STG, this
                      value should be set to zero."
        DEFVAL        { 1 }
        ::= { rcVlanEntry 9 }

rcVlanType OBJECT-TYPE
        SYNTAX        INTEGER {
                         byPort(1),       -- VLAN by Port 
                         byIpSubnet(2),   -- VLAN by IP subnet 
                         byProtocolId(3), -- VLAN by Protocol Id
                         bySrcMac(4),     -- VLAN by Src MAC address
                         byDstMcast(5)    -- VLAN by Dst MultiCast
                      }
        MAX-ACCESS        read-write
        STATUS        current
        DESCRIPTION   "The type of VLAN, distinguished according to the
                      policy used to define its port membership."
        ::= { rcVlanEntry 10 }

rcVlanPortMembers OBJECT-TYPE
        SYNTAX        PortSet
        MAX-ACCESS        read-write
        STATUS        current
        DESCRIPTION   "The set of ports that are members (static or 
                      dynamic) of this VLAN."
        ::= { rcVlanEntry 11 }
 
rcVlanActiveMembers OBJECT-TYPE
        SYNTAX        PortSet
        MAX-ACCESS        read-only
        STATUS        current
        DESCRIPTION   "The set of ports that are currently active in 
                      this VLAN. Active ports include all static ports
                      and any dynamic ports where the VLAN policy was
                      met."
        ::= { rcVlanEntry 12 }
 
rcVlanStaticMembers OBJECT-TYPE
        SYNTAX        PortSet
        MAX-ACCESS        read-write
        STATUS        current
        DESCRIPTION   "The set of ports that are static members of this
                      VLAN. A static member of a VLAN is always active 
                      and is never aged out."
        ::= { rcVlanEntry 13 }

rcVlanNotAllowToJoin OBJECT-TYPE
        SYNTAX        PortSet
        MAX-ACCESS        read-write
        STATUS        current
        DESCRIPTION   "The set of ports that are not allowed to become
                      members of this VLAN."
        ::= { rcVlanEntry 14 }

rcVlanProtocolId OBJECT-TYPE
        SYNTAX        INTEGER {
                         none(0),
                         ip(1),
                         ipx802dot3(2),
                         ipx802dot2(3),
                         ipxSnap(4),
                         ipxEthernet2(5),
                         appleTalk(6),
                         decLat(7),
                         decOther(8),
                         sna802dot2(9),
                         snaEthernet2(10),
                         netBios(11),
                         xns(12),
			 vines(13),
                         ipV6(14), 
                         usrDefined(15),
			 rarp(16)
                      }
        MAX-ACCESS        read-write
        STATUS        current
        DESCRIPTION   "The protocol identifier of this VLAN. This value 
                      is meaningful only if rcVlanType is equal to 
                      byProtocolId(3). For other VLAN types it should
                      have the value none(0)."
        ::= { rcVlanEntry 15 }

rcVlanSubnetAddr OBJECT-TYPE
        SYNTAX        IpAddress
        MAX-ACCESS        read-write
        STATUS        current
        DESCRIPTION   "The IP subnet address of this VLAN. This value 
                      is meaningful only if rcVlanType is equal to 
                      byIpSubnet(2). For other VLAN types it should
                      have the value 0.0.0.0."
        ::= { rcVlanEntry 16 }

rcVlanSubnetMask OBJECT-TYPE
        SYNTAX        IpAddress
        MAX-ACCESS        read-write
        STATUS        current
        DESCRIPTION   "The IP subnet mask of this VLAN. This value
                      is meaningful only if rcVlanType is equal to 
                      byIpSubnet(2). For other VLAN types it should
                      have the value 0.0.0.0."
        ::= { rcVlanEntry 17 }

rcVlanAgingTime OBJECT-TYPE
        SYNTAX        INTEGER (10..1000000)
        MAX-ACCESS        read-write
        STATUS        current
        DESCRIPTION   "The timeout period (in seconds) used for aging
                      out dynamic members of this VLAN. This field is
                      only relevant for policy-based VLANs."
        DEFVAL        { 600 }
        ::= { rcVlanEntry 18 }

rcVlanMacAddress OBJECT-TYPE
        SYNTAX        MacAddress
        MAX-ACCESS        read-only
        STATUS        current
        DESCRIPTION   "The MAC address assigned to the virtual router
                      interface of this VLAN. This field is meaningful 
                      only if rcVlanRoutingEnable is equal to true(1)."
        ::= { rcVlanEntry 19 }

rcVlanRowStatus OBJECT-TYPE
        SYNTAX        RowStatus
        MAX-ACCESS        read-write
        STATUS        current
        DESCRIPTION   "Used to create/delete entries in the rcVlanTable."
        ::= { rcVlanEntry 20 }

rcVlanIgmpSnoopEnable OBJECT-TYPE
        SYNTAX        TruthValue
        MAX-ACCESS        read-write
        STATUS        current
        DESCRIPTION   "A flag to note whether IGMP Snooping is enabled
                      on this VLAN."
        DEFVAL        { false }
        ::= { rcVlanEntry 21 }
 
rcVlanIgmpSnoopReportProxyEnable OBJECT-TYPE
        SYNTAX        TruthValue
        MAX-ACCESS        read-write
        STATUS        current
        DESCRIPTION   "A flag to note whether IGMP Report Proxy is
                      enabled on this VLAN."
        DEFVAL        { true }
        ::= { rcVlanEntry 22 }
 
rcVlanIgmpSnoopRobustness OBJECT-TYPE
        SYNTAX        INTEGER (2..255)
        MAX-ACCESS        read-write
        STATUS        current
        DESCRIPTION   "This variable allows tuning for the expected
                      packet loss on a subnet. If a subnet is expected
                      to be lossy, the Robustness variable may be
                      increased. IGMP is robust to (Robustness - 1)
                      packet losses."
        DEFVAL        { 2 }
        ::= { rcVlanEntry 23 }
 
rcVlanIgmpSnoopQueryInterval OBJECT-TYPE
        SYNTAX        INTEGER (1..65535)
        MAX-ACCESS        read-write
        STATUS        current
        DESCRIPTION   "The interval (in seconds) between IGMP Host-Query
                      packets transmitted on this interface."
        DEFVAL        { 125 }
        ::= { rcVlanEntry 24 }
 
rcVlanIgmpSnoopMRouterPorts OBJECT-TYPE
        SYNTAX        PortSet
        MAX-ACCESS        read-write
        STATUS        current
        DESCRIPTION   "The set of ports in this VLAN that provide
                      connectivity to an IP Multicast router."
        ::= { rcVlanEntry 25 }

rcVlanUserDefinedPid OBJECT-TYPE
        SYNTAX        Integer32
        MAX-ACCESS        read-write
        STATUS        current
        DESCRIPTION   "When rcVlanProtocolId is set to usrDefined(15)
                       in a protocol-based VLAN, this field represents
                       the 16-bit user defined protocol identifier."
        ::= { rcVlanEntry 26 }
 
rcVlanIgmpSnoopActiveMRouterPorts OBJECT-TYPE
        SYNTAX        PortSet
        MAX-ACCESS        read-only
        STATUS        current
        DESCRIPTION   "Active ports."
        ::= { rcVlanEntry 27 }

rcVlanProtocolIds OBJECT-TYPE
        SYNTAX        Integer32
        MAX-ACCESS        read-write
        STATUS        current
        DESCRIPTION   "Bitfield of protocol ids."
        ::= { rcVlanEntry 28 }

rcVlanIgmpSnoopActiveQuerier OBJECT-TYPE
        SYNTAX        IpAddress
        MAX-ACCESS        read-only
        STATUS        current
        DESCRIPTION   "IP address of multicast querier router."
        ::= { rcVlanEntry 29 }

rcVlanIgmpSnoopMRouterExpiration OBJECT-TYPE
        SYNTAX        Integer32
        MAX-ACCESS        read-only
        STATUS        current
        DESCRIPTION   "Multicast querier router aging time out."
        ::= { rcVlanEntry 30 }

rcVlanIgmpSnoopQuerierPort OBJECT-TYPE
        SYNTAX        InterfaceIndex
        MAX-ACCESS        read-only
        STATUS        current
        DESCRIPTION   "The port on which the multicast querier router
		       was heard."
        ::= { rcVlanEntry 31 }

rcVlanUserPriority OBJECT-TYPE
        SYNTAX  	INTEGER {
                            level0(0),
                            level1(1),
                            level2(2),
                            level3(3),
                            level4(4),
                            level5(5),
                            level6(6),
                            level7(7)
                        }
        MAX-ACCESS        	read-only
        STATUS        	current
        DESCRIPTION   	"User priority level."
        ::= { rcVlanEntry 32 }

rcVlanQosLevel OBJECT-TYPE
        SYNTAX  	INTEGER {
                            level0(0),
                            level1(1),
                            level2(2),
                            level3(3),
                            level4(4),
                            level5(5),
                            level6(6),
			    level7(7)
                        }
        MAX-ACCESS        	read-write
        STATUS        	current
    	DESCRIPTION   	"Used to specify the Qos level packets, carried in this
			VLAN, should be processed with."
        DEFVAL        	{ level1 }
        ::= { rcVlanEntry 33 }

rcVlanTosValue OBJECT-TYPE
        SYNTAX        	INTEGER (1..64)
        MAX-ACCESS        	read-write 
        STATUS        	current
        DESCRIPTION   	"Tos value."
	DEFVAL		{ 1 }
        ::= { rcVlanEntry 34 } 


-- VLAN Port Table

rcVlanPortTable OBJECT-TYPE
        SYNTAX        SEQUENCE OF RcVlanPortEntry
        MAX-ACCESS        not-accessible
        STATUS        current
        DESCRIPTION   "A table used to maintain VLAN port related 
                      information." 
        ::= { rcVlan 3 }

rcVlanPortEntry OBJECT-TYPE
        SYNTAX        RcVlanPortEntry
        MAX-ACCESS        not-accessible
        STATUS        current
        DESCRIPTION   "Entry containing VLAN information regarding a 
                      particular port."
        INDEX         { rcVlanPortIndex }
        ::= { rcVlanPortTable 1 }

RcVlanPortEntry ::= SEQUENCE {
                rcVlanPortIndex Integer32,
                rcVlanPortNumVlanIds INTEGER,
                rcVlanPortVlanIds IdList,
                rcVlanPortType INTEGER,
                rcVlanPortDiscardTaggedFrames TruthValue,
                rcVlanPortDiscardUntaggedFrames TruthValue,
                rcVlanPortDefaultVlanId INTEGER,
                rcVlanPortPerformTagging TruthValue
        }

rcVlanPortIndex OBJECT-TYPE
        SYNTAX        Integer32
        MAX-ACCESS        read-only
        STATUS        current
        DESCRIPTION   "An unique index used to identify a particular 
                      port in the system. This index is equal to the
                      ifIndex of the port."
        ::= { rcVlanPortEntry 1 }

rcVlanPortNumVlanIds OBJECT-TYPE
        SYNTAX        Integer32
        MAX-ACCESS        read-only
        STATUS        current
        DESCRIPTION   "Used to indicate the number of VLAN IDs that
                      are stored in the rcVlanPortVlanIds variable."
        ::= { rcVlanPortEntry 2 }

rcVlanPortVlanIds OBJECT-TYPE
        SYNTAX        IdList (SIZE (4096))
        MAX-ACCESS        read-write  
        STATUS        current
        DESCRIPTION   "An array used to identify which VLANs this port 
                      is assigned to.  Each VLAN ID is stored as a two
                      octet value. The first octet in the pair holds
                      bits 15-8 of the VLAN ID, while the second octet
                      holds bits 7-0 of the VLAN ID."
        ::= { rcVlanPortEntry 3 }

rcVlanPortType OBJECT-TYPE
        SYNTAX        INTEGER {
                         access(1),     -- access port type
                         trunk(2)       -- trunk port type
                      }
        MAX-ACCESS        read-write
        STATUS        current
        DESCRIPTION   "The type of port: access(1) or trunk(2)."
        DEFVAL        { access }
        ::= { rcVlanPortEntry 4 }

rcVlanPortDiscardTaggedFrames OBJECT-TYPE
        SYNTAX        TruthValue
        MAX-ACCESS        read-write
        STATUS        current
        DESCRIPTION   "A flag used to determine how to process tagged
                      frames received on this access port. When the 
                      flag is set, these frames are discarded by the
                      forwarding process. When the flag is reset, these
                      frames are processed normally.

		      This field is meaningless when the port is not
		      an access port and should be set to false(2)."
        DEFVAL        { false }
        ::= { rcVlanPortEntry 5 }

rcVlanPortDiscardUntaggedFrames OBJECT-TYPE
        SYNTAX        TruthValue
        MAX-ACCESS        read-write
        STATUS        current
        DESCRIPTION   "A flag used to determine how to process untagged
                      frames received on this trunk port. When the flag 
                      is set, these frames are discarded by the 
                      forwarding process. When the flag is reset, these
                      frames are assigned to the VLAN specified by 
                      rcVlanPortDefaultVlanId.

		      This field is meaningless when the port is not
		      a trunk port and should be set to false(2)."
        DEFVAL        { false }
        ::= { rcVlanPortEntry 6 }

rcVlanPortDefaultVlanId OBJECT-TYPE
        SYNTAX        INTEGER (0..4094)
        MAX-ACCESS        read-write
        STATUS        current
        DESCRIPTION   "The VLAN ID assigned to untagged frames received
                      on this trunk port.

		      This field is meaningless when the port is not
		      a trunk port."
        DEFVAL        { 1 }
        ::= { rcVlanPortEntry 7 } 

rcVlanPortPerformTagging OBJECT-TYPE
        SYNTAX        TruthValue
        MAX-ACCESS        read-write
        STATUS        current
        DESCRIPTION   ""
        DEFVAL        { false }
        ::= { rcVlanPortEntry 8 }

-- VLAN MAC Table

rcVlanMacTable OBJECT-TYPE
        SYNTAX        SEQUENCE OF RcVlanMacEntry
        MAX-ACCESS        not-accessible
        STATUS        current
        DESCRIPTION   "A table used to maintain MAC addresses assigned 
                      to a particular VLAN by MAC address."
        ::= { rcVlan 4 }
 
rcVlanMacEntry OBJECT-TYPE
        SYNTAX        RcVlanMacEntry
        MAX-ACCESS        not-accessible
        STATUS        current
        DESCRIPTION   "Entry containing VLAN information regarding a
                      particular port."
        INDEX         { rcVlanMacVlanId, rcVlanMacAddr }
        ::= { rcVlanMacTable 1 }
 
RcVlanMacEntry ::= SEQUENCE {
                rcVlanMacVlanId INTEGER,
                rcVlanMacAddr MacAddress,
                rcVlanMacRowStatus RowStatus
        }
 
rcVlanMacVlanId OBJECT-TYPE
        SYNTAX        Integer32
        MAX-ACCESS        read-only
        STATUS        current
        DESCRIPTION   "An unique index used to identify a VLAN (by MAC 
                      address) in the system."
        ::= { rcVlanMacEntry 1 }

rcVlanMacAddr OBJECT-TYPE
        SYNTAX        MacAddress
        MAX-ACCESS        read-only
        STATUS        current
        DESCRIPTION   "An unique index used to identify a MAC address
                      assigned to a particular VLAN."
        ::= { rcVlanMacEntry 2 }

rcVlanMacRowStatus OBJECT-TYPE
        SYNTAX        RowStatus
        MAX-ACCESS        read-write
        STATUS        current
        DESCRIPTION   "Row status for this entry."
        ::= { rcVlanMacEntry 3 }


-- VLAN IGMP Snoop Table

rcVlanIgmpSnoopNumGroups OBJECT-TYPE
        SYNTAX        Integer32
        MAX-ACCESS        read-only
        STATUS        current
        DESCRIPTION   "The number of entries (rows) in the
                      rcVlanIgmpSnoopTable."
        ::= { rcVlan 5 }

rcVlanIgmpSnoopTable OBJECT-TYPE
        SYNTAX        SEQUENCE OF RcVlanIgmpSnoopEntry
        MAX-ACCESS        not-accessible
        STATUS        current
        DESCRIPTION   "The (conceptual) table listing the IP multicast
                      groups for which there are members on a particular
                      interface on a particular VLAN (i.e., a list 
		      known multicast receivers).

		      A row is created by the system when it receives
		      an IGMP Join messages on a port."
    ::= { rcVlan 6 }
 
rcVlanIgmpSnoopEntry OBJECT-TYPE
        SYNTAX        RcVlanIgmpSnoopEntry
        MAX-ACCESS        not-accessible
        STATUS        current
        DESCRIPTION   "An entry (row) in the rcVlanIgmpSnoopTable."
        INDEX         { rcVlanIgmpSnoopVlanId, rcVlanIgmpSnoopIpAddress,
                        rcVlanIgmpSnoopIfIndex, rcVlanIgmpSnoopMember }
        ::= { rcVlanIgmpSnoopTable 1 }
 
RcVlanIgmpSnoopEntry ::= SEQUENCE {
            rcVlanIgmpSnoopVlanId     INTEGER,
            rcVlanIgmpSnoopIpAddress  IpAddress,
            rcVlanIgmpSnoopIfIndex    InterfaceIndex,
            rcVlanIgmpSnoopMember     IpAddress,
            rcVlanIgmpSnoopExpiration INTEGER,
            rcVlanIgmpSnoopType       INTEGER
        }

rcVlanIgmpSnoopVlanId OBJECT-TYPE
        SYNTAX        INTEGER (1..4094)
        MAX-ACCESS        read-only
        STATUS        current
        DESCRIPTION   "The VLAN for which this entry contains
                      information."
        ::= { rcVlanIgmpSnoopEntry 1 } 

rcVlanIgmpSnoopIpAddress OBJECT-TYPE
        SYNTAX        IpAddress
        MAX-ACCESS        read-only
        STATUS        current
        DESCRIPTION   "The IP multicast group address for which this 
                      entry contains information."
        ::= { rcVlanIgmpSnoopEntry 2 }
 
rcVlanIgmpSnoopIfIndex OBJECT-TYPE
        SYNTAX        InterfaceIndex
        MAX-ACCESS        read-only
        STATUS        current
        DESCRIPTION   "The interface for which this entry contains 
                      information for this IP multicast group address
                      (i.e., the port the Join message was received)."
        ::= { rcVlanIgmpSnoopEntry 3 }
 
rcVlanIgmpSnoopMember OBJECT-TYPE
        SYNTAX        IpAddress
        MAX-ACCESS        read-only
        STATUS        current
        DESCRIPTION   "The IP Address of the source of the membership
                      report received for this IP Multicast group address
                      on this interface (i.e., the address of the host
                      sending the Join message)."
        ::= { rcVlanIgmpSnoopEntry 4 }
 
rcVlanIgmpSnoopExpiration OBJECT-TYPE
         SYNTAX        Integer32
         MAX-ACCESS       read-only
         STATUS       current
         DESCRIPTION  "The minimum amount of time remaining before this 
                      entry will be aged out."
         ::= { rcVlanIgmpSnoopEntry 5 }

rcVlanIgmpSnoopType OBJECT-TYPE
         SYNTAX       INTEGER {
                         dynamic(1),    -- created via IGMP
                         static(2),     -- created via management
                         blocked(3)
                      }
         MAX-ACCESS       read-only
         STATUS       current
         DESCRIPTION  "The type of entry: dynamic(1) entries are
                      created by snooping IGMP messages, static(2)
                      entries are created via management."
         ::= { rcVlanIgmpSnoopEntry 6 }


-- VLAN IGMP Snoop Static Table

rcVlanIgmpSnoopStaticTable OBJECT-TYPE
        SYNTAX        SEQUENCE OF RcVlanIgmpSnoopStaticEntry
        MAX-ACCESS        not-accessible
        STATUS        current
        DESCRIPTION   "The (conceptual) table listing the statically-
                      defined IP multicast groups for which there are
                      members on a particular interface on a particular
                      VLAN."
    	::= { rcVlan 7 }
 
rcVlanIgmpSnoopStaticEntry OBJECT-TYPE
        SYNTAX        RcVlanIgmpSnoopStaticEntry
        MAX-ACCESS        not-accessible
        STATUS        current
        DESCRIPTION   "An entry (row) in the rcVlanIgmpSnoopStaticTable."
        INDEX         { rcVlanIgmpSnoopStaticVlanId, rcVlanIgmpSnoopStaticIpAddress }
        ::= { rcVlanIgmpSnoopStaticTable 1 }
 
RcVlanIgmpSnoopStaticEntry ::= SEQUENCE {
            rcVlanIgmpSnoopStaticVlanId           INTEGER,
            rcVlanIgmpSnoopStaticIpAddress        IpAddress,
            rcVlanIgmpSnoopStaticMemberPorts      PortSet,
            rcVlanIgmpSnoopStaticRowStatus        RowStatus,
            rcVlanIgmpSnoopStaticNotAllowedToJoin PortSet
        }

rcVlanIgmpSnoopStaticVlanId OBJECT-TYPE
        SYNTAX        INTEGER (1..4094)
        MAX-ACCESS        read-only
        STATUS        current
        DESCRIPTION   "The VLAN for which this entry contains information."
        ::= { rcVlanIgmpSnoopStaticEntry 1 } 

rcVlanIgmpSnoopStaticIpAddress OBJECT-TYPE
        SYNTAX        IpAddress
        MAX-ACCESS        read-only
        STATUS        current
        DESCRIPTION   "The IP multicast group address for which this 
                      entry contains information.  The address must
		      fall within 224.0.1.0 to 239.255.255.255."
        ::= { rcVlanIgmpSnoopStaticEntry 2 }

rcVlanIgmpSnoopStaticMemberPorts OBJECT-TYPE
        SYNTAX        PortSet
        MAX-ACCESS        read-write
        STATUS        current
        DESCRIPTION   "The set of ports in this VLAN multicast traffic
		      for the rcVlanIgmpSnoopStaticIpAddress is to be
		      forwarded to."
        ::= { rcVlanIgmpSnoopStaticEntry 3 }

rcVlanIgmpSnoopStaticRowStatus OBJECT-TYPE
        SYNTAX        RowStatus
        MAX-ACCESS        read-write
        STATUS        current
        DESCRIPTION   "Used to create/delete entries in the 
                      rcVlanIgmpSnoopStaticTable."
        ::= { rcVlanIgmpSnoopStaticEntry 4 }

rcVlanIgmpSnoopStaticNotAllowedToJoin OBJECT-TYPE
        SYNTAX        PortSet
        MAX-ACCESS        read-write
        STATUS        current
        DESCRIPTION   "Not allowed to join"
        ::= { rcVlanIgmpSnoopStaticEntry 5 }


-- VLAN IGMP Snoop Access Table

rcVlanIgmpSnoopAccessTable OBJECT-TYPE
        SYNTAX        SEQUENCE OF RcVlanIgmpSnoopAccessEntry
        MAX-ACCESS        not-accessible
        STATUS        current
        DESCRIPTION   "Table used to specify which host(s) can send
		      and/or receive IP Multicast traffic."
    	::= { rcVlan 8 }
 
rcVlanIgmpSnoopAccessEntry OBJECT-TYPE
        SYNTAX        RcVlanIgmpSnoopAccessEntry
        MAX-ACCESS        not-accessible
        STATUS        current
        DESCRIPTION   "An entry (row) in the rcVlanIgmpSnoopAccessTable."
        INDEX         { rcVlanIgmpSnoopAccessVlanId, 
			rcVlanIgmpSnoopAccessGrpAddr, 
                        rcVlanIgmpSnoopAccessHostAddr, 
			rcVlanIgmpSnoopAccessHostMask }
        ::= { rcVlanIgmpSnoopAccessTable 1 }
 

RcVlanIgmpSnoopAccessEntry ::= SEQUENCE {
            rcVlanIgmpSnoopAccessVlanId        INTEGER,
            rcVlanIgmpSnoopAccessGrpAddr       IpAddress,
            rcVlanIgmpSnoopAccessHostAddr      IpAddress,
            rcVlanIgmpSnoopAccessHostMask      IpAddress,
            rcVlanIgmpSnoopAccessMode          INTEGER,
            rcVlanIgmpSnoopAccessRowStatus     RowStatus
        }

rcVlanIgmpSnoopAccessVlanId OBJECT-TYPE
        SYNTAX        INTEGER (1..4094)
        MAX-ACCESS        read-only
        STATUS        current
        DESCRIPTION   "The VLAN for which this entry contains information."
        ::= { rcVlanIgmpSnoopAccessEntry 1 } 

rcVlanIgmpSnoopAccessGrpAddr OBJECT-TYPE
        SYNTAX        IpAddress
        MAX-ACCESS        read-only
        STATUS        current
        DESCRIPTION   "The IP multicast group address for which this
                      entry contains information."
        ::= { rcVlanIgmpSnoopAccessEntry 2 } 

rcVlanIgmpSnoopAccessHostAddr OBJECT-TYPE
        SYNTAX        IpAddress
        MAX-ACCESS        read-only
        STATUS        current
        DESCRIPTION   "The IP address of a host for which this
                      entry contains information."
        ::= { rcVlanIgmpSnoopAccessEntry 3 }

rcVlanIgmpSnoopAccessHostMask OBJECT-TYPE
        SYNTAX        IpAddress
        MAX-ACCESS        read-only
        STATUS        current
        DESCRIPTION   "The IP netmask of a host for which this
                      entry contains information."
        ::= { rcVlanIgmpSnoopAccessEntry 4 }

rcVlanIgmpSnoopAccessMode OBJECT-TYPE
        SYNTAX        INTEGER {
                          denyTx(1),
                          denyRx(2),
                          denyBoth(3)
                      }
        MAX-ACCESS        read-write
        STATUS        current
        DESCRIPTION   "Used to specify whether the host identified by
		      rcVlanIgmpSnoopAccessHostAddr should be denied
		      IP multicast transmit, receive, or both." 
        ::= { rcVlanIgmpSnoopAccessEntry 5 }

rcVlanIgmpSnoopAccessRowStatus OBJECT-TYPE
        SYNTAX        RowStatus
        MAX-ACCESS        read-write
        STATUS        current
        DESCRIPTION   "Row status"
        ::= { rcVlanIgmpSnoopAccessEntry 6 }


-- VLAN IGMP Snoop Sender Table

rcVlanIgmpSnoopSenderTable OBJECT-TYPE
        SYNTAX        SEQUENCE OF RcVlanIgmpSnoopSenderEntry
        MAX-ACCESS        not-accessible
        STATUS        current
        DESCRIPTION   "The (conceptual) table listing the IP multicast 
                      groups for which there are members on a particular
                      interface on a particular VLAN (i.e., a list  
                      known multicast senders).  
  
                      A row is created by the system when it receives 
                      an IGMP Join messages on a port."
    	::= { rcVlan 9 }
 
rcVlanIgmpSnoopSenderEntry OBJECT-TYPE
        SYNTAX        RcVlanIgmpSnoopSenderEntry
        MAX-ACCESS        not-accessible
        STATUS        current
        DESCRIPTION   "An entry (row) in the rcVlanIgmpSnoopSenderTable."
        INDEX         { rcVlanIgmpSnoopSenderVlanId,
                        rcVlanIgmpSnoopSenderIpAddress,
                        rcVlanIgmpSnoopSenderIfIndex,
                        rcVlanIgmpSnoopSenderMember }
        ::= { rcVlanIgmpSnoopSenderTable 1 }
 

RcVlanIgmpSnoopSenderEntry ::= SEQUENCE {
            rcVlanIgmpSnoopSenderVlanId        INTEGER,
            rcVlanIgmpSnoopSenderIpAddress     IpAddress,
            rcVlanIgmpSnoopSenderIfIndex       InterfaceIndex,
            rcVlanIgmpSnoopSenderMember        IpAddress,
            rcVlanIgmpSnoopSenderAction        INTEGER
        }

rcVlanIgmpSnoopSenderVlanId OBJECT-TYPE
        SYNTAX        INTEGER (1..4094)
        MAX-ACCESS        read-only
        STATUS        current
        DESCRIPTION   "The VLAN for which this entry contains information."
        ::= { rcVlanIgmpSnoopSenderEntry 1 } 

rcVlanIgmpSnoopSenderIpAddress OBJECT-TYPE
        SYNTAX        IpAddress
        MAX-ACCESS        read-only
        STATUS        current
        DESCRIPTION   "The IP multicast group address for which this
                      entry contains information."
        ::= { rcVlanIgmpSnoopSenderEntry 2 } 

rcVlanIgmpSnoopSenderIfIndex OBJECT-TYPE
        SYNTAX        InterfaceIndex
        MAX-ACCESS        read-only
        STATUS        current
        DESCRIPTION   "The interface for which this entry contains
                      information for this IP multicast group address
                      (i.e., the port the multicast traffic was received)."
        ::= { rcVlanIgmpSnoopSenderEntry 3 }
 
rcVlanIgmpSnoopSenderMember OBJECT-TYPE
        SYNTAX        IpAddress
        MAX-ACCESS        read-only
        STATUS        current
        DESCRIPTION   "The IP Address of the host sending the multicast
		      traffic." 
        ::= { rcVlanIgmpSnoopSenderEntry 4 } 

rcVlanIgmpSnoopSenderAction OBJECT-TYPE
	SYNTAX        INTEGER {
		         none(0),
		         flushEntry(1),
	     	         flushGrp(2)
	              }
        MAX-ACCESS        read-write
        STATUS        current
        DESCRIPTION   "Used to specify an action to perform on this group."
        ::= { rcVlanIgmpSnoopSenderEntry 5 } 


-- PHYSICAL Elements

rcChasType OBJECT-TYPE
	SYNTAX	      INTEGER {
		         unknown(1),  -- unknown chassis
 		         a1100(2),    -- 3  slot chassis (1/2, 1/2, full)
 		         a1250(6),    -- 4  slot chassis (full, ... , full)
 		         a1150(7),    -- 3  slot chassis (1/2, 1/2, full)
 		         a1200(8),    -- 8  slot chassis (full, ... , full)
 			 a1050(9),    -- 2  slot chassis (seahawk)
 			 a8006(280887558), -- 6  slot chassis (raptillion)
                         a8010(280887562)  -- 10 slot chassis (raptillion)
	              }
	MAX-ACCESS 	      read-only
	STATUS 	      current
	DESCRIPTION   "Chassis Type"
        ::= { rcChassis 1 }

rcChasSerialNumber OBJECT-TYPE
        SYNTAX        DisplayString (SIZE (0..8))
        MAX-ACCESS        read-only
        STATUS        current
        DESCRIPTION   "Unique serial number for this chassis."
        ::= { rcChassis 2 }

rcChasHardwareRevision OBJECT-TYPE
	SYNTAX 	      DisplayString (SIZE (0..20))
	MAX-ACCESS 	      read-only
	STATUS 	      current
	DESCRIPTION   "Device hardware revision level"
	::= { rcChassis 3 }
	
rcChasNumSlots OBJECT-TYPE
        SYNTAX        INTEGER (1..16)
        MAX-ACCESS        read-only
        STATUS        current
        DESCRIPTION   "The number of slots in the chassis available for
                      plug-in cards."
        ::= { rcChassis 4 }

rcChasNumPorts OBJECT-TYPE
        SYNTAX        INTEGER (0..255) 
        MAX-ACCESS        read-only
        STATUS        current
        DESCRIPTION   "The total number of ports currently installed in
		      the chassis."
        ::= { rcChassis 5 }

-- TBD FIXME : We need to get the final list from Hardware
rcChasTestResult OBJECT-TYPE
	SYNTAX        INTEGER {
			 other(1),
			 ok(2),
			 crceeprom(3),
			 timer(4),
			 procdram(5),
			 led(6),
       	         	 formaccpuaccess(7),
       	         	 asiccpuaccess(8),
                	 memory(9),
                	 loopback(10)
		      }
	MAX-ACCESS 	      read-only
	STATUS 	      current
	DESCRIPTION   "Chassis start-up diagnostic tests."
	::= { rcChassis 6 }

rcChasFan OBJECT IDENTIFIER ::= { rcChassis 7 }

rcChasFanTable OBJECT-TYPE
	SYNTAX        SEQUENCE OF RcChasFanEntry
	MAX-ACCESS        not-accessible
	STATUS        current
	DESCRIPTION   "This table contains information about power 
		      supplies."
	::= { rcChasFan 1 }

rcChasFanEntry OBJECT-TYPE
	SYNTAX        RcChasFanEntry
	MAX-ACCESS        not-accessible
	STATUS        current
	DESCRIPTION   "Contains information regarding a power supply
		      unit."
	INDEX         { rcChasFanId }
	::= { rcChasFanTable 1 }

RcChasFanEntry ::=
	SEQUENCE {
		rcChasFanId INTEGER,
		rcChasFanOperStatus INTEGER,
		rcChasFanAmbientTemperature Gauge32
	}

rcChasFanId OBJECT-TYPE
	SYNTAX        INTEGER(1..4)
	MAX-ACCESS        read-only
	STATUS        current
	DESCRIPTION ""
	::= { rcChasFanEntry 1 }

rcChasFanOperStatus OBJECT-TYPE
	SYNTAX        INTEGER {
		         unknown(1),
		         up(2),
		         down(3)
	              }
	MAX-ACCESS        read-only
	STATUS        current
	DESCRIPTION   "Actual status of the Fan:
	              - unknown(1) - status can not be determined.
	              - up(2) - present and supplying power.
	              - down(3) - present, but failure indicated."
	::= { rcChasFanEntry 2 }

rcChasFanAmbientTemperature OBJECT-TYPE
        SYNTAX          Gauge32
        MAX-ACCESS          read-only
        STATUS          current
        DESCRIPTION     "Used to indicate the temperature of the air
                        entering the fan."
        ::= { rcChasFanEntry 3 }

rcChasPowerSupply OBJECT IDENTIFIER ::= { rcChassis 8 }

rcChasPowerSupplyTable OBJECT-TYPE
	SYNTAX        	SEQUENCE OF RcChasPowerSupplyEntry
	MAX-ACCESS        	not-accessible
	STATUS        	current
	DESCRIPTION   	"This table contains information about power 
		      	supplies."
	::= { rcChasPowerSupply 1 }

rcChasPowerSupplyEntry OBJECT-TYPE
	SYNTAX        	RcChasPowerSupplyEntry
	MAX-ACCESS        	not-accessible
	STATUS        	current
	DESCRIPTION   	"Contains information regarding a power supply
		      	unit."
	INDEX  { rcChasPowerSupplyId }
	::= { rcChasPowerSupplyTable 1 }

RcChasPowerSupplyEntry ::=
	SEQUENCE {
		rcChasPowerSupplyId INTEGER,
		rcChasPowerSupplyOperStatus INTEGER
	}

rcChasPowerSupplyId OBJECT-TYPE
	SYNTAX        	INTEGER(1..3)
	MAX-ACCESS        	read-only
	STATUS        	current
	DESCRIPTION ""
	::= { rcChasPowerSupplyEntry 1 }


rcChasPowerSupplyOperStatus OBJECT-TYPE
	SYNTAX         INTEGER {
		          unknown(1),
		          empty(2),
		          up(3),
	     	          down(4)
	               }
	MAX-ACCESS         read-only
	STATUS         current
	DESCRIPTION   "Actual status of the power supply:
	              - unknown(1) - status can not be determined.
	              - empty(2) - power supply not installed.
	              - up(3) - present and supplying power.
	              - down(4) - present, but failure indicated."
	::= { rcChasPowerSupplyEntry 2 }


rcChasPowerSupplyDetailTable OBJECT-TYPE
	SYNTAX        	SEQUENCE OF RcChasPowerSupplyDetailEntry
	MAX-ACCESS        	not-accessible
	STATUS        	current
	DESCRIPTION   	"This table contains detailed information about
			power supplies."
	::= { rcChasPowerSupply 2 }

rcChasPowerSupplyDetailEntry OBJECT-TYPE
	SYNTAX        	RcChasPowerSupplyDetailEntry
	MAX-ACCESS        	not-accessible
	STATUS        	current
	DESCRIPTION   	"Contains detailed info regarding a power supply
		      	unit."
	INDEX  { rcChasPowerSupplyDetailId }
	::= { rcChasPowerSupplyDetailTable 1 }

RcChasPowerSupplyDetailEntry ::=
	SEQUENCE {
		rcChasPowerSupplyDetailId INTEGER,
		rcChasPowerSupplyDetailType INTEGER,
		rcChasPowerSupplyDetailSerialNumber DisplayString,
		rcChasPowerSupplyDetailHardwareRevision DisplayString,
		rcChasPowerSupplyDetailPartNumber DisplayString
	}

rcChasPowerSupplyDetailId OBJECT-TYPE
	SYNTAX        	INTEGER(1..3)
	MAX-ACCESS        	read-only
	STATUS        	current
	DESCRIPTION ""
	::= { rcChasPowerSupplyDetailEntry 1 }

rcChasPowerSupplyDetailType OBJECT-TYPE
        SYNTAX        	INTEGER {
				ac(1),
				dc(2)
		      	}
        MAX-ACCESS        	read-only
        STATUS        	current
	DESCRIPTION ""
        ::= { rcChasPowerSupplyDetailEntry 2 }

rcChasPowerSupplyDetailSerialNumber OBJECT-TYPE
        SYNTAX        DisplayString (SIZE (0..8))
        MAX-ACCESS        read-only
        STATUS        current
	DESCRIPTION ""
        ::= { rcChasPowerSupplyDetailEntry 3 }

rcChasPowerSupplyDetailHardwareRevision OBJECT-TYPE
        SYNTAX        DisplayString (SIZE (0..8))
        MAX-ACCESS        read-only
        STATUS        current
	DESCRIPTION ""
        ::= { rcChasPowerSupplyDetailEntry 4 }

rcChasPowerSupplyDetailPartNumber OBJECT-TYPE
        SYNTAX        DisplayString (SIZE (0..6))
        MAX-ACCESS        read-only
        STATUS        current
	DESCRIPTION ""
        ::= { rcChasPowerSupplyDetailEntry 5 }


rcCard OBJECT IDENTIFIER ::= { rcChassis 9 }

rcCardTable OBJECT-TYPE
	SYNTAX        SEQUENCE OF RcCardEntry
	MAX-ACCESS        not-accessible
	STATUS        current
	DESCRIPTION   "A table that contains information about the 
                      cards in this chassis.  For those slots that 
                      do not contain a physical card, the table may 
		      be implemented to contain a conceptual row 
                      with the type of physical module set to 
 		      'chasCardEmpty', or it may be implemented to 
		      have no conceptual row instance."
	::= { rcCard 1 }

rcCardEntry OBJECT-TYPE
	SYNTAX        RcCardEntry
	MAX-ACCESS        not-accessible
	STATUS        current
	DESCRIPTION   "Card attributes"
	INDEX         { rcCardIndex }
	::= { rcCardTable 1 }

RcCardEntry ::=
	SEQUENCE {
		rcCardIndex INTEGER,
		rcCardType INTEGER,
		rcCardSerialNumber DisplayString,
		rcCardHardwareRevision DisplayString,
		rcCardAdminStatus INTEGER,
		rcCardOperStatus INTEGER,
		rcCardPCMCIAType INTEGER,
		rcCardPartNumber DisplayString
	}

rcCardIndex OBJECT-TYPE
        SYNTAX        	INTEGER (1..8)
        MAX-ACCESS        	read-only
        STATUS       	current
        DESCRIPTION   	"A unique value for each module within the chassis.
                      	This value is determined by the chassis slot number
                      	where the module is inserted.  Valid entries are 1
                      	to the value of rcChasNumSlots"
        ::= { rcCardEntry 1 }

rcCardType OBJECT-TYPE
        SYNTAX        INTEGER {
	other(1),                        -- no card installed
        rcCPU(2),                        -- [1200] CPU Card (A1200)
        rc8x100BaseTX(3),                -- [1208TX] 8 port (cat 5) (A1200)
        rc8x100BaseT2(4),                -- [] 8 port (cat 3) (A1200)
        rc8x100BaseF(5),                 -- [1208FX] 8 port fiber (A1200)
        rc16x100BaseTX(6),               -- [1216TX] 16 port (cat 5) (A1200)
        rc8x100BaseTXWG(12),             -- [1108TX] 8 port (half width) (A1100)
        rc16x100BaseTXWG(13),            -- [1100] 16 port + CPU (A1100)
        rc4x100BaseFWG(14),              -- [1104FX] 4 port (half width) (A1100)
        rc12x100BaseTXWG(15),            -- [1050] 12 port + CPU (A1050)
        rc12x100BaseFBB(16),             -- [] 12 port (A1200)
        rc8x100BaseFWG(17),              -- [1108FX] 8 port (A1100)
        rc12x100BaseTX-2x100BaseFBB(18), -- [] 12 port + 2 port (A1200)
        rc2x155BaseFBB(19),              -- [] 2 sonet port (A1200)
        rc4x155BaseFBB(20),              -- [] 4 sonet port (A1200)
        rc16x100BaseFBB(21),             -- [1216FX] 16 port fiber (A1200)
        rc14x100BaseTX-2x100BaseFBB(22), -- [1216TF] 14 port + 2 port (A1200)
        rc8x10BaseFBB(23),               -- [1208FL] 8 port fiber low-speed (A1200)
	rc4xOC3(24),			 -- [1200xx] 4 port OC3 (A1200)
	rc1xOC12(25),			 -- [1200xx] 1 port OC12 (A1200)
        rcRMON(26),			 -- [1200xx] RMON (A1200) 
        rc1xOC12POSBaseMMF(27),          -- [1200xx] 1 port OC12 POS (A1200)
        rc1xOC12POSBaseSMF(28),          -- [1200xx] 1 port OC12 POS (A1200)
        rc4x1000BaseSXWG(1028),          -- [1150] 1 0 00 000 0100 + CPU (A1150)
        rc1x1000BaseSXWG(1025),          -- [1101SX] 1 0 00 000 0001
        rc2x1000BaseSXWG(1026),          -- [1102SX] 1 0 00 000 0010
        rc1x1000BaseSXRWG(1537),         -- [1101SR] 1 1 00 000 0001
        rc2x1000BaseSXRWG(1538),         -- [1102SR] 1 1 00 000 0010
        rc1x1000BaseLXWG(1153),          -- [1101LX] 1 0 01 000 0001
        rc2x1000BaseLXWG(1154),          -- [1102LX] 1 0 01 000 0010
        rc2x1000BaseXDWG(1282),          -- [1102XD] 1 0 10 000 0010
        rc1x1000BaseLXRWG(1665),         -- [1101LR] 1 1 01 000 0001
        rc2x1000BaseLXRWG(1666),         -- [1102LR] 1 1 01 000 0010
        rc1x1000BaseSXBB(1041),          -- [1201SX] 1 0 00 001 0001
        rc2x1000BaseSXBB(1042),          -- [1202SX] 1 0 00 001 0010
        rc1x1000BaseSXRBB(1553),         -- [1201SR] 1 1 00 001 0001
        rc2x1000BaseSXRBB(1554),         -- [1202SR] 1 1 00 001 0010
        rc1x1000BaseLXBB(1169),          -- [1201LX] 1 0 01 001 0001
        rc2x1000BaseLXBB(1170),          -- [1202LX] 1 0 01 001 0010
        rc2x1000BaseXDBB(1298),          -- [1202XD] 1 0 10 001 0010
        rc1x1000BaseLXRBB(1681),         -- [1201LR] 1 1 01 001 0001
        rc2x1000BaseLXRBB(1682)          -- [1202LR] 1 1 01 001 0010
	}
	MAX-ACCESS 	      	read-only
	STATUS 	      	current
	DESCRIPTION   	"Used to indicate a card types in the Accelar
			1000 product families.  

			For Accelar 1000 devices, gigabit cards use
		      	an encoded value according to the following rule:

                                +-----+--+-+---+---+---+
                      	bits  : |31-11|10|9|8-7|6-4|3-0|
                                +-----+--+-+---+---+---+
                      	field : |  a  | b|c| d | e | f |
                                +-----+--+-+---+---+---+

                             a : not-used
                             b : 1=gigabit
                             c : 0=non-redundant, 
                                 1=redundant
                             d : 0=short-haul, 
                                 1=long-haul, 
                                 2=extra-distance,
                             e : 0=work-group(a1100 & a1150)
                                 1=back-bone(a1200 & f1250 & f2000), 
                             f : 1=1-port, 2=2-port, 4=4-port, 8=8-port
                      "
	::= { rcCardEntry 2 }

rcCardSerialNumber OBJECT-TYPE
        SYNTAX        DisplayString (SIZE (0..8))
	MAX-ACCESS        read-only
	STATUS        current
	DESCRIPTION   "Unique serial number for this card."
	::= { rcCardEntry 3 }

rcCardHardwareRevision OBJECT-TYPE
	SYNTAX        DisplayString (SIZE (0..8))
	MAX-ACCESS        read-only
	STATUS        current
	DESCRIPTION   "Hardware Version"
	::= { rcCardEntry 4 }

rcCardAdminStatus OBJECT-TYPE
        SYNTAX       INTEGER { 
			 up(1),
         		 down(2),
			 testing(3)
                      }
        MAX-ACCESS        read-write 
        STATUS        current
        DESCRIPTION   "Used to indicate the administrative status of this
                       card"
        ::= { rcCardEntry 5 }

rcCardOperStatus OBJECT-TYPE
	SYNTAX        INTEGER { 
			 up(1),
         		 down(2),
			 testing(3),
			 unknown(4),
		 	 dormant(5)
                      }
	MAX-ACCESS        read-only
	STATUS        current
	DESCRIPTION   "Used to indicate the operational status of this card."
	::= { rcCardEntry 6 }

rcCardPCMCIAType OBJECT-TYPE
        SYNTAX        INTEGER {
			 none(1),
			 modem28kbs(2),
			 flash2meg(3),
			 flash4meg(4)
                      }
        MAX-ACCESS        read-only
        STATUS        current
        DESCRIPTION   "Used to indicate the type of PCMCIA card currently
                      installed in this CPU card, if any.

                      For non-CPU cards, this variable has no meaning and
                      will always be set to none."
	DEFVAL        { none }
        ::= { rcCardEntry 7 }

rcCardPartNumber OBJECT-TYPE
        SYNTAX        	DisplayString (SIZE (0..6))
        MAX-ACCESS        	read-only
        STATUS        	current
        DESCRIPTION   	"Card Part Number"
        ::= { rcCardEntry 8 }

-- Port Table

rcPort OBJECT IDENTIFIER ::= { rcChassis 10 }

rcPortTable OBJECT-TYPE
        SYNTAX	      SEQUENCE OF RcPortEntry
        MAX-ACCESS        not-accessible
        STATUS        current
        DESCRIPTION   "Port table"
        ::= { rcPort 1 }

rcPortEntry OBJECT-TYPE
        SYNTAX        RcPortEntry
        MAX-ACCESS        not-accessible
        STATUS        current
        DESCRIPTION   "Entry containing info. for a particular port"
        INDEX         { rcPortIndex }
        ::= { rcPortTable 1 }

RcPortEntry ::= SEQUENCE {
		rcPortIndex                           InterfaceIndex,
		rcPortType                            INTEGER,
                rcPortConnectorType                   INTEGER,
		rcPortPerformRouting                  TruthValue,
		rcPortHighPriority                    TruthValue,
                rcPortAction                          INTEGER,
                rcPortResult                          INTEGER,
                rcPortPrimaryConnector                INTEGER,
                rcPortActiveConnector                 INTEGER,
                rcPortBackupConnectorStatus           INTEGER,
                rcPortAutoNegotiate                   TruthValue,
                rcPortAdminDuplex                     INTEGER,
                rcPortOperDuplex                      INTEGER,
                rcPortAdminSpeed                      INTEGER,
                rcPortOperSpeed                       INTEGER,
		rcPortMltId		              INTEGER,
		rcPortLocked		              TruthValue,
		rcPortAutoNegotiationSupported        TruthValue,
		rcPortSingleRoutablePort              TruthValue,
		rcPortUnknownMacDiscard               TruthValue,
                rcPortNumStateTransition              Counter32,
                rcPortAllowOversizeFrame              TruthValue,
		rcPortUserPriority	              INTEGER,
		rcPortQosLevel	                      INTEGER,
		rcPortDiffServEnable                  TruthValue,
		rcPortDiffServType                    INTEGER,
		rcPortDiffServIeee8021POverrideEnable TruthValue,
		rcPortVendorDescr                     DisplayString
	}

rcPortIndex OBJECT-TYPE
        SYNTAX        InterfaceIndex
        MAX-ACCESS        read-only
        STATUS        current
        DESCRIPTION   "An index value that uniquely identifies a port.
                      This value is similar to ifIndex in MIB2."
        ::= { rcPortEntry 1 }

rcPortType OBJECT-TYPE
	SYNTAX        INTEGER {
		         other(0),	     -- no port installed
		         rc100BaseTX(1),     -- (cat 5)
		         rc100BaseT2(2),     -- (cat 3)
		         rc100BaseF(3),	     -- (100 mbps fiber)
		         rc1000BaseF(4),     -- (1000 mbps fiber)
		         rc1000BaseDualF(5), -- (fiber - dual connector)
		         rc10BaseF(6),	     -- (10 mbps fiber)
                         rcPosMMF(7),        -- (multi mode fiber)
                         rcPosSMF(8),        -- (single mode fiber)
                         rcAtm(9),           -- (oc3, oc12, ds3, e3)
		         rcGbicLx(10),	     -- (gigabit long haul)
                         rcGbicSx(11),       -- (gigabit short haul)
                         rcGbicXd(12),       -- (gigabit extended distance)
                         rcGbicCu(13),       -- (gigabit copper)
                         rcGbicOther(14),    -- (gigabit other)
                         rcOc3cSM(15),       -- (OC-3c SM)
                         rcOc3cMM(16),       -- (OC-3c MM)
                         rcOc3cCOPPER(17),   -- (OC-3c COPPER)
                         rcOc12cSM(18),      -- (OC-12c SM)
                         rcOc12cMM(19),      -- (OC-12c MM)
                         rcDs3(20),          -- (Ds3)
                         rcE3(21),           -- (E3)
                         rcGbicNone(22)      -- (Gbic card feature)
	              }
	MAX-ACCESS        read-only
	STATUS        current
	DESCRIPTION   "Port type"
	::= { rcPortEntry 2 }

rcPortConnectorType OBJECT-TYPE
        SYNTAX        INTEGER {
                         nonRedundant(1), -- non-redundant connector type 
                         redundant(2) 	  -- redundant connector type 
                      }
        MAX-ACCESS        read-only
        STATUS        current
        DESCRIPTION   "Type of connector installed on this port."
        DEFVAL        { nonRedundant }
        ::= { rcPortEntry 3 }

rcPortPerformRouting OBJECT-TYPE
	SYNTAX 	      TruthValue
	MAX-ACCESS 	      read-write
        STATUS 	      deprecated
	DESCRIPTION   "Indicate whether this port should perform
                      routing"
	DEFVAL	      { false }
	::= { rcPortEntry 4 }

rcPortHighPriority OBJECT-TYPE 
        SYNTAX 	      TruthValue
        MAX-ACCESS 	      read-write
        STATUS 	      deprecated
        DESCRIPTION   "Indicate whether this port should be treated with 
                      high priority"
	DEFVAL 	      { false }
        ::= { rcPortEntry 5 }

rcPortAction OBJECT-TYPE
        SYNTAX        INTEGER {
                         none(1),            -- none of the following
                         flushMacFdb(2),     -- flush MAC forwarding table
                         flushArp(3),        -- flush ARP table
                         flushIp(4),         -- flush IP route table
                         flushAll(5),        -- flush all tables
			 triggerRipUpdate(6) -- manually trigger rip update
                      }
        MAX-ACCESS        read-write
        STATUS        current
        DESCRIPTION   "Port related actions."
        DEFVAL        { none }
        ::= { rcPortEntry 6 }
 
rcPortResult OBJECT-TYPE 
        SYNTAX        	INTEGER { 
                       		none(1),        -- none of the following 
                       	  	inProgress(2),  -- in progress 
                       	  	success(3),     -- success
                       	  	fail(4)         -- failure 
                      	} 
        MAX-ACCESS		read-only 
        STATUS        	current 
        DESCRIPTION   	"Result from the last Vlan action." 
        DEFVAL        	{ none } 
        ::= { rcPortEntry 7 } 

rcPortPrimaryConnector OBJECT-TYPE 
        SYNTAX 		INTEGER { 
                		left(1),	-- left side connector
                		right(2),	-- right side connector 
				other(3)
        		} 
        MAX-ACCESS          read-write 
        STATUS          current 
        DESCRIPTION     "For ports configured with redundant connectors,
			 this value is used to indicate which connector 
			 should be used as the 'active' connector on this 
			 port the next time the port is placed into the 
			 ifAdminStatus=Up."
	DEFVAL          { left } 
        ::= { rcPortEntry 8 }

rcPortActiveConnector OBJECT-TYPE
        SYNTAX        INTEGER {
                         	left(1),	-- left side connector
                         	right(2),       -- right side connector
				other(3)
                      }
        MAX-ACCESS        read-only
        STATUS        current 
        DESCRIPTION   "For ports configured with redundant connectors,
		      this value is used to indicate which connector
		      is currently the active one.  Only one connector
		      can be active an anytime."
        DEFVAL        { left } 
        ::= { rcPortEntry 9 }

rcPortBackupConnectorStatus OBJECT-TYPE
        SYNTAX 		INTEGER {
                		up(1),            -- link Up
                		down(2),          -- link Down
				other(3)
        }
        MAX-ACCESS          read-only
        STATUS          current
        DESCRIPTION     "Indicate the status of the link attached to the
		 	 back-up (non-active) connector."
        ::= { rcPortEntry 10 }

rcPortAutoNegotiate OBJECT-TYPE
	SYNTAX 	      TruthValue
	MAX-ACCESS 	      read-write
        STATUS 	      current
	DESCRIPTION   "Indicate whether this port enabled for auto 
                      negotiations or not."
	DEFVAL	      { true }
	::= { rcPortEntry 11 }

rcPortAdminDuplex OBJECT-TYPE
        SYNTAX 		INTEGER { 
                		half(1),	-- half duplex
                		full(2)		-- full duplex  
        		} 
	MAX-ACCESS 		read-write
        STATUS 		current
	DESCRIPTION     "Indicates the port duplex type "	
	DEFVAL		{ half }
	::= { rcPortEntry 12 }

rcPortOperDuplex OBJECT-TYPE
        SYNTAX 		INTEGER { 
                		half(1),	-- half duplex
                		full(2)		-- full duplex  
        		} 
	MAX-ACCESS 		read-only
        STATUS 		current
	DESCRIPTION 	"Indicate this port's current duplex value."
	::= { rcPortEntry 13 }

rcPortAdminSpeed OBJECT-TYPE
        SYNTAX 		INTEGER { 
				none(0),
                		mbps10(1),	-- 10Mb/s
                		mbps100(2),	-- 100Mb/s
                		mbps1000(3)	-- 1000Mb/s
        		} 
	MAX-ACCESS 		read-write
        STATUS 		current
	DESCRIPTION 	"Indicate this port's speed."
	DEFVAL		{ mbps10 }
	::= { rcPortEntry 14 }

rcPortOperSpeed OBJECT-TYPE
        SYNTAX 		Integer32
	MAX-ACCESS 	      	read-only
        STATUS 	      	current
	DESCRIPTION   	"Indicate this port's current speed value."
	::= { rcPortEntry 15 }

rcPortMltId OBJECT-TYPE
        SYNTAX 		Integer32
	MAX-ACCESS 	      	read-only
        STATUS 	      	current
	DESCRIPTION   	"Indicate which multi-link trunk (MLT) this port
		 	is assigned to.  If this port is not associated
			with any MLT, this value will be set to zero(0)."
	DEFVAL		{ 0 }
	::= { rcPortEntry 16 }

rcPortLocked OBJECT-TYPE
        SYNTAX        	TruthValue
        MAX-ACCESS        	read-only
        STATUS        	current
        DESCRIPTION   	"Indicate whether this port is locked." 
        DEFVAL        	{ false }
        ::= { rcPortEntry 17 }

rcPortAutoNegotiationSupported OBJECT-TYPE
        SYNTAX        	TruthValue
        MAX-ACCESS        	read-only
        STATUS        	current
        DESCRIPTION   	"Indicate whether this port can support 
		      	auto-negotiation." 
        DEFVAL        	{ false }
        ::= { rcPortEntry 18 }

rcPortSingleRoutablePort OBJECT-TYPE
        SYNTAX        	TruthValue
        MAX-ACCESS        	read-only
        STATUS        	current
        DESCRIPTION   	"Indicate whether this port is a single routable
		      	port.  If this value is true, the port functions
			like a traditional router port."
        DEFVAL        	{ false }
        ::= { rcPortEntry 19 }

rcPortUnknownMacDiscard OBJECT-TYPE
        SYNTAX          TruthValue
        MAX-ACCESS          read-write
        STATUS          current
        DESCRIPTION     "If rcUnknownMacDiscard is set to True, 
                         then a packet with an unknown source MAC address
                         is dropped on that port, and other ports then
                         will discard any packets with this MAC address
                         in the destination field.  
                         For example, 
                         suppose 11:22:33:44:55:66 is an unknown source MAC,
                         packets with source MAC 11:22:33:44:55 coming from 
                         this port is discarded, further more, packets with
                         destination MAC 11:22:33:44:55:66 coming from
                         other ports are also discarded, unless this address
                         is later learned on another port or the restriction
                         ages out."

        DEFVAL          { false }
        ::= { rcPortEntry 20 }

rcPortNumStateTransition OBJECT-TYPE
        SYNTAX        	Counter32
        MAX-ACCESS        	read-only
        STATUS        	current
        DESCRIPTION   	"# state transitions."
        ::= { rcPortEntry 21 }

rcPortUserPriority OBJECT-TYPE
        SYNTAX  	INTEGER {
                            level0(0),
                            level1(1),
                            level2(2),
                            level3(3),
                            level4(4),
                            level5(5),
                            level6(6),
                            level7(7)
                        }
	MAX-ACCESS 	      	read-write
        STATUS 	      	deprecated
	DESCRIPTION   	"User priority level."
        DEFVAL          { level7 }
	::= { rcPortEntry 22 }

rcPortAllowOversizeFrame OBJECT-TYPE
        SYNTAX          TruthValue
        MAX-ACCESS          read-write
        STATUS          current
        DESCRIPTION     "Used to specify whether over-size frames should be
			processed or dropped."
        ::= { rcPortEntry 23 }

rcPortQosLevel OBJECT-TYPE
        SYNTAX  	INTEGER {
                            level0(0),
                            level1(1),
                            level2(2),
                            level3(3),
                            level4(4),
                            level5(5),
                            level6(6),
                            level7(7)
                        }
	MAX-ACCESS 	      	read-write
        STATUS 	      	current
        DESCRIPTION     "Used to specify the Qos level packets, carried on this
                        port, should be processed with."
        DEFVAL          { level1 }
	::= { rcPortEntry 30 }

rcPortDiffServEnable OBJECT-TYPE
        SYNTAX        	TruthValue
        MAX-ACCESS        	read-write
        STATUS        	current
        DESCRIPTION   	"Used to enable/disable the Differentiated Service
			feature on this port."
        DEFVAL        	{ false }
        ::= { rcPortEntry 31 }

rcPortDiffServType OBJECT-TYPE
        SYNTAX  	INTEGER {
                            none(0),
                            access(1),
                            core(2)
                        }
	MAX-ACCESS 	      	read-write
        STATUS 	      	current
	DESCRIPTION   	"Used to specify the Differentiated Service type
			for this port."
        DEFVAL        	{ access }
	::= { rcPortEntry 32 }

rcPortDiffServIeee8021POverrideEnable OBJECT-TYPE
        SYNTAX        	TruthValue
        MAX-ACCESS        	read-write
        STATUS        	current
	DESCRIPTION	"Used to enable/disable the Differentiated Service
			IEEE 802.1P over-ride feature."
        DEFVAL        	{ false }
        ::= { rcPortEntry 33 }

rcPortVendorDescr OBJECT-TYPE
        SYNTAX        	DisplayString (SIZE(16))
        MAX-ACCESS        	read-only
        STATUS        	current
        DESCRIPTION   	"Used to show the name of the vendor of this port's
			connector.  Only applicable to ports on a GBIC cards."
        ::= { rcPortEntry 34 }

-- Port Lock Group

rcPortLock OBJECT IDENTIFIER ::= { rcChassis 11 }

rcPortLockEnable OBJECT-TYPE
        SYNTAX        	TruthValue
        MAX-ACCESS        	read-write
        STATUS        	current
        DESCRIPTION   	"Indicate whether the port lock feature is enabled."
        DEFVAL        	{ false }
        ::= { rcPortLock 1 }

rcPortLockLockedPorts OBJECT-TYPE
        SYNTAX        	PortSet
        MAX-ACCESS        	read-write
        STATUS        	current
        DESCRIPTION   	"The set of ports that are administratively locked.
		      	Locked ports cannot be modified in anyway until the
		      	port is unlocked first."
        ::= { rcPortLock 2 }


-- Additional Chassis Group Variables

rcChasAruMode OBJECT-TYPE
        SYNTAX        	INTEGER 
			{
				aruOne(1),
				aruTwo(2),
				aruThree(3)
			}
        MAX-ACCESS        	read-only
        STATUS        	current
        DESCRIPTION   	"The ARU mode the chassis is operating in."
        ::= { rcChassis 12 }

rcChasQuidMode OBJECT-TYPE
        SYNTAX        	INTEGER 
			{
				quidMixed(1),
				quidTwo(2),
				quidThree(3),
				quidFour(4),
				quidFive(5)
			}
        MAX-ACCESS        	read-only
        STATUS        	current
        DESCRIPTION   	"The Quid mode the chassis is operating in."
        ::= { rcChassis 13 }

rcChasEocModeAdminStatus OBJECT-TYPE
        SYNTAX        	INTEGER 
			{
				default(0),
				aru1Quid4(1),
				aru2Quid4(2),
				aru2Quid5(3),
				aru3Quid4(4),
				aru3Quid5(5)
			}
        MAX-ACCESS        	read-write
        STATUS        	current
        DESCRIPTION     "Used to specify the Enforce Operational
                        Configuration Mode(EOC) of the system.  When a
                        device is configured with hardware of different
                        revisions, the system will initialize in some
                        deterministic manner (e.g., the lowest common
                        denominator that makes sense based on the hardware
                        configuration).  This is the 'default(0)' mode.
                        The user can override this behavior by manually
                        specifying the EOC Mode they would like."
        ::= { rcChassis 14 }

rcChasEocModeOperStatus OBJECT-TYPE
        SYNTAX        	INTEGER 
			{
				default(0),
				aru1Quid4(1),
				aru2Quid4(2),
				aru2Quid5(3),
				aru3Quid4(4),
				aru3Quid5(5)
			}
        MAX-ACCESS        	read-only
        STATUS        	current
        DESCRIPTION     "Used to indicate the Enforce Operational
                        Configuration Mode(EOC) of the system."
        ::= { rcChassis 15 }

rcChasBrouterPorts OBJECT-TYPE
        SYNTAX        	PortSet 
        MAX-ACCESS        	read-only
        STATUS        	current
        DESCRIPTION   	"Used to indicate which ports in the system are
			configured as Brouter ports."
        ::= { rcChassis 17 }

rcChasGlobalFilterEnable OBJECT-TYPE
        SYNTAX        	TruthValue 
        MAX-ACCESS        	read-write
        STATUS        	current
        DESCRIPTION   	"Used to enable/disable global filters in the
			system.  This variable is currently not supported."
	DEFVAL		{ false }
        ::= { rcChassis 18 }

rcChasVlanBySrcMacEnable OBJECT-TYPE
        SYNTAX        	TruthValue 
        MAX-ACCESS        	read-write
        STATUS        	current
        DESCRIPTION   	"Used to enable/disable source MAC based VLANs
			in the system."
	DEFVAL		{ false }
        ::= { rcChassis 19 }


-- Agent Table
 
rcAgentTable OBJECT-TYPE
        SYNTAX        SEQUENCE OF RcAgentEntry
        MAX-ACCESS        not-accessible
        STATUS        current
        DESCRIPTION   "Agents in a chassis table"
        ::= { rcChassis 16 }
 
rcAgentEntry OBJECT-TYPE
        SYNTAX        RcAgentEntry
        MAX-ACCESS        not-accessible
        STATUS        current
        DESCRIPTION   "Entry containing info. for a particular agent"
        INDEX         { rcAgentId }
        ::= { rcAgentTable 1 }
 
RcAgentEntry ::= SEQUENCE {
                rcAgentId       INTEGER,
                rcAgentSlot     INTEGER,
                rcAgentIpAddr   IpAddress
        }
 
rcAgentId OBJECT-TYPE
        SYNTAX        Integer32
        MAX-ACCESS        read-only
        STATUS        current
        DESCRIPTION   "entry id"
        ::= { rcAgentEntry 1 }
 
rcAgentSlot OBJECT-TYPE
        SYNTAX        Integer32
        MAX-ACCESS        read-only
        STATUS        current
        DESCRIPTION   "slot agent is in."
        ::= { rcAgentEntry 2 }
 
rcAgentIpAddr OBJECT-TYPE
         SYNTAX        IpAddress
         MAX-ACCESS        read-only
         STATUS        current
         DESCRIPTION   "agent's ip address."
         ::= { rcAgentEntry 3 }


-- Mirror Group

rcMirrorSaveConfig OBJECT-TYPE
        SYNTAX        	TruthValue
        MAX-ACCESS        	read-write
        STATUS        	current
        DESCRIPTION   	"Control whether Mirror configuration information 
                       	should be saved to NVRAM so mirror settings can 
                       	be automatically reinstalled after a system
                       	reboot. 

                       	Setting rcMirrorSaveConfig to true does not 
                       	immediately save the configuration information.
                       	The save happens when the rcSysAction variable 
                       	is set to 'saveToNVRAM(4)'."
        ::= { rcMirror 1 }

rcMirrorByPort OBJECT IDENTIFIER ::= { rcMirror 2 }

rcMirrorByPortEnable OBJECT-TYPE
        SYNTAX        	TruthValue
        MAX-ACCESS        	read-write
        STATUS        	current
        DESCRIPTION   	"Used to indicate whether the mirror by port
                       	feature is active.  The system can only support 
                       	mirroring on two ports.  When this feature is 
                       	active, all packets received on the port(s) 
                       	specified by rcMirrorSrcPortOne and/or 
                       	rcMirrorSrcPortTwo are copied to rcMirrorDstPort.  
                       	The mirroring operation is non-intrusive." 
	DEFVAL 		{ false }
        ::= { rcMirrorByPort 1 }

rcMirrorByPortMirrorPort OBJECT-TYPE 
        SYNTAX        	InterfaceIndex 
        MAX-ACCESS        	read-write
        STATUS       	current 
        DESCRIPTION   	"The ifIndex of the port to forward mirrored frames to." 
        ::= { rcMirrorByPort 2 }

rcMirrorByPortEnableMirroredPortOne OBJECT-TYPE
        SYNTAX        	TruthValue
        MAX-ACCESS        	read-write
        STATUS        	current
        DESCRIPTION   	"Used to indicate whether the port specified in
                       	rcMirrorByPortMirroredPortOne should be mirrored." 
	DEFVAL 		{ false }
        ::= { rcMirrorByPort 3 }

rcMirrorByPortMirroredPortOne OBJECT-TYPE
        SYNTAX        	InterfaceIndex
        MAX-ACCESS        	read-write
        STATUS        	current
        DESCRIPTION   	"The ifIndex of the port to be mirrored.  That
		       	is, traffic received on this port will be sent
		       	to the mirror port." 
        ::= { rcMirrorByPort 4 }

rcMirrorByPortEnableMirroredPortTwo OBJECT-TYPE
        SYNTAX        	TruthValue
        MAX-ACCESS        	read-write
        STATUS        	current
        DESCRIPTION   	"Used to indicate whether the port specified in
                       	rcMirrorByPortMirroredPortTwo should be mirrored." 
	DEFVAL 		{ false }
        ::= { rcMirrorByPort 5 }

rcMirrorByPortMirroredPortTwo OBJECT-TYPE
        SYNTAX        	InterfaceIndex
        MAX-ACCESS        	read-write
        STATUS        	current
        DESCRIPTION   	"The ifIndex of the port to be mirrored.  That
		       	is, traffic received on this port will be sent
		       	to the mirror port." 
        ::= { rcMirrorByPort 6 }
 
-- Dip-Switch Group

rcIsolateUnconfigPorts OBJECT-TYPE
        SYNTAX        TruthValue
        MAX-ACCESS        read-only
        STATUS        current
        DESCRIPTION   "Used to indicate whether ports that are unconfigured
                      should be assigned to the 'isolated' VLAN.  Ports
                      assigned to the 'isolated' VLAN can only communicate
                      with the CP port.   If this option is not specified,
                      unconfigured ports will be assigned to the 'default'
                      VLAN"
        ::= { rcDipSwitch 1 }

rcUseFactorySettings OBJECT-TYPE
        SYNTAX        TruthValue
        MAX-ACCESS        read-only
        STATUS        current
        DESCRIPTION   "Used to indicate whether the system should ignore
                      the configuration information stored in NVRAM when
                      the system is booted."   
        ::= { rcDipSwitch 2 }

rcHighPriorityMode OBJECT-TYPE
        SYNTAX        TruthValue
        MAX-ACCESS        read-only
        STATUS        current
        DESCRIPTION   "Used to indicate whether the system is configured
                      to operate in a high priority mode.  The switch can  
                      operate in either a 'best effort' or 'high priority' 
                      mode.  In the 'best effort' setting, the maximum 
                      queue thresholds for the QUIDs are set to 768/768 
                      buffers.  In the 'high priority' mode the setting
                      is 512/768.  This means that in 'high priority' mode
                      the normal priority queue can't have more than 512 
                      buffers, while the high priority queue can have up 
                      to 768." 
        ::= { rcDipSwitch 3 }


-- Table Size Group

rcTblRmonStatSize OBJECT-TYPE
        SYNTAX        Integer32
        MAX-ACCESS        read-only
        STATUS        current
        DESCRIPTION   "Used to indicate the current size of the RMON
                      Statistic table."
        ::= { rcTblSize 1 }

rcTblRmonHistoryControlSize OBJECT-TYPE
        SYNTAX        Integer32
        MAX-ACCESS        read-only
        STATUS        current
        DESCRIPTION   "Used to indicate the current size of the RMON  
                      History Control table." 
        ::= { rcTblSize 2 }

rcTblRmonHistoryEnetSize OBJECT-TYPE
        SYNTAX        Integer32
        MAX-ACCESS        read-only
        STATUS        current
        DESCRIPTION   "Used to indicate the current size of the RMON  
                      History Ethernet table." 
        ::= { rcTblSize 3 }

rcTblRmonAlarmSize OBJECT-TYPE
        SYNTAX        Integer32
        MAX-ACCESS        read-only
        STATUS        current
        DESCRIPTION   "Used to indicate the current size of the RMON  
                      Alarm table." 
        ::= { rcTblSize 4 }

rcTblRmonEventSize OBJECT-TYPE
        SYNTAX        Integer32
        MAX-ACCESS        read-only
        STATUS        current
        DESCRIPTION   "Used to indicate the current size of the RMON  
                      Event table." 
        ::= { rcTblSize 5 }

rcTblRmonLogSize OBJECT-TYPE
        SYNTAX        Integer32
        MAX-ACCESS        read-only
        STATUS        current
        DESCRIPTION   "Used to indicate the current size of the RMON  
                      Log table." 
        ::= { rcTblSize 6 }

rcTblArTblSize OBJECT-TYPE  
        SYNTAX        Integer32
        MAX-ACCESS        read-only  
        STATUS        current  
        DESCRIPTION   "Used to indicate the size of the Address 
                      Translation (AR) table."
        ::= { rcTblSize 7 }


rcTblArFree OBJECT-TYPE  
        SYNTAX        Integer32
        MAX-ACCESS        read-only  
        STATUS        current  
        DESCRIPTION   "Used to indicate the number of free
                      entries that are available in the Address 
                      Translation (AR) table."
        ::= { rcTblSize 8 }

rcTblArNoSpace OBJECT-TYPE  
        SYNTAX        Integer32
        MAX-ACCESS        read-only  
        STATUS        current  
        DESCRIPTION   "Used to indicate the number of entries that could
                      not be added to the Address Translation (AR) table
                      due to lack of space."  
        ::= { rcTblSize 9 }

rcTblArAdded OBJECT-TYPE
        SYNTAX        Integer32
        MAX-ACCESS        read-only
        STATUS        current
        DESCRIPTION   "Used to indicate the number of entries added to
                      the Address Translation (AR) table." 
        ::= { rcTblSize 10 }

rcTblArDeleted OBJECT-TYPE 
        SYNTAX        Integer32
        MAX-ACCESS        read-only 
        STATUS        current 
        DESCRIPTION   "Used to indicate the number of entries deleted to
                      the Address Translation (AR) table."
        ::= { rcTblSize 11 }

rcTblArMacAdded OBJECT-TYPE 
        SYNTAX        Integer32
        MAX-ACCESS        read-only 
        STATUS        current 
        DESCRIPTION   "Used to indicate the number of MAC entries added to
                      the Address Translation (AR) table."
        ::= { rcTblSize 12 }

rcTblArMacDeleted OBJECT-TYPE 
        SYNTAX        Integer32
        MAX-ACCESS        read-only 
        STATUS        current 
        DESCRIPTION   "Used to indicate the number of MAC entries deleted to
                      the Address Translation (AR) table."
        ::= { rcTblSize 13 }

rcTblArMacMoved OBJECT-TYPE 
        SYNTAX        Integer32
        MAX-ACCESS        read-only 
        STATUS        current 
        DESCRIPTION   "Used to indicate the number of MAC entries moved in 
                      the Address Translation (AR) table."
        ::= { rcTblSize 14 }

rcTblArIpAdded OBJECT-TYPE 
        SYNTAX        Integer32
        MAX-ACCESS        read-only 
        STATUS        current 
        DESCRIPTION   "Used to indicate the number of IP entries added to
                      the Address Translation (AR) table."
        ::= { rcTblSize 15 }

rcTblArIpDeleted OBJECT-TYPE  
        SYNTAX        Integer32
        MAX-ACCESS        read-only  
        STATUS        current  
        DESCRIPTION   "Used to indicate the number of IP entries deleted to 
                      the Address Translation (AR) table."    
        ::= { rcTblSize 16 }

rcTblArMcastTblSize OBJECT-TYPE  
        SYNTAX        Integer32
        MAX-ACCESS        read-only  
        STATUS        current  
        DESCRIPTION   "Used to indicate the size of the Multicast 
                      Address Translation (AR) table."
        ::= { rcTblSize 17 }


rcTblArFreeMcastGroups OBJECT-TYPE  
        SYNTAX        Integer32
        MAX-ACCESS        read-only  
        STATUS        current  
        DESCRIPTION   "Used to indicate the number of free multicast
                      groups availabe in the Address Translation (AR) 
                      table."
        ::= { rcTblSize 18 }

rcTblArIpMcastAdded OBJECT-TYPE  
        SYNTAX        Integer32
        MAX-ACCESS        read-only  
        STATUS        current  
        DESCRIPTION   "Used to indicate the number of Ip multicast
                      entries that are added to the Address 
                      Translation (AR) table."
        ::= { rcTblSize 19 }

rcTblArIpMcastDeleted OBJECT-TYPE  
        SYNTAX        Integer32
        MAX-ACCESS        read-only  
        STATUS        current  
        DESCRIPTION   "Used to indicate the number of Ip multicast
                      entries that are deleted from the Address 
                      Translation (AR) table."
        ::= { rcTblSize 20 }

rcTblArVlanByPortAdded OBJECT-TYPE  
        SYNTAX        Integer32
        MAX-ACCESS        read-only  
        STATUS        current  
        DESCRIPTION   "Used to indicate the number of VLAN by port
                      entries that are added to the Address 
                      Translation (AR) table."
        ::= { rcTblSize 21 }

rcTblArVlanByPortDeleted OBJECT-TYPE  
        SYNTAX        Integer32
        MAX-ACCESS        read-only  
        STATUS        current  
        DESCRIPTION   "Used to indicate the number of VLAN by port
                      entries that are deleted from the Address 
                      Translation (AR) table."
        ::= { rcTblSize 22 }

rcTblArVlanByProtocolAdded OBJECT-TYPE  
        SYNTAX        Integer32
        MAX-ACCESS        read-only  
        STATUS        current  
        DESCRIPTION   "Used to indicate the number of Vlans by 
                      Protocol Type entries that are added to 
                      the Address Translation (AR) table."
        ::= { rcTblSize 23 }

rcTblArVlanByProtocolDeleted OBJECT-TYPE  
        SYNTAX        Integer32
        MAX-ACCESS        read-only  
        STATUS        current  
        DESCRIPTION   "Used to indicate the number of Vlans by 
                      Protocol Type entries that are deleted from 
                      the Address Translation (AR) table."
        ::= { rcTblSize 24 }

rcTblArVlanByIpSubnetAdded OBJECT-TYPE  
        SYNTAX        Integer32
        MAX-ACCESS        read-only  
        STATUS        current  
        DESCRIPTION   "Used to indicate the number of VLAN by Ip 
                      entries that are added to the Address 
                      Translation (AR) table."
        ::= { rcTblSize 25 }

rcTblArVlanByIpSubnetDeleted OBJECT-TYPE  
        SYNTAX        Integer32
        MAX-ACCESS        read-only  
        STATUS        current  
        DESCRIPTION   "Used to indicate the number of VLAN by Ip 
                      entries that are deleted from the Address 
                      Translation (AR) table."
        ::= { rcTblSize 26 }

rcTblArIpSubnetsAdded OBJECT-TYPE  
        SYNTAX        Integer32
        MAX-ACCESS        read-only  
        STATUS        current  
        DESCRIPTION   "Used to indicate the number of Ip subnet
                      entries that are added to the Address 
                      Translation (AR) table."
        ::= { rcTblSize 27 }

rcTblArIpSubnetsDeleted OBJECT-TYPE  
        SYNTAX        Integer32
        MAX-ACCESS        read-only  
        STATUS        current  
        DESCRIPTION   "Used to indicate the number of Ip subnet 
                      entries that are deleted from the Address 
                      Translation (AR) table."
        ::= { rcTblSize 28 }

rcTblArRsvpsAdded OBJECT-TYPE  
        SYNTAX        Integer32
        MAX-ACCESS        read-only  
        STATUS        current  
        DESCRIPTION   "Used to indicate the number of RSVP
                      entries that are added to the Address 
                      Translation (AR) table."
        ::= { rcTblSize 29 }

rcTblArRsvpsDeleted OBJECT-TYPE  
        SYNTAX        Integer32
        MAX-ACCESS        read-only  
        STATUS        current  
        DESCRIPTION   "Used to indicate the number of RSVP
                      entries that are deleted from the Address 
                      Translation (AR) table."
        ::= { rcTblSize 30 }


rcTblBrdgFdbSize OBJECT-TYPE  
        SYNTAX        Integer32
        MAX-ACCESS        read-only  
        STATUS        current  
        DESCRIPTION   "Used to indicate the number of entries in the 
                      dot1d forwarding database table."    
        ::= { rcTblSize 31 }

rcTblBrdgStaticSize OBJECT-TYPE  
        SYNTAX        Integer32
        MAX-ACCESS        read-only  
        STATUS        current  
        DESCRIPTION   "Used to indicate the number of entries in the 
                      dot1d Static Address Filtering table."    
        ::= { rcTblSize 32 }

rcTblIpAddrSize OBJECT-TYPE  
        SYNTAX        Integer32
        MAX-ACCESS        read-only  
        STATUS        current  
        DESCRIPTION   "Used to indicate the number of entries in the 
                      IP Address table."    
        ::= { rcTblSize 33 }

rcTblIpForwardingSize OBJECT-TYPE  
        SYNTAX        Integer32
        MAX-ACCESS        read-only   
        STATUS        current   
        DESCRIPTION   "Used to indicate the number of entries in the 
                      IP Forwarding table."        
        ::= { rcTblSize 34 }

rcTblIpNetToMediaSize OBJECT-TYPE  
        SYNTAX        Integer32
        MAX-ACCESS        read-only   
        STATUS        current   
        DESCRIPTION   "Used to indicate the number of entries in the 
                      IP Net-to-media table."        
        ::= { rcTblSize 35 }


-- IP Group

rcIpConf OBJECT IDENTIFIER ::= { rcIp 1 }

-- IP Configuration Table

rcIpConfTable OBJECT-TYPE
        SYNTAX        SEQUENCE OF RcIpConfEntry
        MAX-ACCESS        not-accessible
        STATUS        current
        DESCRIPTION   "A table used to maintain IP routing information 
                      for a particular interface."
        ::= { rcIpConf 1 }
 
rcIpConfEntry OBJECT-TYPE
        SYNTAX        RcIpConfEntry
        MAX-ACCESS        not-accessible
        STATUS        current
        DESCRIPTION   "Entry containing IP routing information.  An entry
                      is automatically created in this table when routing 
		      is enabled for an interface -or- when an ip address 
                      is configured on an interface."
        INDEX         { rcIpConfIfIndex }
        ::= { rcIpConfTable 1 }
 
RcIpConfEntry ::= SEQUENCE {
                rcIpConfIfIndex               InterfaceIndex,
                rcIpConfAdvertDefRte          TruthValue,
                rcIpConfAcceptDefRte          TruthValue,
		rcIpConfRowStatus             RowStatus,
                rcIpConfRipEnable             TruthValue,
                rcIpConfOspfEnable            TruthValue,
                rcIpConfIgmpEnable            TruthValue,
                rcIpConfAddrAssigned          TruthValue,
                rcIpConfDhcpEnable            TruthValue,
                rcIpConfTriggeredUpdateEnable TruthValue,
                rcIpConfRipAutoAggrerateEnable TruthValue,
                rcIpConfRipGenerateDefaultRoute TruthValue,
                rcIpConfAdvertiseWhenDown       TruthValue,
                rcIpConfDirectBroadcastEnable   TruthValue
        }

rcIpConfIfIndex OBJECT-TYPE
        SYNTAX        InterfaceIndex (0..4094)
        MAX-ACCESS        read-only
        STATUS        current
        DESCRIPTION   "An unique value to identify a physical interface 
 		      or a logical interface (VLAN)."
        ::= { rcIpConfEntry 1 }

rcIpConfAdvertDefRte OBJECT-TYPE
        SYNTAX        TruthValue
        MAX-ACCESS        read-write
        STATUS        current
        DESCRIPTION   "Used to indicate whether this interface should
		      advertize a RIP default route." 
        ::= { rcIpConfEntry 2 }

rcIpConfAcceptDefRte OBJECT-TYPE
        SYNTAX        TruthValue
        MAX-ACCESS        read-write
        STATUS        current
        DESCRIPTION   "Used to indicate whether this interface should
		      accept a RIP default route."
        ::= { rcIpConfEntry 3 }

rcIpConfRowStatus OBJECT-TYPE
        SYNTAX        RowStatus
        MAX-ACCESS        read-write
        STATUS        current
        DESCRIPTION   "Row status for this entry."
        ::= { rcIpConfEntry 4 }

rcIpConfRipEnable OBJECT-TYPE
        SYNTAX        TruthValue
        MAX-ACCESS        read-write
        STATUS        current
        DESCRIPTION   "Enable or disable RIP routing on the specified
                      interface."
        ::= { rcIpConfEntry 5 }
 
rcIpConfOspfEnable OBJECT-TYPE
        SYNTAX        TruthValue
        MAX-ACCESS        read-write
        STATUS        current
        DESCRIPTION   "Enable or disable OSPF routing on the specified
                      interface."
        ::= { rcIpConfEntry 6 }
 
rcIpConfIgmpEnable OBJECT-TYPE
        SYNTAX        TruthValue
        MAX-ACCESS        read-write
        STATUS        current
        DESCRIPTION   "Enable or disable IGMP on the specified
                      interface."
        ::= { rcIpConfEntry 7 }
 
rcIpConfAddrAssigned OBJECT-TYPE
        SYNTAX        TruthValue
        MAX-ACCESS        read-only
        STATUS        current
        DESCRIPTION   "Indicate whether IpAddress has been assigned 
                      for this interface."
        ::= { rcIpConfEntry 8 }

rcIpConfDhcpEnable OBJECT-TYPE
        SYNTAX        TruthValue
        MAX-ACCESS        read-write
        STATUS        current
        DESCRIPTION   "Enable or disable DHCP on the specified
                      interface."
        ::= { rcIpConfEntry 9 }

rcIpConfTriggeredUpdateEnable OBJECT-TYPE
        SYNTAX        TruthValue
        MAX-ACCESS        read-write
        STATUS        current
        DESCRIPTION   "Used to indicate whether the RIP triggered update
		      feature should be enabled on this interface." 
        ::= { rcIpConfEntry 10 }
 
rcIpConfRipAutoAggrerateEnable OBJECT-TYPE
        SYNTAX        TruthValue
        MAX-ACCESS        read-write
        STATUS        current
        DESCRIPTION   "Used to indicate whether the auto aggregation 
		      feature should be enabled on this interface." 
        ::= { rcIpConfEntry 11 }
 
rcIpConfRipGenerateDefaultRoute OBJECT-TYPE
        SYNTAX        TruthValue
        MAX-ACCESS        read-write
        STATUS        current
        DESCRIPTION   "Used to indicate whether to generate a default
		      RIP route	on this interface." 
        ::= { rcIpConfEntry 12 }

rcIpConfAdvertiseWhenDown OBJECT-TYPE
        SYNTAX        TruthValue
        MAX-ACCESS        read-write
        STATUS        current
        DESCRIPTION   "The value is used indicated whether vlan state change
                       should be notified to layer 3 or not, provided the vlan
                       is configured as routable interface. Also used for
                       single routable ports, in that case the criteria for
                       state is PortOperStatus.
                       Vlan is considered as UP if atleast one member of the
                       port based vlan has link up, or atleast one port member
                       of the policy based has an entry in the MGID or atleast
                       one static member of the policy based vlan has link up.
                       Otherwise, vlan is considered as DOWN.
                       If the value is 'true' then the interface state change 
                       will not be notified to layer 3. (i.e., it always stays 
                       up). If the value is 'false' then the vlan state change 
                       will be notified to layer 3 so that IP related status 
                       reflects routable interface state."
        DEFVAL        { false }
        ::= { rcIpConfEntry 13 }
 
rcIpConfDirectBroadcastEnable OBJECT-TYPE
        SYNTAX        TruthValue
        MAX-ACCESS        read-write
        STATUS        current
        DESCRIPTION   "Used to indicate whether this interface should
                      forward direct broadcast traffic"
        DEFVAL        { true }
        ::= { rcIpConfEntry 14 }
 

-- Ospf Configuration Table
 
rcIpConfOspfTable OBJECT-TYPE
        SYNTAX        SEQUENCE OF RcIpConfOspfEntry
        MAX-ACCESS        not-accessible
        STATUS        current
        DESCRIPTION   "A table used to maintain OSPF information
                      for a particular interface."
        ::= { rcIpConf 2 }
 
rcIpConfOspfEntry OBJECT-TYPE
        SYNTAX        RcIpConfOspfEntry
        MAX-ACCESS        not-accessible
        STATUS        current
        DESCRIPTION   "Entry containing OSPF information.  An entry is
                      automatically created in this table when routing 
		      is enabled for an interface -or- when an ip address 
                      is configured on an interface." 
        INDEX         { rcIpConfOspfIfIndex }
        ::= { rcIpConfOspfTable 1 }
 
RcIpConfOspfEntry ::= SEQUENCE {
                rcIpConfOspfIfIndex           InterfaceIndex,
                rcIpConfOspfRtrPriority       INTEGER,
                rcIpConfOspfMetric            INTEGER,
                rcIpConfOspfAuthKey           DisplayString,
                rcIpConfOspfRowStatus         RowStatus,
                rcIpConfOspfHelloInterval     INTEGER,
                rcIpConfOspfRtrDeadInterval   INTEGER,
                rcIpConfOspfIfAreaId          IpAddress,
                rcIpConfOspfAuthType          INTEGER
        }
 
rcIpConfOspfIfIndex OBJECT-TYPE
        SYNTAX        InterfaceIndex (0..4094)
        MAX-ACCESS        read-only
        STATUS        current
        DESCRIPTION   "An unique value to identify a physical interface 
 		      or a logical interface (VLAN)."
        ::= { rcIpConfOspfEntry 1 }

rcIpConfOspfRtrPriority OBJECT-TYPE
        SYNTAX        INTEGER (0..'FF'h)
        MAX-ACCESS        read-write
        STATUS        current
        DESCRIPTION   "The priority of this interface.  Used in multi-
                      access networks, this field is used in the
                      designated router election algorithm.  The value 0
                      signifies that the router is not eligible to become
                      the designated router on this particular network.
                      In the event of a tie in this value, routers will
                      use their router id as a tie breaker."
        DEFVAL        { 1 }
        ::= { rcIpConfOspfEntry 2 }
 
rcIpConfOspfMetric OBJECT-TYPE
        SYNTAX        INTEGER (0..'FFFF'h)
        MAX-ACCESS        read-write
        STATUS        current
        DESCRIPTION   "The metric for this type of service (TOS) on this
                      interface.  The default value of the TOS 0 Metric
                      is (10^9 / ifSpeed). The value FFFF means 'no route 
		      via this TOS'. A value of 0 means the interface speed 
                      (rcIpConfOspfDefaultMetric) will be used as metric 
		      value, when the state of the interface is up." 
        DEFVAL        { 0 }
        ::= { rcIpConfOspfEntry 3 }
 
rcIpConfOspfAuthKey OBJECT-TYPE
        SYNTAX        DisplayString (SIZE(8))
        MAX-ACCESS        read-write
        STATUS        current
        DESCRIPTION   "The Authentication Key.  If the Area's
                      Authorization Type is simplePassword, and the key
                      length is shorter than 8 octets, the agent will
                      left adjust and zero fill to 8 octets.  When read,
                      ospfIfAuthKey always returns an Octet String of
                      length zero."
        REFERENCE     "OSPF Version 2, Section 9 The Interface Data
                      Structure"
        ::= { rcIpConfOspfEntry 4 }

rcIpConfOspfRowStatus OBJECT-TYPE
        SYNTAX        RowStatus
        MAX-ACCESS        read-write
        STATUS        current
        DESCRIPTION   "Row status for this entry."
        ::= { rcIpConfOspfEntry 5 }

rcIpConfOspfHelloInterval OBJECT-TYPE
        SYNTAX        INTEGER (1..'FFFF'h)
        MAX-ACCESS        read-write
        STATUS        current
        DESCRIPTION   "The length of time, in seconds, between the 
                      Hello packets that the router sends on the 
                      interface. This value must be the same for all
                      routers attached to a common network."
        DEFVAL        { 10 }
        ::= { rcIpConfOspfEntry 6 }

rcIpConfOspfRtrDeadInterval OBJECT-TYPE
        SYNTAX        INTEGER (1..'7FFFFFFF'h)
        MAX-ACCESS        read-write
        STATUS        current
        DESCRIPTION   "The number of seconds that a router's Hello 
                      packets have not been seen before it's 
                      neighbors declare the router down. This should
                      be some multiple of the Hello interval. This 
                      value must be the same for all routers attached
                      to a common network."
        DEFVAL        { 40 }
        ::= { rcIpConfOspfEntry 7 }

rcIpConfOspfIfAreaId OBJECT-TYPE
         SYNTAX        IpAddress
         MAX-ACCESS        read-write
         STATUS        current
         DESCRIPTION   "A 32-bit integer uniquely identifying the area to
                       which the interface connects.  Area ID 0.0.0.0 is used
                       for the OSPF backbone."
         DEFVAL   { '00000000'H }    -- 0.0.0.0
         ::= { rcIpConfOspfEntry 8 }

rcIpConfOspfAuthType OBJECT-TYPE
         SYNTAX        INTEGER {
                           none (0),
                           simplePassword (1),
                           md5 (2)
                           
                       }
        MAX-ACCESS         read-write
        STATUS         current
        DESCRIPTION    "The authentication type specified for  an  interface.   
                       Additional  authentication types may be assigned locally."
        REFERENCE      "OSPF Version 2, Appendix E Authentication"
        DEFVAL { 0 }        -- no authentication, by default
        ::= { rcIpConfOspfEntry 9 }

 
-- Ospf Cost Grp

rcIpConfOspfDefaultMetric   OBJECT IDENTIFIER       ::= { rcIpConf 3 }
 
rcIpConfOspfDefaultMetric10MegPort OBJECT-TYPE
        SYNTAX        INTEGER (1..'FFFF'h)
        MAX-ACCESS        read-write
        STATUS        current
        DESCRIPTION   "Used to indicate the cost associated with
                      10Meg Interface(Port)."
        ::= { rcIpConfOspfDefaultMetric 1 }
 
rcIpConfOspfDefaultMetric100MegPort OBJECT-TYPE
        SYNTAX        INTEGER (1..'FFFF'h)
        MAX-ACCESS        read-write
        STATUS        current
        DESCRIPTION   "Used to indicate the cost associated with
                      100Meg Interface(Port)."
        ::= { rcIpConfOspfDefaultMetric 2 }
 
rcIpConfOspfDefaultMetric1000MegPort OBJECT-TYPE
        SYNTAX        INTEGER (1..'FFFF'h)
        MAX-ACCESS        read-write
        STATUS        current
        DESCRIPTION   "Used to indicate the cost associated with
                      1000Meg Interface(Port)."
        ::= { rcIpConfOspfDefaultMetric 3 }

rcIpConfOspf   OBJECT IDENTIFIER       ::= { rcIpConf 4 }

 
rcIpConfOspfTrapEnable  OBJECT-TYPE
        SYNTAX        TruthValue
        MAX-ACCESS        read-write
        STATUS        current
        DESCRIPTION   "Used to indicate whether Ospf Traps should be sent."
        ::= { rcIpConfOspf 1 }

rcIpConfOspfAutoVirtLinkEnable  OBJECT-TYPE
        SYNTAX        TruthValue
        MAX-ACCESS        read-write
        STATUS        current
        DESCRIPTION   "Used to indicate whether auto virtual link 
                      creation is enabled or not. If set to true
                      OSPF will create virtual links between 
                      ABRs whether it is needed or not, but adjacency
                      will established only when one of the ABR 
                      losses connection to backbone area. If set to
                      false then it is user resposibity to create
                      virtual link whenever needed."
	DEFVAL	      { false }
        ::= { rcIpConfOspf 2 }

rcIpConfOspfSpfHoldDownTime OBJECT-TYPE
         SYNTAX   INTEGER (3..60)
         MAX-ACCESS   read-write
         STATUS   current
         DESCRIPTION   "The SPF Hold Down Timer value. The SPF will run
                        at most once per hold down timer value."
         DEFVAL  { 10 }
         ::= { rcIpConfOspf 3 }


rcIpConfGlobal   OBJECT IDENTIFIER       ::= { rcIpConf 6 }

rcIpConfGlobalRipHoldDownTime OBJECT-TYPE
        SYNTAX	      INTEGER (0..360)
        MAX-ACCESS        read-write
        STATUS        current
        DESCRIPTION   "Used to set the system-wide RIP hold down time
		      in seconds."
        DEFVAL        { 180 }
        ::= { rcIpConfGlobal 1 }


-- Ospf Area Table
 
rcIpConfOspfAreaTable OBJECT-TYPE
        SYNTAX        SEQUENCE OF RcIpConfOspfAreaEntry
        MAX-ACCESS        not-accessible
        STATUS        current
        DESCRIPTION   "A table used to maintain OSPF information
                      for a particular Area."
        ::= { rcIpConf 7 }
 
rcIpConfOspfAreaEntry OBJECT-TYPE
        SYNTAX        RcIpConfOspfAreaEntry
        MAX-ACCESS        not-accessible
        STATUS        current
        DESCRIPTION   "Entry containing OSPF Area configuration 
                      information.  An entry is automatically created 
                      in this table when an area is configured through 
                      ospfAreaTable in (rfc1253rcc.mib)."
        INDEX         { rcIpConfOspfAreaId }
        ::= { rcIpConfOspfAreaTable 1 }
 
RcIpConfOspfAreaEntry ::= SEQUENCE {
                rcIpConfOspfAreaId              IpAddress,
                rcIpConfOspfAreaImportSummary   TruthValue,
                rcIpConfOspfAreaActiveIfCount   INTEGER
        }
 
rcIpConfOspfAreaId OBJECT-TYPE
        SYNTAX        IpAddress
        MAX-ACCESS        read-only
        STATUS        current
        DESCRIPTION   "An unique value to identify an area. Area ID
 		      0.0.0.0 is used for the OSPF backbone."
        ::= { rcIpConfOspfAreaEntry 1 }

rcIpConfOspfAreaImportSummary OBJECT-TYPE
        SYNTAX        TruthValue
        MAX-ACCESS        read-write
        STATUS        current
        DESCRIPTION   "The area's support for importing Summary 
                      advertisements into a stub area. This field
                      should be used only if ospfImportASExtern is
                      set to FALSE"
        DEFVAL        { true }
        ::= { rcIpConfOspfAreaEntry 2 }
 
rcIpConfOspfAreaActiveIfCount OBJECT-TYPE
        SYNTAX        Integer32
        MAX-ACCESS        read-only
        STATUS        current
        DESCRIPTION   "This variable displays the number of active
                      interfaces configured in this area. An area
                      cannot be deleted if this value is > 0."
        ::= { rcIpConfOspfAreaEntry 3 }
 
-- IP Configuration IP Interface Table

rcIpConfV2Table OBJECT-TYPE
        SYNTAX        SEQUENCE OF RcIpConfV2Entry
        MAX-ACCESS        not-accessible
        STATUS        current
        DESCRIPTION   "A table used to maintain IP routing information 
                      for a particular interface."
        ::= { rcIpConf 8 }
 
rcIpConfV2Entry OBJECT-TYPE
        SYNTAX        RcIpConfV2Entry
        MAX-ACCESS        not-accessible
        STATUS        current
        DESCRIPTION   "Entry containing IP routing information.  An entry
                      is automatically created in this table when routing 
		      is enabled for an interface -or- when an ip address 
                      is configured on an interface."
        INDEX         { rcIpConfV2Index, rcIpConfV2Addr }
        ::= { rcIpConfV2Table 1 }
 
RcIpConfV2Entry ::= SEQUENCE {
                rcIpConfV2Index               InterfaceIndex,
                rcIpConfV2Addr                  IpAddress,
		rcIpConfV2RowStatus             RowStatus,
                rcIpConfV2AdvertDefRte          TruthValue,
                rcIpConfV2AcceptDefRte          TruthValue,
                rcIpConfV2RipEnable             TruthValue,
                rcIpConfV2OspfEnable            TruthValue,
                rcIpConfV2IgmpEnable            TruthValue,
                rcIpConfV2AddrAssigned          TruthValue,
                rcIpConfV2TriggeredUpdateEnable TruthValue,
                rcIpConfV2RipAutoAggrerateEnable TruthValue,
                rcIpConfV2RipGenerateDefaultRoute TruthValue,
                rcIpConfV2AdvertiseWhenDown       TruthValue
        }

rcIpConfV2Index OBJECT-TYPE
        SYNTAX        InterfaceIndex (0..4094)
        MAX-ACCESS        read-only
        STATUS        current
        DESCRIPTION   "An unique value to identify a physical interface 
 		      or a logical interface (VLAN)."
        ::= { rcIpConfV2Entry 1 }

rcIpConfV2Addr OBJECT-TYPE
        SYNTAX        IpAddress
        MAX-ACCESS        read-only
        STATUS        current
        DESCRIPTION   "Ip interface address." 
        ::= { rcIpConfV2Entry 2 }

rcIpConfV2RowStatus OBJECT-TYPE
        SYNTAX        RowStatus
        MAX-ACCESS        read-write
        STATUS        current
        DESCRIPTION   "Row status for this entry."
        ::= { rcIpConfV2Entry 3 }

rcIpConfV2AdvertDefRte OBJECT-TYPE
        SYNTAX        TruthValue
        MAX-ACCESS        read-write
        STATUS        current
        DESCRIPTION   "Used to indicate whether this interface should
		      advertize a RIP default route." 
        ::= { rcIpConfV2Entry 4 }

rcIpConfV2AcceptDefRte OBJECT-TYPE
        SYNTAX        TruthValue
        MAX-ACCESS        read-write
        STATUS        current
        DESCRIPTION   "Used to indicate whether this interface should
		      accept a RIP default route."
        ::= { rcIpConfV2Entry 5 }

rcIpConfV2RipEnable OBJECT-TYPE
        SYNTAX        TruthValue
        MAX-ACCESS        read-write
        STATUS        current
        DESCRIPTION   "Enable or disable RIP routing on the specified
                      interface."
        ::= { rcIpConfV2Entry 6 }
 
rcIpConfV2OspfEnable OBJECT-TYPE
        SYNTAX        TruthValue
        MAX-ACCESS        read-write
        STATUS        current
        DESCRIPTION   "Enable or disable OSPF routing on the specified
                      interface."
        ::= { rcIpConfV2Entry 7 }
 
rcIpConfV2IgmpEnable OBJECT-TYPE
        SYNTAX        TruthValue
        MAX-ACCESS        read-write
        STATUS        current
        DESCRIPTION   "Enable or disable IGMP on the specified
                      interface."
        ::= { rcIpConfV2Entry 8 }
 
rcIpConfV2AddrAssigned OBJECT-TYPE
        SYNTAX        TruthValue
        MAX-ACCESS        read-only
        STATUS        current
        DESCRIPTION   "Indicate whether IpAddress has been assigned 
                      for this interface."
        ::= { rcIpConfV2Entry 9 }

rcIpConfV2TriggeredUpdateEnable OBJECT-TYPE
        SYNTAX        TruthValue
        MAX-ACCESS        read-write
        STATUS        current
        DESCRIPTION   "Used to indicate whether the RIP triggered update
		      feature should be enabled on this interface." 
        ::= { rcIpConfV2Entry 10 }
 
rcIpConfV2RipAutoAggrerateEnable OBJECT-TYPE
        SYNTAX        TruthValue
        MAX-ACCESS        read-write
        STATUS        current
        DESCRIPTION   "Used to indicate whether the auto aggregation 
		      feature should be enabled on this interface." 
        ::= { rcIpConfV2Entry 11 }
 
rcIpConfV2RipGenerateDefaultRoute OBJECT-TYPE
        SYNTAX        TruthValue
        MAX-ACCESS        read-write
        STATUS        current
        DESCRIPTION   "Used to indicate whether to generate a default
		      RIP route	on this interface." 
        ::= { rcIpConfV2Entry 12 }

rcIpConfV2AdvertiseWhenDown OBJECT-TYPE
        SYNTAX        TruthValue
        MAX-ACCESS        read-write
        STATUS        current
        DESCRIPTION   "The value is used indicated whether vlan state change
                       should be notified to layer 3 or not, provided the vlan
                       is configured as routable interface. Also used for
                       single routable ports, in that case the criteria for
                       state is PortOperStatus.
                       Vlan is considered as UP if atleast one member of the
                       port based vlan has link up, or atleast one port member
                       of the policy based has an entry in the MGID or atleast
                       one static member of the policy based vlan has link up.
                       Otherwise, vlan is considered as DOWN.
                       If the value is 'true' then the interface state change 
                       will not be notified to layer 3. (i.e., it always stays 
                       up). If the value is 'false' then the vlan state change 
                       will be notified to layer 3 so that IP related status 
                       reflects routable interface state."
        DEFVAL        { false }
        ::= { rcIpConfV2Entry 13 }
 
-- Ospf Configuration Ip Interface Table
 
rcIpConfOspfV2Table OBJECT-TYPE
        SYNTAX        SEQUENCE OF RcIpConfOspfV2Entry
        MAX-ACCESS        not-accessible
        STATUS        current
        DESCRIPTION   "A table used to maintain OSPF information
                      for a particular interface."
        ::= { rcIpConf 9 }
 
rcIpConfOspfV2Entry OBJECT-TYPE
        SYNTAX        RcIpConfOspfV2Entry
        MAX-ACCESS        not-accessible
        STATUS        current
        DESCRIPTION   "Entry containing OSPF information.  An entry is
                      automatically created in this table when routing 
		      is enabled for an interface -or- when an ip address 
                      is configured on an interface." 
        INDEX         { rcIpConfOspfV2IfIndex, rcIpConfOspfV2IpAddr }
        ::= { rcIpConfOspfV2Table 1 }
 
RcIpConfOspfV2Entry ::= SEQUENCE {
                rcIpConfOspfV2IfIndex           InterfaceIndex,
                rcIpConfOspfV2IpAddr            IpAddress,
                rcIpConfOspfV2RtrPriority       INTEGER,
                rcIpConfOspfV2Metric            INTEGER,
                rcIpConfOspfV2AuthKey           DisplayString,
                rcIpConfOspfV2RowStatus         RowStatus,
                rcIpConfOspfV2HelloInterval     INTEGER,
                rcIpConfOspfV2RtrDeadInterval   INTEGER,
                rcIpConfOspfV2IfAreaId          IpAddress,
                rcIpConfOspfV2AuthType          INTEGER
        }
 
rcIpConfOspfV2IfIndex OBJECT-TYPE
        SYNTAX        InterfaceIndex (0..4094)
        MAX-ACCESS        read-only
        STATUS        current
        DESCRIPTION   "An unique value to identify a physical interface 
 		      or a logical interface (VLAN)."
        ::= { rcIpConfOspfV2Entry 1 }

rcIpConfOspfV2IpAddr OBJECT-TYPE
        SYNTAX        IpAddress
        MAX-ACCESS        read-only
        STATUS        current
        DESCRIPTION   "IpAddress of the IP interface."
        ::= { rcIpConfOspfV2Entry 2 }

rcIpConfOspfV2RtrPriority OBJECT-TYPE
        SYNTAX        INTEGER (0..'FF'h)
        MAX-ACCESS        read-write
        STATUS        current
        DESCRIPTION   "The priority of this interface.  Used in multi-
                      access networks, this field is used in the
                      designated router election algorithm.  The value 0
                      signifies that the router is not eligible to become
                      the designated router on this particular network.
                      In the event of a tie in this value, routers will
                      use their router id as a tie breaker."
        DEFVAL        { 1 }
        ::= { rcIpConfOspfV2Entry 3 }
 
rcIpConfOspfV2Metric OBJECT-TYPE
        SYNTAX        INTEGER (0..'FFFF'h)
        MAX-ACCESS        read-write
        STATUS        current
        DESCRIPTION   "The metric for this type of service (TOS) on this
                      interface.  The default value of the TOS 0 Metric
                      is (10^9 / ifSpeed). The value FFFF means 'no route 
		      via this TOS'. A value of 0 means the interface speed 
                      (rcIpConfOspfV2DefaultMetric) will be used as metric 
		      value, when the state of the interface is up." 
        DEFVAL        { 0 }
        ::= { rcIpConfOspfV2Entry 4 }
 
rcIpConfOspfV2AuthKey OBJECT-TYPE
        SYNTAX        DisplayString (SIZE(8))
        MAX-ACCESS        read-write
        STATUS        current
        DESCRIPTION   "The Authentication Key.  If the Area's
                      Authorization Type is simplePassword, and the key
                      length is shorter than 8 octets, the agent will
                      left adjust and zero fill to 8 octets.  When read,
                      ospfIfAuthKey always returns an Octet String of
                      length zero."
        REFERENCE     "OSPF Version 2, Section 9 The Interface Data
                      Structure"
        ::= { rcIpConfOspfV2Entry 5 }

rcIpConfOspfV2RowStatus OBJECT-TYPE
        SYNTAX        RowStatus
        MAX-ACCESS        read-write
        STATUS        current
        DESCRIPTION   "Row status for this entry."
        ::= { rcIpConfOspfV2Entry 6 }

rcIpConfOspfV2HelloInterval OBJECT-TYPE
        SYNTAX        INTEGER (1..'FFFF'h)
        MAX-ACCESS        read-write
        STATUS        current
        DESCRIPTION   "The length of time, in seconds, between the 
                      Hello packets that the router sends on the 
                      interface. This value must be the same for all
                      routers attached to a common network."
        DEFVAL        { 10 }
        ::= { rcIpConfOspfV2Entry 7 }

rcIpConfOspfV2RtrDeadInterval OBJECT-TYPE
        SYNTAX        INTEGER (1..'7FFFFFFF'h)
        MAX-ACCESS        read-write
        STATUS        current
        DESCRIPTION   "The number of seconds that a router's Hello 
                      packets have not been seen before it's 
                      neighbors declare the router down. This should
                      be some multiple of the Hello interval. This 
                      value must be the same for all routers attached
                      to a common network."
        DEFVAL        { 40 }
        ::= { rcIpConfOspfV2Entry 8 }

rcIpConfOspfV2IfAreaId OBJECT-TYPE
         SYNTAX        IpAddress
         MAX-ACCESS        read-write
         STATUS        current
         DESCRIPTION   "A 32-bit integer uniquely identifying the area to
                       which the interface connects.  Area ID 0.0.0.0 is used
                       for the OSPF backbone."
         DEFVAL   { '00000000'H }    -- 0.0.0.0
         ::= { rcIpConfOspfV2Entry 9 }

rcIpConfOspfV2AuthType OBJECT-TYPE
         SYNTAX        INTEGER {
                           none (0),
                           simplePassword (1),
                           md5 (2)
                           
                       }
        MAX-ACCESS         read-write
        STATUS         current
        DESCRIPTION    "The authentication type specified for  an  interface.   
                       Additional  authentication types may be assigned locally."
        REFERENCE      "OSPF Version 2, Appendix E Authentication"
        DEFVAL { 0 }        -- no authentication, by default
        ::= { rcIpConfOspfV2Entry 10 }

-- IP Address Table

rcIpAddrTable OBJECT-TYPE
        SYNTAX        SEQUENCE OF RcIpAddrEntry
        MAX-ACCESS        not-accessible
        STATUS        current
        DESCRIPTION   "The table of addressing information relevant to
                      this entity's IP addresses.

                      This table is identical to the ipAddrTable in 
                      MIB2 except the columns rcIpAdEntIfIndex and 
                      rcIpAdEntAddr are reversed.  Also, the table 
                      is indexed by both these variables."
	::= { rcIp 2 }

rcIpAddrEntry OBJECT-TYPE
	SYNTAX        RcIpAddrEntry
	MAX-ACCESS 	      not-accessible
	STATUS 	      current
	DESCRIPTION   "The addressing information for one of this
                      entity's IP addresses."
	INDEX         { rcIpAdEntIfIndex, rcIpAdEntAddr }
	::= { rcIpAddrTable 1 }

RcIpAddrEntry ::=
    	SEQUENCE {
        	rcIpAdEntIfIndex InterfaceIndex,
	        rcIpAdEntAddr IpAddress,
	        rcIpAdEntNetMask IpAddress,
	        rcIpAdEntBcastAddrFormat INTEGER,
	        rcIpAdEntReasmMaxSize INTEGER (0..65535),
                rcIpAdEntRowStatus RowStatus,
                rcIpAdEntVlanId INTEGER (1..4094), 
                rcIpAdEntBrouterPort TruthValue,
                rcIpAdEntMacOffset INTEGER,
                rcIpAdEntIfType INTEGER
    	}

rcIpAdEntIfIndex OBJECT-TYPE
   	SYNTAX        InterfaceIndex
  	MAX-ACCESS        read-only
  	STATUS        current
	DESCRIPTION   "The index value which uniquely identifies the
                      interface to which this entry is applicable.  The
                      interface identified by a particular value of this
                      index is the same interface as identified by the
                      same value of ifIndex."
	::= { rcIpAddrEntry 1 }

rcIpAdEntAddr OBJECT-TYPE
	SYNTAX        IpAddress
        MAX-ACCESS        read-only
        STATUS        current
        DESCRIPTION   "The IP address to which this entry's addressing
                      information pertains."
	::= { rcIpAddrEntry 2 }

rcIpAdEntNetMask OBJECT-TYPE
        SYNTAX        IpAddress
        MAX-ACCESS        read-write
        STATUS        current
        DESCRIPTION   "The subnet mask associated with the IP address of
                      this entry.  The value of the mask is an IP
                      address with all the network bits set to 1 and all
                      the hosts bits set to 0."
	::= { rcIpAddrEntry 3 }

rcIpAdEntBcastAddrFormat OBJECT-TYPE
        SYNTAX        INTEGER {
			 zeros(0),	-- use zeros
			 ones(1)	-- use ones
		      }
        MAX-ACCESS        read-only
        STATUS        current
        DESCRIPTION   "The IP broadcast address format used on this 
                      interface."
	::= { rcIpAddrEntry 4 }

rcIpAdEntReasmMaxSize OBJECT-TYPE
        SYNTAX        INTEGER (0..65535)
        MAX-ACCESS        read-only
        STATUS        current
        DESCRIPTION   "The size of the largest IP datagram which this
                      entity can re-assemble from incoming IP fragmented
                      datagrams received on this interface."
        ::= { rcIpAddrEntry 5 }

rcIpAdEntRowStatus OBJECT-TYPE
        SYNTAX        RowStatus
        MAX-ACCESS        read-write
        STATUS        current
        DESCRIPTION   "Used to create/delete entries"
        ::= { rcIpAddrEntry 6 }

rcIpAdEntVlanId OBJECT-TYPE
        SYNTAX        INTEGER (1..4094)
        MAX-ACCESS        read-write
        STATUS        current
        DESCRIPTION   "A value that uniquely identifies the Virtual LAN
                      associated with this entry. This value corresponds
                      to the lower 12 bits in the IEEE 802.1Q VLAN Tag."
        ::= { rcIpAddrEntry 7 }

rcIpAdEntBrouterPort OBJECT-TYPE
        SYNTAX        TruthValue
        MAX-ACCESS        read-only
        STATUS        current
        DESCRIPTION   "Used to indicate whether this entry correponds
		      to a brouter port (as oppose to a routable VLAN).
 		      This value cannot be changed after the row is
		      created."
        ::= { rcIpAddrEntry 8 }

rcIpAdEntMacOffset OBJECT-TYPE
        SYNTAX        INTEGER (0..511)
        MAX-ACCESS    read-write
        STATUS        current
        DESCRIPTION   "Used to translate the ip address into mac address.
                       The system has 512 mac addresses of which 0-507 are
                       reserved for
                       Boardwalk box. 508-511 is reserved for MG. One can either

                       mention a mac offset while configuring an ip on the
                       vlan or it can be alloted by the system within the above
                       range."
        ::= { rcIpAddrEntry 9 }

rcIpAdEntIfType   OBJECT-TYPE
     SYNTAX INTEGER {
                circuitLessIP(1),
                brouterPort(2),
                vlan(3)
            }
     MAX-ACCESS     read-only
     STATUS         current
     DESCRIPTION    "The address entry IfType indicates the type of the
                     interface. In the case of circuit-less-IP there is
                     no association with any ports. In other words, it can
                     be thought of as a virtual interface. The value
                     'brouter port' indicates this interface is associated
                     with a specific physical port. The value 'vlan'
                     indicates a logical port that contains one or physical
                     ports/MLT ports."
        ::= { rcIpAddrEntry 10 }


-- FlowContorl Group

rcIpFlowTable OBJECT-TYPE
        SYNTAX        SEQUENCE OF RcIpFlowEntry
        MAX-ACCESS        not-accessible
        STATUS        current
        DESCRIPTION   "IpFlow Table.  This table contain entries that
		      correspond to RSVP records in the switching
		      fabric Address Resolution table.

		      A connection that has a matching entry in this 
                      table will be processed with a higher priority 
                      than connections that do not have an entry."
        ::= { rcIp 3 }

rcIpFlowEntry OBJECT-TYPE
        SYNTAX        RcIpFlowEntry
        MAX-ACCESS        not-accessible
        STATUS        current
        DESCRIPTION   "Proprietary flow control variables."
        INDEX         { rcIpFlowSrcIpAddress, rcIpFlowSrcIpPort,
		        rcIpFlowDstIpAddress, rcIpFlowDstIpPort,
		        rcIpFlowProtocol }
        ::= { rcIpFlowTable 1 }

RcIpFlowEntry ::=
        SEQUENCE {
                rcIpFlowSrcIpAddress IpAddress,
                rcIpFlowSrcIpPort    INTEGER,
                rcIpFlowDstIpAddress IpAddress,
                rcIpFlowDstIpPort    INTEGER,
		rcIpFlowProtocol     INTEGER,
		rcIpFlowRowStatus    RowStatus
        }

rcIpFlowSrcIpAddress OBJECT-TYPE
        SYNTAX        IpAddress
        MAX-ACCESS        read-only
        STATUS        current
        DESCRIPTION   "The source IP address of an IP packet."
        ::= { rcIpFlowEntry 1 }

rcIpFlowSrcIpPort OBJECT-TYPE
        SYNTAX        INTEGER (0..65535)
        MAX-ACCESS        read-only
        STATUS        current
        DESCRIPTION   "The source port of an IP packet.  A zero value 
                      in this field is used as a wildcard value."
        DEFVAL 	      { 0 }
        ::= { rcIpFlowEntry 2 }

rcIpFlowDstIpAddress OBJECT-TYPE
        SYNTAX        IpAddress
        MAX-ACCESS        read-only
        STATUS        current
        DESCRIPTION   "The destination IP address of an IP packet."
        ::= { rcIpFlowEntry 3 }

rcIpFlowDstIpPort OBJECT-TYPE
        SYNTAX        INTEGER (0..65535)
        MAX-ACCESS        read-only
        STATUS        current
        DESCRIPTION   "The destination port of an IP packet.  A zero
                      value in this field is used as a wildcard value."
	DEFVAL	      { 0 }
        ::= { rcIpFlowEntry 4 }

rcIpFlowProtocol OBJECT-TYPE
        SYNTAX 	      INTEGER {
                         ip(4),	        -- ip
			 tcp(6),	-- tcp
			 udp(17)	-- udp
        	      }
        MAX-ACCESS        read-only
        STATUS        current
        DESCRIPTION   "The protocol type of an IP packet.  A zero value
                      in this field is used as a wildcard value."
	DEFVAL 	      { ip }
        ::= { rcIpFlowEntry 5 }

rcIpFlowRowStatus OBJECT-TYPE
        SYNTAX        RowStatus
        MAX-ACCESS        read-write
        STATUS        current
        DESCRIPTION   "Status of entry."
        ::= { rcIpFlowEntry 6 }


-- Routing group

rcIpRouting OBJECT IDENTIFIER ::= { rcIp 4 }


-- rcIpRouting/rcIpRoutingRedistributeRipToOspf Group

rcIpRoutingRedistributeRipToOspf OBJECT IDENTIFIER ::= {rcIpRouting 1}

rcIpRoutingRedistributeRipToOspfEnable OBJECT-TYPE
        SYNTAX        TruthValue
        MAX-ACCESS        read-write
        STATUS        obsolete
        DESCRIPTION   "Used to indicate whether or not to Redistribute
                      RIP routes to OSPF."
        DEFVAL        { false }
        ::= { rcIpRoutingRedistributeRipToOspf 1 }
 
rcIpRoutingRedistributeRipToOspfExplicitMetric OBJECT-TYPE
        SYNTAX        INTEGER (1..'FFFF'h)
        MAX-ACCESS        read-write
        STATUS        obsolete
        DESCRIPTION   "Value of metric that is used to translate the
                      RIP route to OSPF."
        DEFVAL        { 1 }
        ::= { rcIpRoutingRedistributeRipToOspf 2 }

rcIpRoutingRedistributeRipToOspfUseExplicitMetric OBJECT-TYPE
        SYNTAX        TruthValue
        MAX-ACCESS        read-write
        STATUS        obsolete
        DESCRIPTION   "Used to indicate whether or not to use the user
                      specified default metric for redistributing
                      RIP routes to OSPF."
        DEFVAL        { false }
        ::= { rcIpRoutingRedistributeRipToOspf 3 }
 
rcIpRoutingRedistributeRipToOspfExternalMetricType  OBJECT-TYPE
        SYNTAX        INTEGER {
                         type1(1),          -- extenal metric type1
                         type2(2)           -- extenal metric type2
                      }
        MAX-ACCESS        read-write
        STATUS        obsolete
        DESCRIPTION   "Used to configure the metric type of the
                      distributed routes to OSPF domain.
                      type1 means the metric is comparable directly
                      to the link state metric 
                      (cost = internal cost + external cost). 
                      type2 means the metric is considered larger 
                      than any link state metric (cost = external 
                      cost)."
        DEFVAL        { type2 }
        ::= { rcIpRoutingRedistributeRipToOspf 4 }


-- rcIpRouting/rcIpRoutingRedistributeOspfToRip Group

rcIpRoutingRedistributeOspfToRip OBJECT IDENTIFIER ::= {rcIpRouting 2}

rcIpRoutingRedistributeOspfToRipEnable OBJECT-TYPE
        SYNTAX        TruthValue
        MAX-ACCESS        read-write
        STATUS        obsolete
        DESCRIPTION   "Used to indicate whether or not to redistribute 
                      OSPF routes to RIP."
        DEFVAL        { false }
        ::= { rcIpRoutingRedistributeOspfToRip 1 }

rcIpRoutingRedistributeOspfToRipExplicitMetric OBJECT-TYPE
        SYNTAX        INTEGER (1..16)
        MAX-ACCESS        read-write
        STATUS        obsolete
        DESCRIPTION   "Value of metric that is used to translate the
                      OSPF route to RIP."
        DEFVAL        { 1 }
        ::= { rcIpRoutingRedistributeOspfToRip 2 }
 
rcIpRoutingRedistributeOspfToRipUseExplicitMetric OBJECT-TYPE
        SYNTAX        TruthValue
        MAX-ACCESS        read-write
        STATUS        obsolete
        DESCRIPTION   "Used to indicate whether or not to use the user
                      specified default metric for redistributing
                      OSPF routes to RIP."
        DEFVAL        { true }
        ::= { rcIpRoutingRedistributeOspfToRip 3 }

-- rcIpRouting/rcIpRoutingRedistributeDirectToOspf Group

rcIpRoutingRedistributeDirectToOspf OBJECT IDENTIFIER ::= {rcIpRouting 3}

rcIpRoutingRedistributeDirectToOspfEnable  OBJECT-TYPE
        SYNTAX        TruthValue
        MAX-ACCESS        read-write
        STATUS        obsolete
        DESCRIPTION   "Used to indicate whether directly connected
                      networks through non-ospf interfaces are
                      distributed to OSPF database or not. If 
                      set to true all the static routes
                      will be added as external routes to OSPF
                      routing domain, provided the router is
                      configured as AS Border router. Also originates
                      asExtern link LSA."
        DEFVAL        { false }
        ::= { rcIpRoutingRedistributeDirectToOspf 1 }
 
rcIpRoutingRedistributeDirectToOspfMethod OBJECT-TYPE
        SYNTAX        INTEGER {
                         usePortSpeed(1),       
                         useExplicitMetric(2)  
                      }
        MAX-ACCESS        read-write
        STATUS        obsolete
        DESCRIPTION   "Used to indicate whether or not to use the user
                      specified default metric for redistributing
                      direct routes to OSPF."
        DEFVAL        { usePortSpeed }
        ::= { rcIpRoutingRedistributeDirectToOspf 2 }

rcIpRoutingRedistributeDirectToOspfExplicitMetric OBJECT-TYPE
        SYNTAX        INTEGER (1..'FFFF'h)
        MAX-ACCESS        read-write
        STATUS        obsolete
        DESCRIPTION   "Value of metric that is used to translate the
                      routes to directly connected networks to OSPF."
        DEFVAL        { 1 }
        ::= { rcIpRoutingRedistributeDirectToOspf 3 }
 
rcIpRoutingRedistributeDirectToOspfExternalMetricType  OBJECT-TYPE
        SYNTAX        INTEGER {
                         type1(1),          -- extenal metric type1
                         type2(2)           -- extenal metric type2
                      }
        MAX-ACCESS        read-write
        STATUS        obsolete
        DESCRIPTION   "Used to configure the metric type of the
                      distributed routes to OSPF domain.
                      type1 means the metric is comparable directly
                      to the link state metric 
                      (cost = internal cost + external cost). 
                      type2 means the metric is considered larger 
                      than any link state metric (cost = external 
                      cost)."
        DEFVAL        { type1 }
        ::= { rcIpRoutingRedistributeDirectToOspf 4 }


-- rcIpRouting/rcIpRoutingRedistributeStaticToOspf Group

rcIpRoutingRedistributeStaticToOspf OBJECT IDENTIFIER ::= {rcIpRouting 4}

rcIpRoutingRedistributeStaticToOspfEnable  OBJECT-TYPE
        SYNTAX        TruthValue
        MAX-ACCESS        read-write
        STATUS        obsolete
        DESCRIPTION   "Used to indicate whether static routes (that
                      are configured locally through management
                      protocol) are distributed to OSPF database
                      or not. If set to true all the static routes
                      will be added as external routes to OSPF
                      routing domain, provided the router is
                      configured as AS Border router. Also originates
                      asExtern link LSA."
        DEFVAL        { false }
        ::= { rcIpRoutingRedistributeStaticToOspf 1 }
 
rcIpRoutingRedistributeStaticToOspfExplicitMetric OBJECT-TYPE
        SYNTAX        INTEGER (1..'FFFF'h)
        MAX-ACCESS        read-write
        STATUS        obsolete
        DESCRIPTION   "Value of metric that is used to translate the
                      static routes to OSPF."
        DEFVAL        { 10 }
        ::= { rcIpRoutingRedistributeStaticToOspf 2 }
 
rcIpRoutingRedistributeStaticToOspfUseExplicitMetric OBJECT-TYPE
        SYNTAX        TruthValue
        MAX-ACCESS        read-write
        STATUS        obsolete
        DESCRIPTION   "Used to indicate whether or not to use the user
                      specified default metric for redistributing
                      static routes to OSPF."
        DEFVAL        { false }
        ::= { rcIpRoutingRedistributeStaticToOspf 3 }

rcIpRoutingRedistributeStaticToOspfExternalMetricType  OBJECT-TYPE
        SYNTAX        INTEGER {
                         type1(1),          -- extenal metric type1
                         type2(2)           -- extenal metric type2
                      }
        MAX-ACCESS        read-write
        STATUS        obsolete
        DESCRIPTION   "Used to configure the metric type of the
                      distributed routes to OSPF domain.
                      type1 means the metric is comparable directly
                      to the link state metric 
                      (cost = internal cost + external cost). 
                      type2 means the metric is considered larger 
                      than any link state metric (cost = external 
                      cost)."
        DEFVAL        { type2 }
        ::= { rcIpRoutingRedistributeStaticToOspf 4 }

rcIpRoutingRedistributeStaticToOspfAdvertDefRte  OBJECT-TYPE
        SYNTAX        TruthValue
        MAX-ACCESS        read-write
        STATUS        obsolete
        DESCRIPTION   "Used to indicate whether default route (that
                      are configured locally through management
                      protocol) should be distributed to OSPF database
                      or not. If set to true then the default route will 
                      be added as external route to OSPF routing domain, 
                      provided the router is configured as AS Border router. 
                      Also originates asExtern link LSA."
        DEFVAL        { false }
        ::= { rcIpRoutingRedistributeStaticToOspf 5 }

-- rcIpRouting/rcIpRoutingRedistributeDirectToRip Group

rcIpRoutingRedistributeDirectToRip OBJECT IDENTIFIER ::= {rcIpRouting 5}

rcIpRoutingRedistributeDirectToRipEnable  OBJECT-TYPE
        SYNTAX        TruthValue
        MAX-ACCESS        read-write
        STATUS        obsolete
        DESCRIPTION   "Used to indicate whether directly connected
                      networks through non-rip interfaces are
                      distributed to RIP or not." 
        DEFVAL        { false }
        ::= { rcIpRoutingRedistributeDirectToRip 1 }


-- rcIpRouting/rcIpRoutingRedistributeStaticToRip Group

rcIpRoutingRedistributeStaticToRip OBJECT IDENTIFIER ::= {rcIpRouting 6}

rcIpRoutingRedistributeStaticToRipEnable  OBJECT-TYPE
        SYNTAX        TruthValue
        MAX-ACCESS        read-write
        STATUS        obsolete
        DESCRIPTION   "Used to indicate whether static routes (that
                      are configured locally through management
                      protocol) are distributed to RIP database
                      or not. If set to true all the static routes
                      will be added as external routes to RIP
                      routing domain."
        DEFVAL        { false }
        ::= { rcIpRoutingRedistributeStaticToRip 1 }


rcIpConfIgmpTable OBJECT-TYPE
        SYNTAX        SEQUENCE OF RcIpConfIgmpEntry
        MAX-ACCESS        not-accessible
        STATUS        current
        DESCRIPTION   "A table used to maintain IGMP information
                      for a particular interface."
    ::= { rcIp 5 }
 
rcIpConfIgmpEntry OBJECT-TYPE
        SYNTAX        RcIpConfIgmpEntry
        MAX-ACCESS        not-accessible
        STATUS        current
        DESCRIPTION   "Entry containing IGMP information.  An entry is
                      automatically created in this table when routing 
                      is enabled for an interface -or- when an ip address 
                      is configured on an interface."
        INDEX      { rcIpConfIgmpIfIndex }
        ::= { rcIpConfIgmpTable 1 }
 
RcIpConfIgmpEntry ::= SEQUENCE {
        rcIpConfIgmpIfIndex                 INTEGER,
        rcIpConfIgmpQueryInterval           INTEGER,
        rcIpConfIgmpVersion                 INTEGER,
        rcIpConfIgmpQueryMaxResponseTime    INTEGER,
        rcIpConfIgmpQuerierPresentTimeout   INTEGER,
        rcIpConfIgmpLeaveEnabled            TruthValue,
        rcIpConfIgmpRowStatus               RowStatus,
        rcIpConfIgmpRobustness              INTEGER,
        rcIpConfIgmpLastMemberQueryInterval INTEGER
}

rcIpConfIgmpIfIndex OBJECT-TYPE
        SYNTAX          INTEGER (0..65535)
        MAX-ACCESS          read-only
        STATUS          current
        DESCRIPTION     "An unique value to identify a physical 
                        interface or a logical interface (VLAN)."
        ::= { rcIpConfIgmpEntry 1 }

rcIpConfIgmpQueryInterval OBJECT-TYPE
         SYNTAX     INTEGER (1..65535)
         MAX-ACCESS     read-write
         STATUS     current
         DESCRIPTION "The frequency at which IGMP Host-Query packets are
                     transmitted on this interface."
         DEFVAL     { 125 }
         ::= { rcIpConfIgmpEntry 2 }
 
rcIpConfIgmpVersion OBJECT-TYPE
         SYNTAX     INTEGER { version1(1), version2(2) }
         MAX-ACCESS     read-write
         STATUS     current
         DESCRIPTION "The version of IGMP which is running on this
                     interface. This object can be used to configure a
                     router capable of running either value.  For IGMP
                     to function correctly, all routers on a LAN must
                     be configured to run the same version of IGMP on
                     that LAN."
         DEFVAL     { version2 }
         ::= { rcIpConfIgmpEntry 3 }
 
rcIpConfIgmpQueryMaxResponseTime OBJECT-TYPE
         SYNTAX     INTEGER (1..255)
         MAX-ACCESS     read-write
         STATUS     current
         DESCRIPTION "The maximum query response time advertised in
                     IGMPv2 queries on this interface.  Smaller values
                     allow a router to prune groups faster."
         DEFVAL     { 10 }
         ::= { rcIpConfIgmpEntry 4 }
 
rcIpConfIgmpQuerierPresentTimeout OBJECT-TYPE
         SYNTAX        Integer32
         MAX-ACCESS     read-write
         STATUS     current
         DESCRIPTION "A timeout interval.  If no IGMPv2 queries are
                     heard on this interface within this timeout
                     interval, the local router will take over the
                     Querier on the IP subnet to which this interface
                     is attached."
         DEFVAL     { 255 }
 
         ::= { rcIpConfIgmpEntry 5 }
 
rcIpConfIgmpLeaveEnabled OBJECT-TYPE
         SYNTAX     TruthValue
         MAX-ACCESS     read-write
         STATUS     current
         DESCRIPTION "An indication of whether the processing of IGMPv2
                      Leave messages is enabled on this interface."
         DEFVAL    { true }
         ::= { rcIpConfIgmpEntry 6 }
 
rcIpConfIgmpRowStatus OBJECT-TYPE
        SYNTAX          RowStatus
        MAX-ACCESS          read-write
        STATUS          current
        DESCRIPTION     "Status of entry."
        ::= { rcIpConfIgmpEntry 7 }

rcIpConfIgmpRobustness OBJECT-TYPE
        SYNTAX          INTEGER (2..255)
        MAX-ACCESS          read-write
        STATUS          current
        DESCRIPTION     "lossiness of network."
        ::= { rcIpConfIgmpEntry 8 }

rcIpConfIgmpLastMemberQueryInterval OBJECT-TYPE
        SYNTAX          INTEGER (1..255)
        MAX-ACCESS          read-write
        STATUS          current
        DESCRIPTION     "max response in GrpSpec Query."
        ::= { rcIpConfIgmpEntry 9 }

rcIgmpGroupTable OBJECT-TYPE
        SYNTAX     SEQUENCE OF RcIgmpGroupEntry
        MAX-ACCESS     not-accessible
        STATUS     current
        DESCRIPTION "The (conceptual) table listing the multicast 
                    groups configured in the device."
    ::= { rcIp 6 }
 
rcIgmpGroupEntry OBJECT-TYPE
        SYNTAX     RcIgmpGroupEntry
        MAX-ACCESS     not-accessible
        STATUS     current
        DESCRIPTION "An entry (conceptual row) representing an
                    Igmp group."
        INDEX      { rcIgmpGroupIpAddress, rcIgmpGroupMembers }
        ::= { rcIgmpGroupTable 1 }
 
RcIgmpGroupEntry ::= SEQUENCE {
        rcIgmpGroupIpAddress         IpAddress,
        rcIgmpGroupMembers           IpAddress,
        rcIgmpGroupInPort            INTEGER,
        rcIgmpGroupExpiration        INTEGER 
}

rcIgmpGroupIpAddress OBJECT-TYPE
        SYNTAX          IpAddress 
        MAX-ACCESS          read-only
        STATUS          current
        DESCRIPTION     "Multicast group Address (Class D) that others
                         want to join. A group address can be the same 
                         for many incoming ports."
        ::= { rcIgmpGroupEntry 1 }

rcIgmpGroupMembers OBJECT-TYPE
        SYNTAX          IpAddress 
        MAX-ACCESS          read-only
        STATUS          current
        DESCRIPTION     "IP Address of a source that has sent group 
                         report wishing to join this group."
        ::= { rcIgmpGroupEntry 2 }
 
rcIgmpGroupInPort OBJECT-TYPE
        SYNTAX          INTEGER (0..65535)
        MAX-ACCESS          read-only
        STATUS          current
        DESCRIPTION     "An unique value to identify a physical
                        interface or a logical interface (VLAN),
                        which has received Group reports from various
                        sources."
        ::= { rcIgmpGroupEntry 3 }

rcIgmpGroupExpiration OBJECT-TYPE
         SYNTAX        Integer32
         MAX-ACCESS     read-only
         STATUS     current
         DESCRIPTION "Time left before the group report expired on this
                      port. Only one of this variable port. This 
                      variable is updated upon receiving a group report."
         ::= { rcIgmpGroupEntry 4 }

-- IP Route Table

rcIpRouteTable OBJECT-TYPE 
        SYNTAX          SEQUENCE OF RcIpRouteEntry
        MAX-ACCESS          not-accessible 
        STATUS          current 
        DESCRIPTION     "This entity's IP Routing table."
    ::= { rcIp 7 }

rcIpRouteEntry OBJECT-TYPE
	SYNTAX  	RcIpRouteEntry
        MAX-ACCESS  	not-accessible
        STATUS  	current
        DESCRIPTION	"A route to a particular destination."
        INDEX   { rcIpRouteDest, rcIpRouteMask }
    ::= { rcIpRouteTable 1 }

RcIpRouteEntry ::=
	SEQUENCE {
        	rcIpRouteDest IpAddress,
                rcIpRouteMask IpAddress,
                rcIpRouteNextHop IpAddress,
                rcIpRouteMetric  INTEGER,
                rcIpRouteIfIndex InterfaceIndex,
                rcIpRouteType INTEGER,
                rcIpRouteProto INTEGER,
                rcIpRouteAge INTEGER,
		rcIpRouteRowStatus RowStatus
              }

rcIpRouteDest OBJECT-TYPE
        SYNTAX  	IpAddress
        MAX-ACCESS  	read-only
        STATUS  	current
        DESCRIPTION 	"The destination IP address of this route.  An
                      	entry with a value of 0.0.0.0 is considered a
                      	default route.  Multiple routes to a single
                      	destination can appear in the table, but access to
                      	such multiple entries is dependent on the table-
                      	access mechanisms defined by the network
                      	management protocol in use."
    ::= { rcIpRouteEntry 1 }

rcIpRouteMask OBJECT-TYPE
        SYNTAX  	IpAddress
        MAX-ACCESS  	read-only
        STATUS  	current
        DESCRIPTION	"Indicate the mask to be logical-ANDed with the
                      	destination address before being compared to the
                      	value in the rcIpRouteDest field.  For those systems
                      	that do not support arbitrary subnet masks, an
                      	agent constructs the value of the rcIpRouteMask by
                      	determining whether the value of the correspondent
                      	rcIpRouteDest field belong to a class-A, B, or C
                      	network, and then using one of:

                           mask           network
                           255.0.0.0      class-A
                           255.255.0.0    class-B
                           255.255.255.0  class-C

                      	If the value of the rcIpRouteDest is 0.0.0.0 (a
                      	default route), then the mask value is also
                      	0.0.0.0.  It should be noted that all IP routing
                      	subsystems implicitly use this mechanism."
    ::= { rcIpRouteEntry 2 }

rcIpRouteNextHop OBJECT-TYPE
        SYNTAX  	IpAddress
        MAX-ACCESS  	read-write
        STATUS  	current
        DESCRIPTION 	"The IP address of the next hop of this route.
                      	(In the case of a route bound to an interface
                      	which is realized via a broadcast media, the value
                      	of this field is the agent's IP address on that
                      	interface)."
    ::= { rcIpRouteEntry 3 }

rcIpRouteMetric OBJECT-TYPE
        SYNTAX          Integer32
        MAX-ACCESS  	read-write
        STATUS  	current
        DESCRIPTION 	"The primary routing metric for this route.  The
                      	semantics of this metric are determined by the
                      	routing-protocol specified in the route's
                      	rcIpRouteProto value.  If this metric is not used,
                      	its value should be set to -1."
    ::= { rcIpRouteEntry 4 }

rcIpRouteIfIndex OBJECT-TYPE
        SYNTAX  	InterfaceIndex
        MAX-ACCESS  	read-only
        STATUS  	current
        DESCRIPTION 	"The index value which uniquely identifies the
                      	local interface through which the next hop of this
                      	route should be reached.  The interface identified
                      	by a particular value of this index is the same
                      	interface as identified by the same value of
                      	ifIndex."
    ::= { rcIpRouteEntry 5 }

rcIpRouteType OBJECT-TYPE
        SYNTAX  INTEGER {
                    other(1),        -- none of the following
                    direct(3),       -- connected (sub-)network

                                     -- route to a non-local
                    indirect(4)      -- host/network/sub-network
               }
        MAX-ACCESS  	read-only
        STATUS  	current
        DESCRIPTION 	"The type of route.  Note that the values
                      	direct(3) and indirect(4) refer to the notion of
                      	direct and indirect routing in the IP
                      	architecture."
    ::= { rcIpRouteEntry 6 }

rcIpRouteProto OBJECT-TYPE
        SYNTAX  INTEGER {
                    other(1),       -- none of the following

                                    -- non-protocol information,
                                    -- e.g., manually configured
                    local(2),       -- entries

                                    -- set via a network
                    netmgmt(3),     -- management protocol

                                    -- obtained via ICMP,
                    icmp(4),        -- e.g., Redirect

                                    -- the remaining values are
                                    -- all gateway routing
                                    -- protocols
                    egp(5),
                    ggp(6),
                    hello(7),
                    rip(8),
                    is-is(9),
                    es-is(10),
                    ciscoIgrp(11),
                    bbnSpfIgp(12),
                    ospf(13),
                    bgp(14)
                }
        MAX-ACCESS  	read-only
        STATUS  	current
        DESCRIPTION	"The routing mechanism via which this route was
                      	learned.  Inclusion of values for gateway routing
                      	protocols is not intended to imply that hosts
                      	should support those protocols."
    ::= { rcIpRouteEntry 7 }

rcIpRouteAge OBJECT-TYPE
        SYNTAX          Integer32
        MAX-ACCESS  	read-only
        STATUS  	current
        DESCRIPTION	"The number of seconds since this route was last
                      	updated or otherwise determined to be correct.
                      	Note that no semantics of `too old' can be implied
                      	except through knowledge of the routing protocol
                      	by which the route was learned."
    ::= { rcIpRouteEntry 8 }

rcIpRouteRowStatus OBJECT-TYPE
        SYNTAX        	RowStatus
        MAX-ACCESS        	read-write
        STATUS        	current
        DESCRIPTION   	"Used to create/delete entries"
    ::= { rcIpRouteEntry 9 }


-- Ip Config Dhcp Table
 
rcIpConfDhcpTable OBJECT-TYPE 
        SYNTAX          SEQUENCE OF RcIpConfDhcpEntry
        MAX-ACCESS          not-accessible 
        STATUS          current 
        DESCRIPTION     "DHCP configuration table"
    ::= { rcIp 8 }

rcIpConfDhcpEntry OBJECT-TYPE
        SYNTAX        	RcIpConfDhcpEntry
        MAX-ACCESS        	not-accessible
        STATUS        	current
        DESCRIPTION   	"Used to configure DHCP on a particular port.  An
		      	entry is created automatically when the variable
		      	rcIpConfDhcpEnable is set to TRUE.  

 		      	Once created this entry will only be deleted if the 
		      	rcIpConfDhcpRowStatus is set to 'destroy(6)'.  In
		      	which case, the rcIpConfDhcpEnable is automatically
		      	reset to the FALSE setting."
        INDEX         	{ rcIpConfDhcpIfIndex }
        ::= { rcIpConfDhcpTable 1 }
 
RcIpConfDhcpEntry ::=
        SEQUENCE {
                rcIpConfDhcpIfIndex   	    InterfaceIndex,
                rcIpConfDhcpMaxHop    	    INTEGER,
                rcIpConfDhcpMinSec    	    INTEGER,
                rcIpConfDhcpMode      	    INTEGER,
                rcIpConfDhcpRowStatus 	    RowStatus,
		rcIpConfDhcpNumRequests     Counter32,
		rcIpConfDhcpNumReplies	    Counter32,
		rcIpConfDhcpAlwaysBroadcast TruthValue
        }
 
rcIpConfDhcpIfIndex OBJECT-TYPE
        SYNTAX        	InterfaceIndex (0..4094)
        MAX-ACCESS        	read-only
        STATUS        	current
        DESCRIPTION   	"Interface number.  The number can represent either
		      	a physical or logical(VLAN) interface."
        ::= { rcIpConfDhcpEntry 1 }
 
rcIpConfDhcpMaxHop OBJECT-TYPE
        SYNTAX        	INTEGER (1..16)
        MAX-ACCESS        	read-write
        STATUS        	current
        DESCRIPTION   	"Used to indicate the maximum number of hops a 
		      	DHCP packet can take from the source device to 
		      	the destination device (i.e., DHCP client to 
		      	DHCP server)."
 	DEFVAL        	{ 4 }
        ::= { rcIpConfDhcpEntry 2 }
 
rcIpConfDhcpMinSec OBJECT-TYPE
        SYNTAX        	INTEGER (0..65535)
        MAX-ACCESS        	read-write
        STATUS        	current
        DESCRIPTION   	"Used to indicate the minimum number of seconds 
		      	to wait between receiving a DHCP packet and
		      	actually forwarding the DHCP packet to the 
		      	destination device.  A value of zero(0) indicates
		      	forwarding should be done immediately without any
		      	delay."
	DEFVAL        	{ 0 }
        ::= { rcIpConfDhcpEntry 3 }
 
rcIpConfDhcpMode OBJECT-TYPE
        SYNTAX		INTEGER {
				none(0),
				bootp(2),
				dhcp(3),
				both(4)
			}
        MAX-ACCESS     	read-write
        STATUS        	current
        DESCRIPTION   	"Used to indicate what type of DHCP packets this
		      	interface should support.  A value of none(1) will
		      	result in all incoming DHCP and BOOTP packets to
		      	be dropped." 
        DEFVAL        	{ both }
        ::= { rcIpConfDhcpEntry 4 }
 
rcIpConfDhcpRowStatus OBJECT-TYPE
        SYNTAX        	RowStatus
        MAX-ACCESS        	read-write
        STATUS        	current
        DESCRIPTION   	"An entry is created automatically when the variable
                      	rcIpConfDhcpEnable is set to TRUE.

                      	Once created this entry will only be deleted if the
                      	rcIpConfDhcpRowStatus is set to 'destroy(6)'.  In
                      	which case, the rcIpConfDhcpEnable is automatically
                      	reset to the FALSE setting."
        ::= { rcIpConfDhcpEntry 5 }

rcIpConfDhcpNumRequests OBJECT-TYPE
        SYNTAX        	Counter32
        MAX-ACCESS        	read-only
        STATUS        	current
        DESCRIPTION   	"The total number of DHCP requests seen on this interface."
        ::= { rcIpConfDhcpEntry 6 }

rcIpConfDhcpNumReplies OBJECT-TYPE
        SYNTAX        	Counter32
        MAX-ACCESS        	read-only
        STATUS        	current
        DESCRIPTION   	"The total number of DHCP replies seen on this interface."
        ::= { rcIpConfDhcpEntry 7 }

rcIpConfDhcpAlwaysBroadcast OBJECT-TYPE
        SYNTAX        	TruthValue
        MAX-ACCESS        	read-write
        STATUS        	current
        DESCRIPTION   	"Used to indicate if DHCP Reply packets should be 
		    	broadcast to the DHCP client on this interface."
	DEFVAL		{ false }
        ::= { rcIpConfDhcpEntry 8 }


-- Ip Dhcp Forward Table
 
rcIpDhcpForwardTable OBJECT-TYPE 
        SYNTAX	      	SEQUENCE OF RcIpDhcpForwardEntry
        MAX-ACCESS        	not-accessible 
        STATUS        	current 
        DESCRIPTION   	"DHCP forwarding table."
    ::= { rcIp 9 }

rcIpDhcpForwardEntry OBJECT-TYPE
        SYNTAX        	RcIpDhcpForwardEntry
        MAX-ACCESS        	not-accessible
        STATUS        	current
        DESCRIPTION   	"An entry used represents a DHCP forwarding directive."
        INDEX         	{ rcIpDhcpForwardAgentAddr, rcIpDhcpForwardServerAddr }
        ::= { rcIpDhcpForwardTable 1 }
 
RcIpDhcpForwardEntry ::=
        SEQUENCE {
                rcIpDhcpForwardAgentAddr   IpAddress,
                rcIpDhcpForwardServerAddr  IpAddress,
                rcIpDhcpForwardEnable      TruthValue,
                rcIpDhcpForwardMode        INTEGER,
                rcIpDhcpForwardRowStatus   RowStatus
        }
 
rcIpDhcpForwardAgentAddr OBJECT-TYPE
        SYNTAX        	IpAddress
        MAX-ACCESS        	read-only
        STATUS        	current
        DESCRIPTION   	"The IP address configured on an interface
                      	(i.e., a locally configured IP address)."
        ::= { rcIpDhcpForwardEntry 1 }
 
rcIpDhcpForwardServerAddr OBJECT-TYPE
        SYNTAX        	IpAddress
        MAX-ACCESS        	read-only
        STATUS        	current
        DESCRIPTION   	"The IP address of the DHCP server.  If this
	              	IP address corresponds to a locally configured
		      	IP network, the DHCP packet is broadcasted out
	       	      	the interface the IP address is assigned to.
		      	This behavior is known as 'relay agent' mode.

 		      	If this IP address is a remote address, the DHCP
		      	packet is sent via unicast to the remote device.
		      	This behavior is known as 'preferred server' mode."
        ::= { rcIpDhcpForwardEntry 2 }
 
rcIpDhcpForwardEnable OBJECT-TYPE
        SYNTAX        	TruthValue
        MAX-ACCESS        	read-write
        STATUS        	current
        DESCRIPTION   	"Used to indicate whether is entry should be used."
	DEFVAL        	{ true }
        ::= { rcIpDhcpForwardEntry 3 }
 
rcIpDhcpForwardMode OBJECT-TYPE
        SYNTAX        	INTEGER {
				none(0),
				bootp(2),
				dhcp(3),
				both(4)
			}
        MAX-ACCESS        	read-write
        STATUS        	current
        DESCRIPTION   	"Used to indicate whether this entry pertains to
		      	BOOTP packets, DHCP packets, or both."
	DEFVAL        	{ both }
        ::= { rcIpDhcpForwardEntry 4 }
 
rcIpDhcpForwardRowStatus OBJECT-TYPE
        SYNTAX        	RowStatus
        MAX-ACCESS        	read-write
        STATUS        	current
        DESCRIPTION   	"Row status of this entry."
        ::= { rcIpDhcpForwardEntry 5 }


-- IP Filter Group

rcIpFilter OBJECT IDENTIFIER ::= { rcIp 10 }

rcIpFilterFilterTableSize OBJECT-TYPE
        SYNTAX        	Integer32
        MAX-ACCESS        	read-only
        STATUS        	current
        DESCRIPTION   	"Used to indicate the number of entries in the
                      	rcIpFilterTable."
        ::= { rcIpFilter 1 }

rcIpFilterGlobalListTableSize OBJECT-TYPE
        SYNTAX        	Integer32
        MAX-ACCESS        	read-only
        STATUS        	current
        DESCRIPTION   	"Used to indicate the number of entries in the
                      	rcIpFilterGlobalListTable."
        ::= { rcIpFilter 2 }

rcIpFilterBaseListTableSize OBJECT-TYPE
        SYNTAX        	Integer32
        MAX-ACCESS        	read-only
        STATUS        	current
        DESCRIPTION   	"Used to indicate the number of entries in the
                      	rcIpFilterBaseListTable."
        ::= { rcIpFilter 3 }

rcIpFilterPortTableSize OBJECT-TYPE
        SYNTAX        	Integer32
        MAX-ACCESS        	read-only
        STATUS        	current
        DESCRIPTION   	"Used to indicate the number of entries in the
                      	rcIpFilterPortTable."
        ::= { rcIpFilter 4 }

rcIpFilterNextAvailFilterId OBJECT-TYPE
        SYNTAX        Integer32
        MAX-ACCESS          read-only
        STATUS          current
        DESCRIPTION     "next available filter-id in the
                        rcIpFilterPortTable."
        ::= { rcIpFilter 5 }
 

-- IP Filter Table

rcIpFilterTable OBJECT-TYPE
        SYNTAX		SEQUENCE OF RcIpFilterEntry
        MAX-ACCESS        	not-accessible
        STATUS        	current
        DESCRIPTION   	"A table containing IP filters."
        ::= { rcIpFilter 20 }

rcIpFilterEntry OBJECT-TYPE
	SYNTAX        	RcIpFilterEntry
        MAX-ACCESS        	not-accessible
        STATUS        	current
        DESCRIPTION   	"IP filter attributes.  

			The system supports a vast array of filter options.
			Each of these options are supported in this entry.
			If a particular option is not used, the column
			should be set to zero."
        INDEX         	{ rcIpFilterType, rcIpFilterDstAddr,
			  rcIpFilterDstMask, rcIpFilterSrcAddr,
			  rcIpFilterSrcMask, rcIpFilterId }
        ::= { rcIpFilterTable 1 }

RcIpFilterEntry ::= SEQUENCE {
		rcIpFilterType INTEGER,
		rcIpFilterDstAddr IpAddress,
		rcIpFilterDstMask IpAddress,
		rcIpFilterSrcAddr IpAddress,
		rcIpFilterSrcMask IpAddress,
		rcIpFilterId INTEGER (1..4096),
		rcIpFilterName DisplayString (SIZE (0..15)),
		rcIpFilterProtocolType INTEGER,
		rcIpFilterSrcPort INTEGER (0..65535),
		rcIpFilterSrcOption INTEGER,
		rcIpFilterDstPort INTEGER (0..65535),
		rcIpFilterDstOption INTEGER,
		rcIpFilterCopyToCpu TruthValue,
		rcIpFilterMirror TruthValue,
		rcIpFilterHighPriority TruthValue,
		rcIpFilterTcpConnect TruthValue,
		rcIpFilterIeeeVlanPriority INTEGER,
		rcIpFilterUsePktLimit TruthValue,
		rcIpFilterPktLimit INTEGER,
		rcIpFilterRowStatus RowStatus,
                rcIpFilterMode INTEGER,
                rcIpFilterIpTosRule INTEGER,
		rcIpFilterStopOnMatch TruthValue,
                rcIpFilterDiffServMatchIeee8021PEnable TruthValue,
                rcIpFilterDiffServMatchIeee8021P INTEGER(0..7),
                rcIpFilterDiffServMatchDsFieldEnable TruthValue,
                rcIpFilterDiffServMatchDsField INTEGER(0..63),
                rcIpFilterDiffServModifyIeee8021PEnable TruthValue,
                rcIpFilterDiffServModifyIeee8021P INTEGER(0..7),
                rcIpFilterDiffServModifyDsFieldEnable TruthValue,
                rcIpFilterDiffServModifyDsField INTEGER(0..63),
                rcIpFilterDiffServTrafficProfileId INTEGER(0..64),
                rcIpFilterMatchIcmpRequest TruthValue,
                rcIpFilterMatchIpFragment TruthValue,
                rcIpFilterStatisticEnable TruthValue,
                rcIpFilterInOctets Counter32,
                rcIpFilterInPackets Counter32,
                rcIpFilterRateLimitDiscardPackets Counter32

		}

rcIpFilterType OBJECT-TYPE
        SYNTAX		INTEGER {
			   global(1),
			   destination(2),
			   source(3)
			}
        MAX-ACCESS		read-only
        STATUS		current
        DESCRIPTION	"Used to indicate a particular type of filter.  

                        A 'global' filter is a filter that is applied to
                        all packets irregardless of the packet's source
                        or destination IP address.
 
                        A 'destination' filter is used to match the
                        destination IP address field of incoming packets.
                        When a match is found, this filter is applied to
                        the packet.
 
                        A 'source' filter is used to match the source
                        IP address field of incoming packets.  When a
                        match is found, this filter is applied to the
                        packet."
        ::= { rcIpFilterEntry 1 }

rcIpFilterDstAddr OBJECT-TYPE
        SYNTAX		IpAddress
        MAX-ACCESS		read-only
        STATUS		current
        DESCRIPTION	"Destination IP address to filter on."
        ::= { rcIpFilterEntry 2 }

rcIpFilterDstMask OBJECT-TYPE
        SYNTAX		IpAddress
        MAX-ACCESS		read-only
        STATUS		current
        DESCRIPTION	"Destination IP subnet mask to filter on."
        ::= { rcIpFilterEntry 3 }

rcIpFilterSrcAddr OBJECT-TYPE
        SYNTAX		IpAddress
        MAX-ACCESS		read-only
        STATUS		current
        DESCRIPTION	"Source IP address to filter on."
        ::= { rcIpFilterEntry 4 }

rcIpFilterSrcMask OBJECT-TYPE
        SYNTAX		IpAddress
        MAX-ACCESS		read-only
        STATUS		current
        DESCRIPTION	"Source IP subnet mask to filter on."
        ::= { rcIpFilterEntry 5 }

rcIpFilterId OBJECT-TYPE
        SYNTAX		INTEGER (1..4096)
        MAX-ACCESS		read-only
        STATUS		current
        DESCRIPTION	"This filter's unique identifier(id).  This id
			is automatically generated by the system when
			a filter is created.  This id is used in the
			'rcIpFilterGlobalListTable' and 
			'rcIpFilterBaseListTable' when grouping one
			or more filters into a filter list."
        ::= { rcIpFilterEntry 6 }

rcIpFilterName OBJECT-TYPE
        SYNTAX		DisplayString (SIZE (0..15))
        MAX-ACCESS		read-write
        STATUS		current
        DESCRIPTION	"This filter's name."
        ::= { rcIpFilterEntry 7 }

rcIpFilterProtocolType OBJECT-TYPE
        SYNTAX		INTEGER {
			    ignore(0),
			    icmp(1),
			    tcp(6),
			    udp(17)
			}
        MAX-ACCESS		read-write
        STATUS		current
        DESCRIPTION	"Type of protocol to filter on."
	DEFVAL		{ ignore }
        ::= { rcIpFilterEntry 8 }

rcIpFilterSrcPort OBJECT-TYPE
        SYNTAX		INTEGER (0..65535)
        MAX-ACCESS		read-write
        STATUS		current
        DESCRIPTION	"TCP/UDP source port to filter on."
	DEFVAL		{ 0 }
        ::= { rcIpFilterEntry 9 }

rcIpFilterSrcOption OBJECT-TYPE
        SYNTAX		INTEGER {
                            equal(0),
                            notEqual(1),
                            greater(2),
                            less(3),
                            ignore(4)
			}
        MAX-ACCESS		read-write
        STATUS		current
        DESCRIPTION	"Type of matching to perform on the field
			'rcIpFilterSrcPort'.
			
			For 'source' and 'destination' filters, this
			value can only be 'equal(1)'."
	DEFVAL 		{ ignore }
        ::= { rcIpFilterEntry 10 }

rcIpFilterDstPort OBJECT-TYPE
        SYNTAX		INTEGER (0..65535)
        MAX-ACCESS		read-write
        STATUS		current
        DESCRIPTION	"TCP/UDP destination port to filter on."
	DEFVAL		{ 0 }
        ::= { rcIpFilterEntry 11 }

rcIpFilterDstOption OBJECT-TYPE
        SYNTAX		INTEGER {
                            equal(0),
                            notEqual(1),
                            greater(2),
                            less(3),
                            ignore(4)
			}
        MAX-ACCESS		read-write
        STATUS		current
        DESCRIPTION	"Type of matching to perform on the field
			'rcIpFilterDstPort'.

			For 'source' and 'destination' filters, this
			value can only be 'equal(1)'."
	DEFVAL		{ ignore }
        ::= { rcIpFilterEntry 12 }

rcIpFilterCopyToCpu OBJECT-TYPE
        SYNTAX		TruthValue
        MAX-ACCESS		read-write
        STATUS		deprecated
        DESCRIPTION	"Used to specify whether a packet matching
			this filter should be copied to the CPU."
	DEFVAL		{ false }
        ::= { rcIpFilterEntry 13 }

rcIpFilterMirror OBJECT-TYPE
        SYNTAX		TruthValue
        MAX-ACCESS		read-write
        STATUS		current
        DESCRIPTION	"Used to specify whether a packet matching
			this filter should be mirrored to the port
			specified by 'rcMirrorByPortMirrorPort'."
	DEFVAL		{ false }
        ::= { rcIpFilterEntry 14 }

rcIpFilterHighPriority OBJECT-TYPE
        SYNTAX		TruthValue
        MAX-ACCESS		read-write
        STATUS		deprecated
        DESCRIPTION	"Used to specify whether a packet matching
			this filter should be forwarded with high
			priority." 
	DEFVAL		{ false }
        ::= { rcIpFilterEntry 15 }

rcIpFilterTcpConnect OBJECT-TYPE
        SYNTAX		TruthValue
        MAX-ACCESS		read-write
        STATUS		current
        DESCRIPTION	"Used to specify whether a TCP packet matching
                         this filter should be accepted.  Pass only 
                         those matching TCP packets with either the
                         ACK bit or RST bit set.  Apply only if the IP 
                         Protocol is set to TCP."
	DEFVAL		{ false }
        ::= { rcIpFilterEntry 16 }

rcIpFilterIeeeVlanPriority OBJECT-TYPE
        SYNTAX		INTEGER (0..7)
        MAX-ACCESS		read-write
        STATUS		current
        DESCRIPTION	"Used to specify the priority bits for explicit
                         IEEE VLAN tag for a packet matching this filter.
                         If this priority bit field is greater than the
                         priority field currently in the IEEE tag in the
                         Packet Header, this priority field will be loaded
                         into the Packet Header."
        DEFVAL          { 0 }
        ::= { rcIpFilterEntry 17 }

rcIpFilterUsePktLimit OBJECT-TYPE
        SYNTAX		TruthValue
        MAX-ACCESS		read-write
        STATUS		deprecated
        DESCRIPTION	"Used to specify whether the 'rcIpFilterPktLimit'
			field in this entry should be used when applying
			this filter." 
	DEFVAL		{ false }
        ::= { rcIpFilterEntry 18 }

rcIpFilterPktLimit OBJECT-TYPE
        SYNTAX		INTEGER (0..65535)
        MAX-ACCESS		read-write
        STATUS		deprecated
        DESCRIPTION	"The maximum packet size limit to filter against."
	DEFVAL		{ 1500 }
        ::= { rcIpFilterEntry 19 }

rcIpFilterRowStatus OBJECT-TYPE
        SYNTAX		RowStatus
        MAX-ACCESS		read-write
        STATUS		current
        DESCRIPTION	"Row status of this entry."
        ::= { rcIpFilterEntry 20 }

rcIpFilterMode OBJECT-TYPE
        SYNTAX          INTEGER {
                            useDefaultAction(1),
                            forward(2),
                            drop(3)
                        }
        MAX-ACCESS          read-write
        STATUS          current
        DESCRIPTION     "Used to specify the operation mode for this entry.
			'useDefaultAction' means use the setting specified
			in the 'rcIpFilterPortDefaultAction' variable.  

			'forward' means forward the packet if the packet 
			satisfies this policy.  

			'drop' means drop the packet if the packet satisfies 
			this policy.

			This variable setting has higher precedence than the
			setting in 'rcIpFilterPortDefaultAction'."
        DEFVAL          { useDefaultAction }
        ::= { rcIpFilterEntry 21 }

rcIpFilterIpTosRule OBJECT-TYPE
        SYNTAX          INTEGER {
			    none(0),
                            ipTosRule1(1),
                            ipTosRule2(2),
                            ipTosRule3(3)
                        }
        MAX-ACCESS          read-write
        STATUS          deprecated
        DESCRIPTION     "Used to specify the operation mode for this entry.
                        'none' means do not manupulate the Ip ToS byte.
			'ipTosRule1' means manipulate the Ip ToS byte 
			according to Quid/Gid Rule 1 which is defined in
                        rcIpTosRuleOrRule1.
			'ipTosRule2' means manipulate the Ip ToS byte 
			according to Quid/Gid Rule 2 which is defined in
			rcIpTosRuleOrRule2.
			'ipTosRule3' means manipulate the Ip ToS byte 
			according to Quid/Gid Rule 3 which is defined in
                        rcIpTosRuleOrRule3."
        DEFVAL          { none }
        ::= { rcIpFilterEntry 22 }

rcIpFilterStopOnMatch OBJECT-TYPE
        SYNTAX          TruthValue
        MAX-ACCESS          read-write
        STATUS          current
        DESCRIPTION     "Used to stop further filtering if this filter
			is applied."
        DEFVAL          { true }
        ::= { rcIpFilterEntry 23 }

rcIpFilterDiffServMatchIeee8021PEnable OBJECT-TYPE
        SYNTAX          TruthValue
        MAX-ACCESS          read-write
        STATUS          current
	DESCRIPTION	"Used to specify whether the value stored in the
			variable 'rcIpFilterDiffServMatchIeee8021P' should
			be used in this filter." 
        DEFVAL          { false }
        ::= { rcIpFilterEntry 24 }

rcIpFilterDiffServMatchIeee8021P OBJECT-TYPE
        SYNTAX          INTEGER (0..7)
        MAX-ACCESS          read-write
        STATUS          current
	DESCRIPTION	"Used to specify the match value for the 802.1P
			field.  If the 802.1P field in the incoming packet
			matches this value, then this filter will be
			applied to the packet."
	DEFVAL		{ 0 }
        ::= { rcIpFilterEntry 25 }

rcIpFilterDiffServMatchDsFieldEnable OBJECT-TYPE
        SYNTAX          TruthValue
        MAX-ACCESS          read-write
        STATUS          current
        DESCRIPTION     "Used to specify whether the value stored in the 
                        variable 'rcIpFilterDiffServMatchDsField' should    
                        be used in this filter."
        DEFVAL          { false }
        ::= { rcIpFilterEntry 26 }

rcIpFilterDiffServMatchDsField OBJECT-TYPE
        SYNTAX          INTEGER (0..63)
        MAX-ACCESS          read-write
        STATUS          current
	DESCRIPTION	"Used to specify the match value for the DSCP
			field.  If the DSCP field in the incoming packet
			matches this value, then this filter will be
			applied to the packet."
	DEFVAL		{ 0 }
        ::= { rcIpFilterEntry 27 }

rcIpFilterDiffServModifyIeee8021PEnable OBJECT-TYPE
        SYNTAX          TruthValue
        MAX-ACCESS          read-write
        STATUS          current
        DESCRIPTION     "Used to specify whether the value stored in the 
                        variable 'rcIpFilterDiffServModifyIeee8021P' should    
                        be used in this filter."
        DEFVAL          { false }
        ::= { rcIpFilterEntry 28 }

rcIpFilterDiffServModifyIeee8021P OBJECT-TYPE
        SYNTAX          INTEGER (0..7)
        MAX-ACCESS          read-write
        STATUS          current
        DESCRIPTION     "Used to specify the value the 802.1P field
			should be modified to if this filter is applied.
			The modification is applied at the egress point."
	DEFVAL		{ 0 }
        ::= { rcIpFilterEntry 29 }

rcIpFilterDiffServModifyDsFieldEnable OBJECT-TYPE
        SYNTAX          TruthValue
        MAX-ACCESS          read-write
        STATUS          current
        DESCRIPTION     "Used to specify whether the value stored in the  
                        variable 'rcIpFilterDiffServModifyDsField' should     
                        be used in this filter."
        DEFVAL          { false }
        ::= { rcIpFilterEntry 30 }

rcIpFilterDiffServModifyDsField OBJECT-TYPE
        SYNTAX          INTEGER (0..63)
        MAX-ACCESS          read-write
        STATUS          current
        DESCRIPTION     "Used to specify the value the DSCP field
			should be modified to if this filter is applied.
			The modification is applied at the egress point."
	DEFVAL		{ 0 }
        ::= { rcIpFilterEntry 31 }

rcIpFilterDiffServTrafficProfileId OBJECT-TYPE
        SYNTAX          INTEGER (0..64)
        MAX-ACCESS          read-write
        STATUS          current
        DESCRIPTION    	"Used to specify which traffic profile should
			be applied to packets matching this filter. 
			Traffic profiles are specified in the
			'rc2kQosTrafficProfileTable' table.  A '0'
			value means do not apply any traffic profile."
	DEFVAL		{ 0 }
        ::= { rcIpFilterEntry 32 }

rcIpFilterMatchIcmpRequest OBJECT-TYPE
        SYNTAX		TruthValue
        MAX-ACCESS		read-write
        STATUS		current
        DESCRIPTION	"Used to specify whether matching on ICMP
			Request packets should be performed."
	DEFVAL		{ false }
        ::= { rcIpFilterEntry 33 }

rcIpFilterMatchIpFragment OBJECT-TYPE
        SYNTAX		TruthValue
        MAX-ACCESS		read-write
        STATUS		current
        DESCRIPTION	"Used to specify whether matching on fragmented
			IP packets should be performed."
	DEFVAL		{ false }
        ::= { rcIpFilterEntry 34 }

rcIpFilterStatisticEnable OBJECT-TYPE
        SYNTAX		TruthValue
        MAX-ACCESS		read-write
        STATUS		current
        DESCRIPTION	"Used to turn on/off counters for this filter."
	DEFVAL		{ false }
        ::= { rcIpFilterEntry 35 }

rcIpFilterInOctets OBJECT-TYPE
        SYNTAX          Counter32
        MAX-ACCESS          read-only
        STATUS          current
        DESCRIPTION     "The number of In-Octets for this filter."
        ::= { rcIpFilterEntry 36 }

rcIpFilterInPackets OBJECT-TYPE
        SYNTAX          Counter32
        MAX-ACCESS          read-only
        STATUS          current
        DESCRIPTION     "The number of In-Packets for this filter."
        ::= { rcIpFilterEntry 37 }

rcIpFilterRateLimitDiscardPackets OBJECT-TYPE
        SYNTAX          Counter32
        MAX-ACCESS          read-only
        STATUS          current
        DESCRIPTION     "The number of packets discarded due to rate
			limiting."
        ::= { rcIpFilterEntry 38 }


-- IP Filter Global List Table

rcIpFilterGlobalListTable OBJECT-TYPE
        SYNTAX          SEQUENCE OF RcIpFilterGlobalListEntry
        MAX-ACCESS          not-accessible
        STATUS          current
        DESCRIPTION     "A table used to store global filter list information.
			Each row in the table contains a set of individual
			filters that make up a particular filter list."
        ::= { rcIpFilter 21 }

rcIpFilterGlobalListEntry OBJECT-TYPE
        SYNTAX          RcIpFilterGlobalListEntry
        MAX-ACCESS          not-accessible
        STATUS          current
        DESCRIPTION     "Global filter list attributes."
        INDEX           { rcIpFilterGlobalListId } 
        ::= { rcIpFilterGlobalListTable 1 }

RcIpFilterGlobalListEntry ::= SEQUENCE {
		rcIpFilterGlobalListId INTEGER (1..100),
		rcIpFilterGlobalListName DisplayString (SIZE(0..15)),
		rcIpFilterGlobalListFilterIdListSize INTEGER (0..8),
		rcIpFilterGlobalListFilterIdList IdList(SIZE(16)),
		rcIpFilterGlobalListRowStatus RowStatus,
                rcIpFilterGlobalListMemberPorts PortSet
                }

rcIpFilterGlobalListId OBJECT-TYPE
        SYNTAX		INTEGER (1..100)
        MAX-ACCESS		read-only
        STATUS		current
        DESCRIPTION	"An unique value to identify a particular global
			filter list." 
        ::= { rcIpFilterGlobalListEntry 1 }

rcIpFilterGlobalListName OBJECT-TYPE
        SYNTAX		DisplayString (SIZE(0..15))	        	
        MAX-ACCESS		read-write
        STATUS		current
        DESCRIPTION	"Name of this filter list."
        ::= { rcIpFilterGlobalListEntry 2 }

rcIpFilterGlobalListFilterIdListSize OBJECT-TYPE
        SYNTAX		INTEGER (0..8)
        MAX-ACCESS		read-only
        STATUS		current
        DESCRIPTION	"Used to indicate the number of filters are
			associated with this filter list."
        ::= { rcIpFilterGlobalListEntry 3 }

rcIpFilterGlobalListFilterIdList OBJECT-TYPE
        SYNTAX		IdList (SIZE(16))	
        MAX-ACCESS		read-write
        STATUS		current
        DESCRIPTION	"Used to indicate zero or more filters that are
			associated with this filter list.  Each filter
			identifier is stored as two bytes in this array
			starting from offset zero.  Any unused bytes
			should be set to zero."
        ::= { rcIpFilterGlobalListEntry 4 }

rcIpFilterGlobalListRowStatus OBJECT-TYPE
        SYNTAX		RowStatus	
        MAX-ACCESS		read-write
        STATUS		current
        DESCRIPTION	"Row status of this entry."
        ::= { rcIpFilterGlobalListEntry 5 }

rcIpFilterGlobalListMemberPorts OBJECT-TYPE
        SYNTAX          PortSet
        MAX-ACCESS          read-only
        STATUS          current
        DESCRIPTION     "Ports filter is used on."
        ::= { rcIpFilterGlobalListEntry 6 }


-- IP Filter Base Table

rcIpFilterBaseListTable OBJECT-TYPE
        SYNTAX          SEQUENCE OF RcIpFilterBaseListEntry
        MAX-ACCESS          not-accessible
        STATUS          current
        DESCRIPTION     "A table used to store base filter list information.
			Each row in the table contains a set of individual
			filters that make up a particular filter list."
        ::= { rcIpFilter 22 }

rcIpFilterBaseListEntry OBJECT-TYPE
        SYNTAX          RcIpFilterBaseListEntry
        MAX-ACCESS          not-accessible
        STATUS          current
        DESCRIPTION     "Base filter list attributes."
        INDEX           { rcIpFilterBaseListId } 
        ::= { rcIpFilterBaseListTable 1 }

RcIpFilterBaseListEntry ::= SEQUENCE {
		rcIpFilterBaseListId INTEGER (300..1000),
		rcIpFilterBaseListName DisplayString (SIZE(0..15)),
		rcIpFilterBaseListFilterIdListSize INTEGER (0..128),
		rcIpFilterBaseListFilterIdList IdList (SIZE(256)),
		rcIpFilterBaseListRowStatus RowStatus,
                rcIpFilterBaseListMemberPorts PortSet
                }

rcIpFilterBaseListId OBJECT-TYPE
        SYNTAX		INTEGER (300..1000)
        MAX-ACCESS		read-only
        STATUS		current
        DESCRIPTION     "An unique value to identify a particular base
                        filter list."
        ::= { rcIpFilterBaseListEntry 1 }

rcIpFilterBaseListName OBJECT-TYPE
        SYNTAX		DisplayString (SIZE(0..15))	        	
        MAX-ACCESS		read-write
        STATUS		current
        DESCRIPTION	"Name of this filter list."
        ::= { rcIpFilterBaseListEntry 2 }

rcIpFilterBaseListFilterIdListSize OBJECT-TYPE
        SYNTAX		INTEGER (0..128)
        MAX-ACCESS		read-only
        STATUS		current
        DESCRIPTION     "Used to indicate the number of filters are
                        associated with this filter list."
        ::= { rcIpFilterBaseListEntry 3 }

rcIpFilterBaseListFilterIdList OBJECT-TYPE
        SYNTAX		IdList (SIZE(256))	
        MAX-ACCESS		read-write
        STATUS		current
        DESCRIPTION     "Used to indicate zero or more filters that are
                        associated with this filter list.  Each filter
                        identifier is stored as two bytes in this array
                        starting from offset zero.  Any unused bytes
                        should be set to zero."
        ::= { rcIpFilterBaseListEntry 4 }

rcIpFilterBaseListRowStatus OBJECT-TYPE
        SYNTAX		RowStatus	
        MAX-ACCESS		read-write
        STATUS		current
        DESCRIPTION	"Row status of this entry."
        ::= { rcIpFilterBaseListEntry 5 }

rcIpFilterBaseListMemberPorts OBJECT-TYPE
        SYNTAX          PortSet
        MAX-ACCESS          read-only
        STATUS          current
        DESCRIPTION     "Ports filter is used on."
        ::= { rcIpFilterBaseListEntry 6 }
 

-- IP Filter Port Table

rcIpFilterPortTable OBJECT-TYPE
        SYNTAX          SEQUENCE OF RcIpFilterPortEntry
        MAX-ACCESS          not-accessible
        STATUS          current
        DESCRIPTION     "A table used to store port filtering information."
        ::= { rcIpFilter 23 }

rcIpFilterPortEntry OBJECT-TYPE
        SYNTAX          RcIpFilterPortEntry
        MAX-ACCESS          not-accessible
        STATUS          current
        DESCRIPTION     "Port entry attributes."
        INDEX           { rcIpFilterPortIfIndex } 
        ::= { rcIpFilterPortTable 1 }

RcIpFilterPortEntry ::= SEQUENCE {
			rcIpFilterPortIfIndex InterfaceIndex,
			rcIpFilterPortFilterListSize INTEGER (0..128),
			rcIpFilterPortFilterList OCTET STRING (SIZE(256)),
			rcIpFilterPortMode INTEGER,
			rcIpFilterPortEnable TruthValue,
			rcIpFilterPortRowStatus RowStatus,
			rcIpFilterPortDefaultAction INTEGER,
                        rcIpFilterPortNumGlobalFilters INTEGER,
                        rcIpFilterPortNumBaseFilters INTEGER
	                }

rcIpFilterPortIfIndex OBJECT-TYPE
        SYNTAX		InterfaceIndex
        MAX-ACCESS		read-only
        STATUS		current
        DESCRIPTION	"IfIndex value of a port where filtering is
			applied."
        ::= { rcIpFilterPortEntry 1 }

rcIpFilterPortFilterListSize OBJECT-TYPE
        SYNTAX		INTEGER (0..128)
        MAX-ACCESS		read-only
        STATUS		current
        DESCRIPTION	"Used to indicate the number of filter list(s)
			that are assigned to this port."
        ::= { rcIpFilterPortEntry 2 }

rcIpFilterPortFilterList OBJECT-TYPE
        SYNTAX		OCTET STRING (SIZE(256))	
        MAX-ACCESS		read-write
        STATUS		current
        DESCRIPTION     "Used to indicate zero or more filter lists that 
			are associated with this port.  Each filter list
                        identifier is stored as two bytes in this array
                        starting from offset zero.  Any unused bytes
                        should be set to zero."
        ::= { rcIpFilterPortEntry 3 }

rcIpFilterPortMode OBJECT-TYPE
        SYNTAX		INTEGER {
			    permit(1),
			    deny(2),
                            none(3)
			}	
        MAX-ACCESS		read-write
        STATUS		obsolete
        DESCRIPTION	"Used to indicate when filters applied to this
			port should be treated as 'permit' or 'deny'
			filters.
 
                        When filters are not enabled on the port the mode
                        is set to none. The port does not block any packet. 
                        Mode None cannot be used when PortEnable is true. 

			On a port configured as 'permit',  any packet
			that satisfies a filter is allowed to be 
			forwarded.

			On a port configured as 'deny', any packet that
			satisfies a filter is dropped."	
	DEFVAL		{ none }
        ::= { rcIpFilterPortEntry 4 }

rcIpFilterPortEnable OBJECT-TYPE
        SYNTAX		TruthValue	
        MAX-ACCESS		read-write
        STATUS		current
        DESCRIPTION	"Used to indicate whether filtering is configured
			on this port."
	DEFVAL		{ false }
        ::= { rcIpFilterPortEntry 5 }

rcIpFilterPortRowStatus OBJECT-TYPE
        SYNTAX		RowStatus
        MAX-ACCESS		read-write
        STATUS		current
        DESCRIPTION	"Row status of this entry."
        ::= { rcIpFilterPortEntry 6 }

rcIpFilterPortDefaultAction OBJECT-TYPE
        SYNTAX          INTEGER {
                            forward(1),
                            drop(2),
                            none(3)
                        }
        MAX-ACCESS          read-write
        STATUS          current
        DESCRIPTION     "Used to indicate the default action that should
			be performed when an IP filter applies to a
			particular port.   

                        When filters are not enabled on the port the action
                        is set to 'none' which means the port does not block 
			any packet.  'none' cannot be used when PortEnable is 
			true.
 
                        On a port configured as 'forward',  any packet
                        that satisfies a filter is allowed to be
                        forwarded.
 
                        On a port configured as 'drop', any packet that
                        satisfies a filter is dropped."
        DEFVAL          { none }
        ::= { rcIpFilterPortEntry 7 }

rcIpFilterPortNumGlobalFilters OBJECT-TYPE
        SYNTAX        Integer32
        MAX-ACCESS          read-only
        STATUS          current
        DESCRIPTION     "# of global filters"
        ::= { rcIpFilterPortEntry 8 }
 
rcIpFilterPortNumBaseFilters OBJECT-TYPE
        SYNTAX        Integer32
        MAX-ACCESS          read-only
        STATUS          current
        DESCRIPTION     "# of base filters"
        ::= { rcIpFilterPortEntry 9 }

-- IP Policy Address Table
 
rcIpPolicy OBJECT IDENTIFIER ::= { rcIp 11 }

rcIpPolicyAddrTableSize OBJECT-TYPE
        SYNTAX        Integer32
        MAX-ACCESS        read-only
        STATUS        current
        DESCRIPTION   "Used to indicate the number of entries in the 
		      rcIpPolicyAddrTable."
        ::= { rcIpPolicy 1 }

rcIpPolicyAddrTable OBJECT-TYPE
        SYNTAX        SEQUENCE OF RcIpPolicyAddrEntry
        MAX-ACCESS        not-accessible
        STATUS        current
        DESCRIPTION   "A table used to store different types list entries.
                      Each row in the table contains a list entry that is
                      used by a set of announce policies."
        ::= { rcIpPolicy 2 }
 
rcIpPolicyAddrEntry OBJECT-TYPE
        SYNTAX        RcIpPolicyAddrEntry
        MAX-ACCESS        not-accessible
        STATUS        current
        DESCRIPTION   "Route entry attributes."
        INDEX         {rcIpPolicyAddrIpAddr}
        ::= { rcIpPolicyAddrTable 1 }
 
RcIpPolicyAddrEntry ::= SEQUENCE {
                        rcIpPolicyAddrIpAddr IpAddress,
                        rcIpPolicyAddrId   INTEGER,
                        rcIpPolicyAddrAddrListIdListSize INTEGER (0..128),
                        rcIpPolicyAddrAddrListIdList OCTET STRING (SIZE(256)),
                        rcIpPolicyAddrRowStatus RowStatus
                        }


rcIpPolicyAddrIpAddr OBJECT-TYPE
        SYNTAX        IpAddress
        MAX-ACCESS        read-only
        STATUS        current
        DESCRIPTION   "The network address for this type of list entry. This 
                      value is required for all types of lists."
        ::= { rcIpPolicyAddrEntry 1 }
 
rcIpPolicyAddrId OBJECT-TYPE
        SYNTAX	      Integer32
        MAX-ACCESS	      read-only
        STATUS	      current
        DESCRIPTION   "Identifier of this entry. Used internally to identify
		      this entry."
        ::= { rcIpPolicyAddrEntry 2 }

rcIpPolicyAddrAddrListIdListSize OBJECT-TYPE
        SYNTAX	      INTEGER (0..128)
        MAX-ACCESS	      read-only
        STATUS	      current
        DESCRIPTION   "Used to indicate the number of id(s) in the
		      rcIpPolicyAddrListIdList variable."
        ::= { rcIpPolicyAddrEntry 3 }

rcIpPolicyAddrAddrListIdList OBJECT-TYPE
        SYNTAX	      OCTET STRING (SIZE(256))	
        MAX-ACCESS	      read-only
        STATUS	      current
        DESCRIPTION   "Used to indicate zero or more rcIpPolicyAddrListEntry(s)
		      that are referring to this entry.  Each list-id identifier 
                      is stored as two bytes in this array starting from 
                      offset zero.  Any unused bytes should be set to zero."
        ::= { rcIpPolicyAddrEntry 4 }

rcIpPolicyAddrRowStatus OBJECT-TYPE
        SYNTAX		RowStatus
        MAX-ACCESS		read-write
        STATUS		current
        DESCRIPTION	"Row status of this entry."
        ::= { rcIpPolicyAddrEntry 5 }


-- Ip Policy Network Table

rcIpPolicyNetTableSize OBJECT-TYPE
        SYNTAX        Integer32
        MAX-ACCESS        read-only
        STATUS        current
        DESCRIPTION   "Used to indicate the number of entries in the 
		      rcIpPolicyNetTable."
        ::= { rcIpPolicy 3 }

rcIpPolicyNetTable OBJECT-TYPE
        SYNTAX        SEQUENCE OF RcIpPolicyNetEntry
        MAX-ACCESS        not-accessible
        STATUS        current
        DESCRIPTION   "A table used to store different types list entries.
                      Each row in the table contains a list entry that is
                      used by a set of announce policies."
        ::= { rcIpPolicy 4 }
 
rcIpPolicyNetEntry OBJECT-TYPE
        SYNTAX        RcIpPolicyNetEntry
        MAX-ACCESS        not-accessible
        STATUS        current
        DESCRIPTION   "Route entry attributes."
        INDEX         {rcIpPolicyNetAddr, rcIpPolicyNetMask }
        ::= { rcIpPolicyNetTable 1 }
 
RcIpPolicyNetEntry ::= SEQUENCE {
                        rcIpPolicyNetAddr IpAddress,
                        rcIpPolicyNetMask IpAddress,
                        rcIpPolicyNetId   INTEGER,
                        rcIpPolicyNetNetListIdListSize INTEGER (0..128),
                        rcIpPolicyNetNetListIdList OCTET STRING (SIZE(256)),
                        rcIpPolicyNetRowStatus RowStatus
                        }

rcIpPolicyNetAddr OBJECT-TYPE
        SYNTAX        IpAddress
        MAX-ACCESS        read-only
        STATUS        current
        DESCRIPTION   "The network address for this type of list entry. This 
                      value is required for all types of lists."
        ::= { rcIpPolicyNetEntry 1 }
 
rcIpPolicyNetMask OBJECT-TYPE
        SYNTAX        IpAddress
        MAX-ACCESS        read-only
        STATUS        current
        DESCRIPTION   "The route mask for this type of list entry. This 
                      value is meaningful only if rcIpPolicyNetEntry 
                      is equal to exactNet(1), rangeNet(2), advertiseNet(3).
                      For other types it should have the value 0.0.0.0."
        ::= { rcIpPolicyNetEntry 2 }

rcIpPolicyNetId OBJECT-TYPE
        SYNTAX	      Integer32 
        MAX-ACCESS	      read-only
        STATUS	      current
        DESCRIPTION   "Used internally to recognize this entry."
        ::= { rcIpPolicyNetEntry 3 }

rcIpPolicyNetNetListIdListSize OBJECT-TYPE
        SYNTAX	      INTEGER (0..128)
        MAX-ACCESS	      read-only
        STATUS	      current
        DESCRIPTION   "Used to indicate the number of id(s) in the 
		      rcIpPolicyNetListIdList variable."
        ::= { rcIpPolicyNetEntry 4 }

rcIpPolicyNetNetListIdList OBJECT-TYPE
        SYNTAX	      OCTET STRING (SIZE(256))	
        MAX-ACCESS	      read-only
        STATUS	      current
        DESCRIPTION   "Used to indicate zero or more rcIpPolicyNetListEntry(s)  
                      that are referring to this entry.  Each list-id identifier
                      is stored as two bytes in this array starting from 
                      offset zero.  Any unused bytes should be set to zero."
        ::= { rcIpPolicyNetEntry 5 }

rcIpPolicyNetRowStatus OBJECT-TYPE
        SYNTAX		RowStatus
        MAX-ACCESS		read-write
        STATUS		current
        DESCRIPTION	"Row status of this entry."
        ::= { rcIpPolicyNetEntry 6 }


-- IP Policy Address List Table

rcIpPolicyAddrListTableSize OBJECT-TYPE
        SYNTAX        Integer32
        MAX-ACCESS        read-only
        STATUS        current
        DESCRIPTION   "Used to indicate the number of entries in the
                      rcIpPolicyAddrListTable."
        ::= { rcIpPolicy 5 }
 
rcIpPolicyAddrListTable OBJECT-TYPE
        SYNTAX        SEQUENCE OF RcIpPolicyAddrListEntry
        MAX-ACCESS        not-accessible
        STATUS        current
        DESCRIPTION   "A table used to group rcIpPolicyAddrEntry(s) 
                      into a list."
        ::= { rcIpPolicy 6 }

rcIpPolicyAddrListEntry OBJECT-TYPE
        SYNTAX        RcIpPolicyAddrListEntry
        MAX-ACCESS        not-accessible
        STATUS        current
        DESCRIPTION   "Route entry attributes."
        INDEX         { rcIpPolicyAddrListId }
        ::= { rcIpPolicyAddrListTable 1 }
 
RcIpPolicyAddrListEntry ::= SEQUENCE {
                  rcIpPolicyAddrListId INTEGER (1..1000),
                  rcIpPolicyAddrListName DisplayString (SIZE(0..15)),
                  rcIpPolicyAddrListIdListSize INTEGER (0..128),
                  rcIpPolicyAddrListIdList OCTET STRING (SIZE(256)),
                  rcIpPolicyAddrListPolicyIdListSize INTEGER (0..128),
                  rcIpPolicyAddrListPolicyIdList OCTET STRING (SIZE(256)),
                  rcIpPolicyAddrListRowStatus RowStatus
                  }

rcIpPolicyAddrListId OBJECT-TYPE
        SYNTAX        INTEGER (1..1000)
        MAX-ACCESS        read-only
        STATUS        current
        DESCRIPTION   "A value that uniquely identifies this list of 
                       rcIpPolicyAddrListEntry."
        ::= { rcIpPolicyAddrListEntry 1 }
 
rcIpPolicyAddrListName OBJECT-TYPE
        SYNTAX        DisplayString (SIZE (0..15))
        MAX-ACCESS        read-write
        STATUS        current
        DESCRIPTION   "An administratively-assigned name for this list."
        ::= { rcIpPolicyAddrListEntry 3 }
 
rcIpPolicyAddrListIdListSize OBJECT-TYPE
        SYNTAX        INTEGER (0..128)
        MAX-ACCESS        read-only
        STATUS        current
        DESCRIPTION   "Used to indicate the number of rcIpPolicyAddrNetEntry 
                      id(s) in the rcIpPolicyAddrListIdList variable."
        ::= { rcIpPolicyAddrListEntry 4 }
 
rcIpPolicyAddrListIdList OBJECT-TYPE
        SYNTAX        OCTET STRING (SIZE(256))
        MAX-ACCESS        read-write
        STATUS        current
        DESCRIPTION   "Used to indicate zero or more AddrListId  that
                      are associated to this list.  Each AddrList identifier
                      is stored as two bytes in this array starting from
                      offset zero.  Any unused bytes should be set to zero."
        ::= { rcIpPolicyAddrListEntry 5 }

rcIpPolicyAddrListPolicyIdListSize OBJECT-TYPE
        SYNTAX        INTEGER (0..128)
        MAX-ACCESS        read-only
        STATUS        current
        DESCRIPTION   "Used to indicate the number of policy id(s) in the 
                      Policy Id list. That are referring to this list."
        ::= { rcIpPolicyAddrListEntry 6 }

rcIpPolicyAddrListPolicyIdList OBJECT-TYPE
        SYNTAX        OCTET STRING (SIZE(256))
        MAX-ACCESS        read-only
        STATUS        current
        DESCRIPTION   "Used to indicate zero or more policies  that
                      are referring to this entry.  Each policy identifier
                      is stored as two bytes in this array starting from
                      offset zero.  Any unused bytes should be set to zero."
        ::= { rcIpPolicyAddrListEntry 7 }


rcIpPolicyAddrListRowStatus OBJECT-TYPE
        SYNTAX          RowStatus
        MAX-ACCESS          read-write
        STATUS          current
        DESCRIPTION     "Row status of this entry."
        ::= { rcIpPolicyAddrListEntry 8 }
 

-- RIP Announce Policy Table

rcIpPolicyRipAnnounceTableSize OBJECT-TYPE
        SYNTAX        Integer32
        MAX-ACCESS        read-only
        STATUS        current
        DESCRIPTION   "Used to indicate the number of entries in the
                      rcIpPolicyRipAnnounceTable."
        ::= { rcIpPolicy 7 }

rcIpPolicyRipAnnounceTable OBJECT-TYPE
        SYNTAX        SEQUENCE OF RcIpPolicyRipAnnounceEntry
        MAX-ACCESS        not-accessible
        STATUS        current
        DESCRIPTION   "A table used to store set of announce policies 
		      configured for RIP routing protocol. The Number
                      of entries is given by rcIpPolicyNumRipPolicies."
        ::= { rcIpPolicy 8 }

rcIpPolicyRipAnnounceEntry OBJECT-TYPE
        SYNTAX        RcIpPolicyRipAnnounceEntry
        MAX-ACCESS        not-accessible
        STATUS        current
        DESCRIPTION   "Entry containing configuration information for a 
                      particular announce policy."
        INDEX         { rcIpPolicyRipAnnounceId }
        ::= { rcIpPolicyRipAnnounceTable 1 }

RcIpPolicyRipAnnounceEntry ::= SEQUENCE {
                rcIpPolicyRipAnnounceId INTEGER (1..1000),
                rcIpPolicyRipAnnounceName DisplayString (SIZE(0..15)),
                rcIpPolicyRipAnnounceEnable TruthValue,
		rcIpPolicyRipAnnounceExactNetListId INTEGER (0..1000),
		rcIpPolicyRipAnnounceRangeNetListId INTEGER (0..1000),
		rcIpPolicyRipAnnounceRipGatewayListId INTEGER (0..1000),
		rcIpPolicyRipAnnounceRipInterfaceListId INTEGER (0..1000),
		rcIpPolicyRipAnnounceOspfRouterListId INTEGER (0..1000),
		rcIpPolicyRipAnnounceAnnounceInterfaceListId INTEGER (0..1000),
                rcIpPolicyRipAnnouncePrecedence INTEGER,
                rcIpPolicyRipAnnounceRouteSource INTEGER,
		rcIpPolicyRipAnnounceAdvertiseNetListId INTEGER (0..1000),
                rcIpPolicyRipAnnounceAction INTEGER,
                rcIpPolicyRipAnnounceOspfRouteType INTEGER,
                rcIpPolicyRipAnnounceRipMetric INTEGER (0..15),
                rcIpPolicyRipAnnounceRowStatus RowStatus 
                }

rcIpPolicyRipAnnounceId OBJECT-TYPE
        SYNTAX        INTEGER (1..1000)
        MAX-ACCESS        read-only
        STATUS        current
        DESCRIPTION   "A value that uniquely identifies the policy
                      associated with this entry."
        ::= { rcIpPolicyRipAnnounceEntry 1 }

rcIpPolicyRipAnnounceName OBJECT-TYPE
        SYNTAX        DisplayString (SIZE (0..15))
        MAX-ACCESS        read-write
        STATUS        current
        DESCRIPTION   "An administratively-assigned name for this policy."
        ::= { rcIpPolicyRipAnnounceEntry 2 }

rcIpPolicyRipAnnounceEnable OBJECT-TYPE
        SYNTAX        TruthValue 
        MAX-ACCESS        read-write
        STATUS        current
        DESCRIPTION   "It indicates whether this policy is enabled or not.
                      The policy should be applied only if it is set to 'true'."
	DEFVAL        { true }
        ::= { rcIpPolicyRipAnnounceEntry 3 }

rcIpPolicyRipAnnounceExactNetListId OBJECT-TYPE
        SYNTAX        INTEGER (0..1000)
        MAX-ACCESS        read-write
        STATUS        current
        DESCRIPTION   "Used to indicate the number of 'exact' type entries
                      that are configured for this policy.

 		      An entry with type 'exactNet' or 'rangeNet' represents
                      the network list.  This indicates which networks will
                      match a particular announce policy. 
 
                      An entry with a 'exact' type means to only match the
                      specific network advertisement (netaddr & mask).

                      An 'exact' entry with addr=0.0.0.0 and mask=0.0.0.0
                      means 'match the default route'.

                      If set to '0', this policy applies to all the routes."

        ::= { rcIpPolicyRipAnnounceEntry 4 }

rcIpPolicyRipAnnounceRangeNetListId OBJECT-TYPE
        SYNTAX        INTEGER (0..1000)
        MAX-ACCESS        read-write
        STATUS        current
        DESCRIPTION   "Used to indicate zero or more 'range' network entries  
                      that are associated with this policy.  

                      An entry with a 'range' type means to match any network
		      number that falls in the range indicated by the addr &
                      mask.

                      A 'range' entry with addr=0.0.0.0 and mask=0.0.0.0
                      means 'match any route'.

                      If set to '0', this policy applies to all the routes."

        ::= { rcIpPolicyRipAnnounceEntry 5 }

rcIpPolicyRipAnnounceRipGatewayListId OBJECT-TYPE
        SYNTAX        INTEGER (0..1000)
        MAX-ACCESS        read-write
        STATUS        current
        DESCRIPTION   "Used to identify the RIP-gatewayList in the list 
                      that are associated with this policy. 

                      This field has meaning only for RIP sourced routes and 
                      if RIP is included as a RouteSource. 
                      The list contains one or more rip-routers (other side
                      of the interface) addresses that could send RIP updates 
                      to this router.  If a router 
                      address is included in this list, this policy applies to 
                      RIP advertisements from that router.
 
                      If set to '0', this policy applies to RIP updates
                      received from any rip routers/interfaces."
 
        ::= { rcIpPolicyRipAnnounceEntry 6 }

rcIpPolicyRipAnnounceRipInterfaceListId OBJECT-TYPE
        SYNTAX        INTEGER (0..1000)
        MAX-ACCESS        read-write
        STATUS        current
        DESCRIPTION   "Used to indicate the number of entries in the 
                      ripInterfaceIdList that are configured for this policy.

                      This field has meaning only for RIP sourced routes and
                      if RIP is included as a RouteSource. The list contains 
                      one or more rip-interface addresses on this router.
                      If an interface address is incuded in this list, this
                      policy applies to RIP advertisements received on that
                      interface.

                      A value of '0' indicates thtat this policy applies to
                      RIP updates received on any rip-interface."

        ::= { rcIpPolicyRipAnnounceEntry 7 }

rcIpPolicyRipAnnounceOspfRouterListId OBJECT-TYPE
        SYNTAX        INTEGER (0..1000) 
        MAX-ACCESS        read-write
        STATUS        current
        DESCRIPTION   "Used to indicate the number of entries in the 
                      OspfRouteIds that are configured for this policy.

                      This field has meaning only for OSPF sourced routes and
                      if OSPF is included as a RouteSource. The list contains
                      one or more router IDs of OSPF routers. If a routerId 
                      is included in this list, this policy applies to
                      OSPF advertisements received from that router.

                      A value of '0' indicates that this policy applies to
                      any OPSF routes received from any router."

        ::= { rcIpPolicyRipAnnounceEntry 8 }

rcIpPolicyRipAnnounceAnnounceInterfaceListId OBJECT-TYPE
        SYNTAX        INTEGER (0..1000)
        MAX-ACCESS        read-write
        STATUS        current
        DESCRIPTION   "Used to indicate the number of entries in the 
                      AnnounceInterfaceids that are configured for this policy.

                      The list contains one or more outbound interface 
                      addresses. If the outbound interface address in this
                      list, the policy applies to RIP updates/advertisements
                      sent through this  interface. 

                      A value of '0' indicates that this policy applies to
                      any outbound RIP interface on this router."

        ::= { rcIpPolicyRipAnnounceEntry 9 }

rcIpPolicyRipAnnouncePrecedence OBJECT-TYPE
        SYNTAX        INTEGER (0..65535) 
        MAX-ACCESS        read-write
        STATUS        current
        DESCRIPTION   "Is used while comparing this policy rule with other 
                      policy that a given route may match.  A rule with a 
                      higher precedence value will be chosen over one with 
                      a smaller value. In the case of a tie, the PolicyId is 
                      used (larger wins)."
        ::= { rcIpPolicyRipAnnounceEntry 10 }

rcIpPolicyRipAnnounceRouteSource OBJECT-TYPE
        SYNTAX        INTEGER {
			 direct(1),
			 static(2),
			 rip(4),
			 ospf(8),
			 any(15) 
		      }
        MAX-ACCESS        read-write
        STATUS        current
        DESCRIPTION   "Is represented as bitset to indicate route sources. 
                      It can contain one or more route sources. If the route 
                      source is in this bit map, then a route from that source 
                      that meets the other criteria of this policy will match 
                      the policy."
        DEFVAL        { any }
        ::= { rcIpPolicyRipAnnounceEntry 11 }

rcIpPolicyRipAnnounceAdvertiseNetListId OBJECT-TYPE 
        SYNTAX        INTEGER (0..1000)
        MAX-ACCESS        read-write
        STATUS        current
        DESCRIPTION   "Used to indicate the number of entries in the
                      AdvertiseNetList that are configured for this policy.

                      This has meaning only if the Action is set to 'announce'.
                      It is useful to send or advertise networks that differ 
                      from actual network in the routing table. Also allows 
                      advertisement of an aggregate or default along with the 
                      actual network.  Aggregation is useful if a number of
                      routes in the table falls in a certain range. Can save
                      space by sending aggregate route instead of the individual
                      routes. 
    
                      Actual network/route is included in the update
                      only if there is a match or there there is an entry
                      (address & mask pair) 255.255.255.255/255.255.255.255   
                      in the list."

        ::= { rcIpPolicyRipAnnounceEntry 12 }

rcIpPolicyRipAnnounceAction OBJECT-TYPE
        SYNTAX        INTEGER {
			 announce(1),
			 ignore(2)
		      }
        MAX-ACCESS        read-write
        STATUS        current
        DESCRIPTION   "It indicates whether the route should be announced 
                      or not."
        DEFVAL  { ignore }
        ::= { rcIpPolicyRipAnnounceEntry 13 }

rcIpPolicyRipAnnounceOspfRouteType OBJECT-TYPE
        SYNTAX        INTEGER {
			 type1(1),
                         type2(2),
                         external(3),
                         internal(4),
                         any(5)
                      }
        MAX-ACCESS        read-write
        STATUS        current
        DESCRIPTION   "Ospf Route type. It applies to OSPF sourced routes only.
		      'type1' means to apply this policy to only type1 OSPF 
                      external routes. 'type2' means to apply this policy to 
                      only type2 OSPF external routes. 'internal' means 'match 
                      ospf specfic routes'. 'any' means apply this policy to 
                      all OSPF external routes."		
         DEFVAL  { any }
        ::= { rcIpPolicyRipAnnounceEntry 14 }

rcIpPolicyRipAnnounceRipMetric OBJECT-TYPE
        SYNTAX        INTEGER (0..15)
        MAX-ACCESS        read-write
        STATUS        current
        DESCRIPTION   "RIP metric. The value is meaningful only if the action 
                      is set to 'announce'. This is optional export metric 
                      to use when advertising a route that matches this policy.
                      If set to zero, the routing table metric calculated for 
                      RIP is is used."
        DEFVAL        {0}
        ::= { rcIpPolicyRipAnnounceEntry 15 }

rcIpPolicyRipAnnounceRowStatus OBJECT-TYPE
        SYNTAX		RowStatus
        MAX-ACCESS		read-write
        STATUS		current
        DESCRIPTION	"Row status of this entry."
        ::= { rcIpPolicyRipAnnounceEntry 16 }

-- OSPF Announce policy table.

rcIpPolicyOspfAnnounceTableSize OBJECT-TYPE
        SYNTAX        Integer32
        MAX-ACCESS        read-only
        STATUS        current
        DESCRIPTION   "Used to indicate the number of entries in the
                      rcIpPolicyOspfAnnounceTable."
        ::= { rcIpPolicy 9 }


rcIpPolicyOspfAnnounceTable OBJECT-TYPE
        SYNTAX        SEQUENCE OF RcIpPolicyOspfAnnounceEntry
        MAX-ACCESS        not-accessible
        STATUS        current
        DESCRIPTION   "A table used to store set of announce policies 
		      configured for OSPF routing protocol. The Number
                      of entries is given by rcIpPolicyNumOspfPolicies."
        ::= { rcIpPolicy 10 }

rcIpPolicyOspfAnnounceEntry OBJECT-TYPE
        SYNTAX        RcIpPolicyOspfAnnounceEntry
        MAX-ACCESS        not-accessible
        STATUS        current
        DESCRIPTION   "Entry containing configuration information for a 
                      particular announce policy."
        INDEX         { rcIpPolicyOspfAnnounceId }
        ::= { rcIpPolicyOspfAnnounceTable 1 }

RcIpPolicyOspfAnnounceEntry ::= SEQUENCE {
                rcIpPolicyOspfAnnounceId INTEGER (2001..3000),
                rcIpPolicyOspfAnnounceName DisplayString (SIZE (0..15)),
                rcIpPolicyOspfAnnounceEnable TruthValue,
		rcIpPolicyOspfAnnounceExactNetListId INTEGER (0..1000),
		rcIpPolicyOspfAnnounceRangeNetListId INTEGER (0..1000),
		rcIpPolicyOspfAnnounceRipGatewayListId INTEGER (0..1000),
		rcIpPolicyOspfAnnounceRipInterfaceListId INTEGER (0..1000),
                rcIpPolicyOspfAnnouncePrecedence INTEGER,
                rcIpPolicyOspfAnnounceRouteSource INTEGER,
		rcIpPolicyOspfAnnounceAdvertiseNetListId INTEGER (0..1000),
                rcIpPolicyOspfAnnounceAction INTEGER,
                rcIpPolicyOspfAnnounceExtMetricType INTEGER,
                rcIpPolicyOspfAnnounceExtMetric INTEGER (0..65535),
                rcIpPolicyOspfAnnounceRowStatus RowStatus 
                }

rcIpPolicyOspfAnnounceId OBJECT-TYPE
        SYNTAX        INTEGER (2001..3000)
        MAX-ACCESS        read-only
        STATUS        current
        DESCRIPTION   "A value that uniquely identifies the policy
                      associated with this entry."
        ::= { rcIpPolicyOspfAnnounceEntry 1 }

rcIpPolicyOspfAnnounceName OBJECT-TYPE
        SYNTAX        DisplayString (SIZE (0..15))
        MAX-ACCESS        read-write
        STATUS        current
        DESCRIPTION   "An administratively-assigned name for this policy."
        ::= { rcIpPolicyOspfAnnounceEntry 2 }

rcIpPolicyOspfAnnounceEnable OBJECT-TYPE
        SYNTAX        TruthValue 
        MAX-ACCESS        read-write
        STATUS        current
        DESCRIPTION   "It indicates whether this policy is enabled or not.
                      The policy should be applied only if it is set to 
		      'true'."
	DEFVAL        { true }
        ::= { rcIpPolicyOspfAnnounceEntry 3 }

rcIpPolicyOspfAnnounceExactNetListId OBJECT-TYPE
        SYNTAX        INTEGER (0..1000)
        MAX-ACCESS        read-write
        STATUS        current
        DESCRIPTION   "Used to indicate the number of 'exact' type entries
                      that are configured for this policy.
 
                      An entry with type 'exactNet' or 'rangeNet' represents
                      the network list.  This indicates which networks will
                      match a particular announce policy.
 
                      An entry with a 'exact' type means to only match the
                      specific network advertisement (netaddr & mask).
 
                      An 'exact' entry with addr=0.0.0.0 and mask=0.0.0.0
                      means 'match the default route'.
 
                      If set to '0', this policy applies to all the routes."
 
        ::= { rcIpPolicyOspfAnnounceEntry 4 }

rcIpPolicyOspfAnnounceRangeNetListId OBJECT-TYPE
        SYNTAX        INTEGER (0..1000)
        MAX-ACCESS        read-write
        STATUS        current
        DESCRIPTION   "Used to indicate zero or more 'range' network entries
                      that are associated with this policy.
 
                      An entry with a 'range' type means to match any network
                      number that falls in the range indicated by the addr &
                      mask.
 
                      A 'range' entry with addr=0.0.0.0 and mask=0.0.0.0
                      means 'match any route'.
 
                      If set to '0', this policy applies to all the routes."

        ::= { rcIpPolicyOspfAnnounceEntry 5 }

rcIpPolicyOspfAnnounceRipGatewayListId OBJECT-TYPE
        SYNTAX        INTEGER (0..1000)
        MAX-ACCESS        read-write
        STATUS        current
        DESCRIPTION   "Used to identify the RIP-gatewayList in the list
                      that are associated with this policy.
 
                      This field has meaning only for RIP sourced routes and
                      if RIP is included as a RouteSource.
                      The list contains one or more rip-routers (other side
                      of the interface) addresses that could send RIP updates
                      to this router.  If a router
                      address is included in this list, this policy applies to
                      RIP advertisements from that router.
 
                      If set to '0', this policy applies to RIP updates
                      received from any rip routers/interfaces."

        ::= { rcIpPolicyOspfAnnounceEntry 6 }

rcIpPolicyOspfAnnounceRipInterfaceListId OBJECT-TYPE
        SYNTAX        INTEGER (0..1000)
        MAX-ACCESS        read-write
        STATUS        current
        DESCRIPTION   "Used to indicate the number of entries in the
                      ripInterfaceIdList that are configured for this policy.
 
                      This field has meaning only for RIP sourced routes and
                      if RIP is included as a RouteSource. The list contains
                      one or more rip-interface addresses on this router.
                      If an interface address is incuded in this list, this
                      policy applies to RIP advertisements received on that
                      interface.
 
                      A value of '0' indicates thtat this policy applies to
                      RIP updates received on any rip-interface."

        ::= { rcIpPolicyOspfAnnounceEntry 7 }


rcIpPolicyOspfAnnouncePrecedence OBJECT-TYPE
        SYNTAX        INTEGER (0..65535) 
        MAX-ACCESS        read-write
        STATUS        current
        DESCRIPTION   "Is used while comparing this policy rule with other 
                      policy that a given route may match.  A rule with a 
                      higher precedence value will be chosen over one with 
                      a smaller value. In the case of a tie, the PolicyId is 
                      used (larger wins)."
        ::= { rcIpPolicyOspfAnnounceEntry 8 }

rcIpPolicyOspfAnnounceRouteSource OBJECT-TYPE
        SYNTAX        INTEGER {
			 direct(1),
			 static(2),
			 rip(4),
			 any(7) 
		      }
        MAX-ACCESS        read-write
        STATUS        current
        DESCRIPTION   "Is represented as bit map to indicate route sources. 
                      It can contain one or more route sources. If the route 
                      source is in this bit map, then a route from that source 
                      that meets the other criteria of this policy will match 
                      the policy."
        DEFVAL        { any }
        ::= { rcIpPolicyOspfAnnounceEntry 9 }

rcIpPolicyOspfAnnounceAdvertiseNetListId OBJECT-TYPE 
        SYNTAX        INTEGER (0..1000)
        MAX-ACCESS        read-write
        STATUS        current
        DESCRIPTION   "Used to indicate the number of entries in the
                      AdvertiseNetList that are configured for this policy.
 
                      This has meaning only if the Action is set to 'announce'.
                      It is useful to send or advertise networks that differ
                      from actual network in the routing table. Also allows
                      advertisement of an aggregate or default along with the
                      actual network.  Aggregation is useful if a number of
                      routes in the table falls in a certain range. Can save
                      space by sending aggregate route instead of the individual
                      routes.
 
                      Actual network/route is included in the update
                      only if there is a match or there there is an entry
                      (address & mask pair) 255.255.255.255/255.255.255.255
                      in the list."

        ::= { rcIpPolicyOspfAnnounceEntry 10 }

rcIpPolicyOspfAnnounceAction OBJECT-TYPE
        SYNTAX        INTEGER {
			 announce(1),
			 ignore(2)
		      }
        MAX-ACCESS        read-write
        STATUS        current
        DESCRIPTION   "It indicates whether the route should be announced 
                      or not."
         DEFVAL  { ignore }
        ::= { rcIpPolicyOspfAnnounceEntry 11 }

rcIpPolicyOspfAnnounceExtMetricType OBJECT-TYPE
        SYNTAX        INTEGER {
			 type1(1),
                         type2(2)
                      }
        MAX-ACCESS        read-write
        STATUS        current
        DESCRIPTION   "Ospf External metric type. It is used to indicate
		      what type of the external metric it is. 'type1' means to 
                      the cost is 'internal ospf cost + ExtMetric'. 
                      'type2' means the ospf-metric is equal to 'type2'."
         DEFVAL  { type2 }
        ::= { rcIpPolicyOspfAnnounceEntry 12 }

rcIpPolicyOspfAnnounceExtMetric OBJECT-TYPE
        SYNTAX        INTEGER (0..65535)
        MAX-ACCESS        read-write
        STATUS        current
        DESCRIPTION   "OSPF External metric. The value is meaningful only if 
                      the action is set to 'announce'. This is optional export 
                      metric to use when advertising a route that matches this 
                      policy. Value '0' is used to indicate that route's actual
                      cost is used to announce."
        DEFVAL        { 0 }
        ::= { rcIpPolicyOspfAnnounceEntry 13 }

rcIpPolicyOspfAnnounceRowStatus OBJECT-TYPE
        SYNTAX		RowStatus
        MAX-ACCESS		read-write
        STATUS		current
        DESCRIPTION	"Row status of this entry."
        ::= { rcIpPolicyOspfAnnounceEntry 14 }
 
-- IP Accept Policy Groups

-- RIP Accept policy table.

rcIpPolicyRipAcceptTableSize OBJECT-TYPE
        SYNTAX        Integer32
        MAX-ACCESS        read-only
        STATUS        current
        DESCRIPTION   "Used to indicate the number of entries in the
                      rcIpPolicyRipAcceptTable."
        ::= { rcIpPolicy 11 }

rcIpPolicyRipAcceptTable OBJECT-TYPE
        SYNTAX        SEQUENCE OF RcIpPolicyRipAcceptEntry
        MAX-ACCESS        not-accessible
        STATUS        current
        DESCRIPTION   "A table used to store set of accept policies 
		      configured for RIP routing protocol. The Number
                      of entries is given by rcIpPolicyNumRipPolicies."
        ::= { rcIpPolicy 12 }

rcIpPolicyRipAcceptEntry OBJECT-TYPE
        SYNTAX        RcIpPolicyRipAcceptEntry
        MAX-ACCESS        not-accessible
        STATUS        current
        DESCRIPTION   "Entry containing configuration information for a 
                      particular accept policy."
        INDEX         { rcIpPolicyRipAcceptId }
        ::= { rcIpPolicyRipAcceptTable 1 }

RcIpPolicyRipAcceptEntry ::= SEQUENCE {
                rcIpPolicyRipAcceptId INTEGER (4001..5000),
                rcIpPolicyRipAcceptName DisplayString (SIZE(0..15)),
                rcIpPolicyRipAcceptEnable TruthValue,
		rcIpPolicyRipAcceptExactNetListId INTEGER (0..1000),
		rcIpPolicyRipAcceptRangeNetListId INTEGER (0..1000),
		rcIpPolicyRipAcceptRipGatewayListId INTEGER (0..1000),
		rcIpPolicyRipAcceptRipInterfaceListId INTEGER (0..1000),
                rcIpPolicyRipAcceptPrecedence INTEGER,
                rcIpPolicyRipAcceptAction INTEGER,
		rcIpPolicyRipAcceptInjectNetListId INTEGER (0..1000),
                rcIpPolicyRipAcceptApplyMask IpAddress,
                rcIpPolicyRipAcceptRowStatus RowStatus 
                }

rcIpPolicyRipAcceptId OBJECT-TYPE
        SYNTAX        INTEGER (4001..5000)
        MAX-ACCESS        read-only
        STATUS        current
        DESCRIPTION   "A value that uniquely identifies the policy
                      associated with this entry."
        ::= { rcIpPolicyRipAcceptEntry 1 }

rcIpPolicyRipAcceptName OBJECT-TYPE
        SYNTAX        DisplayString (SIZE (0..15))
        MAX-ACCESS        read-write
        STATUS        current
        DESCRIPTION   "An administratively-assigned name for this policy."
        ::= { rcIpPolicyRipAcceptEntry 2 }

rcIpPolicyRipAcceptEnable OBJECT-TYPE
        SYNTAX        TruthValue 
        MAX-ACCESS        read-write
        STATUS        current
        DESCRIPTION   "It indicates whether this policy is enabled or not.
                      The policy should be applied only if it is set to 'true'."
	DEFVAL        { true }
        ::= { rcIpPolicyRipAcceptEntry 3 }

rcIpPolicyRipAcceptExactNetListId OBJECT-TYPE
        SYNTAX        INTEGER (0..1000)
        MAX-ACCESS        read-write
        STATUS        current
        DESCRIPTION   "Used to indicate the number of 'exact' type entries
                      that are configured for this policy.

 		      An entry with type 'exactNet' or 'rangeNet' represents
                      the network list.  This indicates which networks will
                      match a particular accept policy. 
 
                      An entry with a 'exact' type means to only match the
                      specific network advertisement (netaddr & mask).

                      An 'exact' entry with addr=0.0.0.0 and mask=0.0.0.0
                      means 'match the default route'."
        ::= { rcIpPolicyRipAcceptEntry 4 }

rcIpPolicyRipAcceptRangeNetListId OBJECT-TYPE
        SYNTAX        INTEGER (0..1000)
        MAX-ACCESS        read-write
        STATUS        current
        DESCRIPTION   "Used to indicate zero or more 'range' network entries  
                      that are associated with this policy.  

                      An entry with a 'range' type means to match any network
		      number that falls in the range indicated by the addr &
                      mask.

                      A 'range' entry with addr=0.0.0.0 and mask=0.0.0.0
                      means 'match any route'.

                      A null list means 'match any route'."
        ::= { rcIpPolicyRipAcceptEntry 5 }

rcIpPolicyRipAcceptRipGatewayListId OBJECT-TYPE
        SYNTAX        INTEGER (0..1000)
        MAX-ACCESS        read-write
        STATUS        current
        DESCRIPTION   "Used to identify the RIP-gatewayList in the 
                      PolicyListTable that iares associated with this 
                      policy. The list contains the addresses of one or more 
                      routers that could send RIP updates to this router.
                      If a router address is included in this list, this
                      policy applies to RIP advertisements from that router.
 
                      If set to '0', this policy applies to RIP updates
                      from any router."

        ::= { rcIpPolicyRipAcceptEntry 6 }

rcIpPolicyRipAcceptRipInterfaceListId OBJECT-TYPE
        SYNTAX        INTEGER (0..1000)
        MAX-ACCESS        read-write
        STATUS        current
        DESCRIPTION   "Used to indicate ListId defined for RipInterfaceList
                      in the rcIpPolicyListTable that is assiciated 
                      with this policy. 
                      The list contains the addresses of one or more interfaces
                      on this router.  If an interface address is included in 
                      the list, this policy applies to RIP advertisements 
                      received on that interface.
 
                      If set to '0', this policy applies to RIP updates
                      received on any interface."

        ::= { rcIpPolicyRipAcceptEntry 7 }

rcIpPolicyRipAcceptPrecedence OBJECT-TYPE
        SYNTAX        INTEGER (0..65535) 
        MAX-ACCESS        read-write
        STATUS        current
        DESCRIPTION   "Is used while comparing this policy rule with other 
                      policy that a given route may match.  A rule with a 
                      higher precedence value will be chosen over one with 
                      a smaller value. In the case of a tie, the PolicyId is 
                      used (larger wins)."
        ::= { rcIpPolicyRipAcceptEntry 8 }

rcIpPolicyRipAcceptAction OBJECT-TYPE
        SYNTAX        INTEGER {
			 accept(1),
			 ignore(2)
		      }
        MAX-ACCESS        read-write
        STATUS        current
        DESCRIPTION   "It indicates whether the route should be acceptd 
                      or not."
         DEFVAL  { accept }
        ::= { rcIpPolicyRipAcceptEntry 9 }

rcIpPolicyRipAcceptInjectNetListId OBJECT-TYPE 
        SYNTAX        INTEGER (0..1000)
        MAX-ACCESS        read-write
        STATUS        current
        DESCRIPTION   "Used to indicate the ListId of the InjectNetList
                      in the rcIpPolicyListTable entry that is assiciated
                      with for this policy. If teh action is 'accept' and if it
                      is desired to insert networks into the routing table that
                      differ from the actual advertised network. For instance,
                      if a number of networks in a certain range are learned
                      and an aggregate advertisement could be inserted instead
                      of the individual networks. 

                      Upon receiving a route that matches this policy, all
                      networks in this list will be considered for inclusion 
                      in the routing table. If the list is empty or if the
                      value of the ListId is '0' then the actual received
                      network is considered.

                      An encoding of 255.255.255.255/255.255.255.255 means
                      'match the actual received network.'. This allows
                      insertion of an aggregate or default along with the 
                      actual netowrk."
        ::= { rcIpPolicyRipAcceptEntry 10 }

rcIpPolicyRipAcceptApplyMask OBJECT-TYPE
        SYNTAX		IpAddress
        MAX-ACCESS		read-write
        STATUS		current
        DESCRIPTION	"If the 'action' is set to 'accept' and the actual
                        received network will be considered, this is an
                        optional IP address mask that will be applied to the 
                        network number from the RIP update.  This is used to 
                        override the interface's subnet mask in the presence 
                        of networks with variable length subnet masks."
        ::= { rcIpPolicyRipAcceptEntry 11 }

rcIpPolicyRipAcceptRowStatus OBJECT-TYPE
        SYNTAX		RowStatus
        MAX-ACCESS		read-write
        STATUS		current
        DESCRIPTION	"Row status of this entry."
        ::= { rcIpPolicyRipAcceptEntry 12 }

-- OSPF Accept policy table.
 
rcIpPolicyOspfAcceptTableSize OBJECT-TYPE
        SYNTAX        Integer32
        MAX-ACCESS        read-only
        STATUS        current
        DESCRIPTION   "Used to indicate the number of entries in the
                      rcIpPolicyOspfAcceptTable."
        ::= { rcIpPolicy 13 }

rcIpPolicyOspfAcceptTable OBJECT-TYPE
        SYNTAX        SEQUENCE OF RcIpPolicyOspfAcceptEntry
        MAX-ACCESS        not-accessible
        STATUS        current
        DESCRIPTION   "A table used to store set of accept policies 
		      configured for RIP routing protocol. The Number
                      of entries is given by rcIpPolicyNumRipPolicies."
        ::= { rcIpPolicy 14 }

rcIpPolicyOspfAcceptEntry OBJECT-TYPE
        SYNTAX        RcIpPolicyOspfAcceptEntry
        MAX-ACCESS        not-accessible
        STATUS        current
        DESCRIPTION   "Entry containing configuration information for a 
                      particular accept policy."
        INDEX         { rcIpPolicyOspfAcceptId }
        ::= { rcIpPolicyOspfAcceptTable 1 }

RcIpPolicyOspfAcceptEntry ::= SEQUENCE {
                rcIpPolicyOspfAcceptId INTEGER (6001..7000),
                rcIpPolicyOspfAcceptName DisplayString (SIZE(0..15)),
                rcIpPolicyOspfAcceptEnable TruthValue,
		rcIpPolicyOspfAcceptExactNetListId INTEGER (0..1000),
		rcIpPolicyOspfAcceptRangeNetListId INTEGER (0..1000),
                rcIpPolicyOspfAcceptPrecedence INTEGER,
                rcIpPolicyOspfAcceptAction INTEGER,
		rcIpPolicyOspfAcceptInjectNetListId INTEGER (0..1000),
                rcIpPolicyOspfAcceptExtType INTEGER,
                rcIpPolicyOspfAcceptRowStatus RowStatus 
                }

rcIpPolicyOspfAcceptId OBJECT-TYPE
        SYNTAX        INTEGER (6001..7000)
        MAX-ACCESS        read-only
        STATUS        current
        DESCRIPTION   "A value that uniquely identifies the policy
                      associated with this entry."
        ::= { rcIpPolicyOspfAcceptEntry 1 }

rcIpPolicyOspfAcceptName OBJECT-TYPE
        SYNTAX        DisplayString (SIZE (0..15))
        MAX-ACCESS        read-write
        STATUS        current
        DESCRIPTION   "An administratively-assigned name for this policy."
        ::= { rcIpPolicyOspfAcceptEntry 2 }

rcIpPolicyOspfAcceptEnable OBJECT-TYPE
        SYNTAX        TruthValue 
        MAX-ACCESS        read-write
        STATUS        current
        DESCRIPTION   "It indicates whether this policy is enabled or not.
                      The policy should be applied only if it is set to 'true'."
	DEFVAL        { true }
        ::= { rcIpPolicyOspfAcceptEntry 3 }

rcIpPolicyOspfAcceptExactNetListId OBJECT-TYPE
        SYNTAX        INTEGER (0..1000)
        MAX-ACCESS        read-write
        STATUS        current
        DESCRIPTION   "Used to indicate the number of 'exact' type entries
                      that are configured for this policy.

 		      An entry with type 'exactNet' or 'rangeNet' represents
                      the network list.  This indicates which networks will
                      match a particular accept policy. 
 
                      An entry with a 'exact' type means to only match the
                      specific network advertisement (netaddr & mask).

                      An 'exact' entry with addr=0.0.0.0 and mask=0.0.0.0
                      means 'match the default route'."
        ::= { rcIpPolicyOspfAcceptEntry 4 }

rcIpPolicyOspfAcceptRangeNetListId OBJECT-TYPE
        SYNTAX        INTEGER (0..1000)
        MAX-ACCESS        read-write
        STATUS        current
        DESCRIPTION   "Used to indicate zero or more 'range' network entries  
                      that are associated with this policy.  

                      An entry with a 'range' type means to match any network
		      number that falls in the range indicated by the addr &
                      mask.

                      A 'range' entry with addr=0.0.0.0 and mask=0.0.0.0
                      means 'match any route'.

                      A null list means 'match any route'."
        ::= { rcIpPolicyOspfAcceptEntry 5 }

rcIpPolicyOspfAcceptPrecedence OBJECT-TYPE
        SYNTAX        INTEGER (0..65535) 
        MAX-ACCESS        read-write
        STATUS        current
        DESCRIPTION   "Is used while comparing this policy rule with other 
                      policy that a given route may match.  A rule with a 
                      higher precedence value will be chosen over one with 
                      a smaller value. In the case of a tie, the PolicyId is 
                      used (larger wins)."
        ::= { rcIpPolicyOspfAcceptEntry 6 }

rcIpPolicyOspfAcceptAction OBJECT-TYPE
        SYNTAX        INTEGER {
			 accept(1),
			 ignore(2)
		      }
        MAX-ACCESS        read-write
        STATUS        current
        DESCRIPTION   "It indicates whether the route should be acceptd 
                      or not."
         DEFVAL  { accept }
        ::= { rcIpPolicyOspfAcceptEntry 7 }

rcIpPolicyOspfAcceptInjectNetListId OBJECT-TYPE 
        SYNTAX        INTEGER (0..1000)
        MAX-ACCESS        read-write
        STATUS        current
        DESCRIPTION   "Used to indicate the ListId of the InjectNetList
                      in the rcIpPolicyListTable entry that is assiciated
                      with for this policy. If teh action is 'accept' and if it
                      is desired to insert networks into the routing table that
                      differ from the actual advertised network. For instance,
                      if a number of networks in a certain range are learned
                      and an aggregate advertisement could be inserted instead
                      of the individual networks. 

                      Upon receiving a route that matches this policy, all
                      networks in this list will be considered for inclusion 
                      in the routing table. If the list is empty or if the
                      value of the ListId is '0' then the actual received
                      network is considered.

                      An encoding of 255.255.255.255/255.255.255.255 means
                      'match the actual received network.'. This allows
                      insertion of an aggregate or default along with the 
                      actual netowrk."
        ::= { rcIpPolicyOspfAcceptEntry 8 }

rcIpPolicyOspfAcceptExtType OBJECT-TYPE
        SYNTAX		INTEGER {
                           type1(1),
                           type2(2),
                           any(3)
                        }

        MAX-ACCESS		read-write
        STATUS		current
        DESCRIPTION     "Used to indicate the ospf external type. This 
                        parameter describes which types of OSPF ASE routes
                        match this policy. 
                        'any' means 'match either ASE type 1 or 2'.	
                        'type1' means 'match any external type 1'.
                        'type2' means 'match any external type 2"
        ::= { rcIpPolicyOspfAcceptEntry 9 }

rcIpPolicyOspfAcceptRowStatus OBJECT-TYPE
        SYNTAX		RowStatus
        MAX-ACCESS		read-write
        STATUS		current
        DESCRIPTION	"Row status of this entry."
        ::= { rcIpPolicyOspfAcceptEntry 10 }


-- IP Policy Network List Table

rcIpPolicyNetListTableSize OBJECT-TYPE
        SYNTAX        Integer32
        MAX-ACCESS        read-only
        STATUS        current
        DESCRIPTION   "Used to indicate the number of entries in the
                      rcIpPolicyNetListTable."
        ::= { rcIpPolicy 15 }
 
rcIpPolicyNetListTable OBJECT-TYPE
        SYNTAX        SEQUENCE OF RcIpPolicyNetListEntry
        MAX-ACCESS        not-accessible
        STATUS        current
        DESCRIPTION   "A table used to group rcIpPolicyAddrEntry(s) 
                      into a list."
        ::= { rcIpPolicy 16 }

rcIpPolicyNetListEntry OBJECT-TYPE
        SYNTAX        RcIpPolicyNetListEntry
        MAX-ACCESS        not-accessible
        STATUS        current
        DESCRIPTION   "Route entry attributes."
        INDEX         { rcIpPolicyNetListId }
        ::= { rcIpPolicyNetListTable 1 }
 
RcIpPolicyNetListEntry ::= SEQUENCE {
                  rcIpPolicyNetListId INTEGER (1..1000),
                  rcIpPolicyNetListName DisplayString (SIZE(0..15)),
                  rcIpPolicyNetListIdListSize INTEGER (0..128),
                  rcIpPolicyNetListIdList OCTET STRING (SIZE(256)),
                  rcIpPolicyNetListPolicyIdListSize INTEGER (0..128),
                  rcIpPolicyNetListPolicyIdList OCTET STRING (SIZE(256)),
                  rcIpPolicyNetListRowStatus RowStatus
                  }

rcIpPolicyNetListId OBJECT-TYPE
        SYNTAX        INTEGER (1..1000)
        MAX-ACCESS        read-only
        STATUS        current
        DESCRIPTION   "A value that uniquely identifies this list of 
                       rcIpPolicyNetListEntry."
        ::= { rcIpPolicyNetListEntry 1 }
 
rcIpPolicyNetListName OBJECT-TYPE
        SYNTAX        DisplayString (SIZE (0..15))
        MAX-ACCESS        read-write
        STATUS        current
        DESCRIPTION   "An administratively-assigned name for this list."
        ::= { rcIpPolicyNetListEntry 3 }
 
rcIpPolicyNetListIdListSize OBJECT-TYPE
        SYNTAX        INTEGER (0..128)
        MAX-ACCESS        read-only
        STATUS        current
        DESCRIPTION   "Used to indicate the number of rcIpPolicyNetEntry 
                      id(s) in the rcIpPolicyNetListIdList variable."
        ::= { rcIpPolicyNetListEntry 4 }
 
rcIpPolicyNetListIdList OBJECT-TYPE
        SYNTAX        OCTET STRING (SIZE(256))
        MAX-ACCESS        read-write
        STATUS        current
        DESCRIPTION   "Used to indicate zero or more NetListId  that
                      are associated to this list.  Each NetList identifier
                      is stored as two bytes in this array starting from
                      offset zero.  Any unused bytes should be set to zero."
        ::= { rcIpPolicyNetListEntry 5 }

rcIpPolicyNetListPolicyIdListSize OBJECT-TYPE
        SYNTAX        INTEGER (0..128)
        MAX-ACCESS        read-only
        STATUS        current
        DESCRIPTION   "Used to indicate the number of policy id(s) in the 
                      Policy Id list. That are referring to this list."
        ::= { rcIpPolicyNetListEntry 6 }

rcIpPolicyNetListPolicyIdList OBJECT-TYPE
        SYNTAX        OCTET STRING (SIZE(256))
        MAX-ACCESS        read-only
        STATUS        current
        DESCRIPTION   "Used to indicate zero or more policies  that
                      are referring to this entry.  Each policy identifier
                      is stored as two bytes in this array starting from
                      offset zero.  Any unused bytes should be set to zero."
        ::= { rcIpPolicyNetListEntry 7 }

rcIpPolicyNetListRowStatus OBJECT-TYPE
        SYNTAX          RowStatus
        MAX-ACCESS          read-write
        STATUS          current
        DESCRIPTION     "Row status of this entry."
        ::= { rcIpPolicyNetListEntry 8 }

 
-- DVMRP Group Extension
 
rcIpDvmrp OBJECT IDENTIFIER ::= { rcIp 12 }
 
rcIpDvmrpGlobal   OBJECT IDENTIFIER       ::= { rcIpDvmrp 1 }

rcIpDvmrpGlobalEnable OBJECT-TYPE
        SYNTAX        TruthValue
        MAX-ACCESS        read-write
        STATUS        current
        DESCRIPTION   "The enabled status of IP Multicast Dvmrp routing
                      on this router."
        ::= { rcIpDvmrpGlobal 1 }

rcIpDvmrpGlobalUpdateInterval OBJECT-TYPE
        SYNTAX         INTEGER (10..2000)
        MAX-ACCESS         read-write
        STATUS         current
        DESCRIPTION    "Route upd interval"
            DEFVAL         { 60 }
        ::= { rcIpDvmrpGlobal 2 }
 
rcIpDvmrpGlobalTriggeredUpdateInterval OBJECT-TYPE
        SYNTAX         INTEGER (5..1000)
        MAX-ACCESS         read-write
        STATUS         current
        DESCRIPTION    "Trigger upd interval"
            DEFVAL         { 5 }
        ::= { rcIpDvmrpGlobal 3 }
 
rcIpDvmrpGlobalLeafTimeOut OBJECT-TYPE
        SYNTAX         INTEGER (25..4000)
        MAX-ACCESS         read-write
        STATUS         current
        DESCRIPTION    "Hold down timer for leaf"
            DEFVAL         { 200 }
        ::= { rcIpDvmrpGlobal 4 }
 
rcIpDvmrpGlobalNbrTimeOut OBJECT-TYPE
        SYNTAX         INTEGER (35..8000)
        MAX-ACCESS         read-write
        STATUS         current
        DESCRIPTION    "Time to age out nbr"
            DEFVAL         { 140 }
        ::= { rcIpDvmrpGlobal 5 }
 
rcIpDvmrpGlobalNbrProbeInterval OBJECT-TYPE
        SYNTAX         INTEGER (5..30)
        MAX-ACCESS         read-write
        STATUS         current
        DESCRIPTION    "How often to send probe"
            DEFVAL         { 10 }
        ::= { rcIpDvmrpGlobal 6 }
 
-- rcIpDvmrpTable
 
rcIpDvmrpTable OBJECT-TYPE
        SYNTAX        SEQUENCE OF RcIpDvmrpTableEntry
        MAX-ACCESS        not-accessible
        STATUS        current
        DESCRIPTION   "Dvmrp Interface extension table.  This table
                      augments the standard dvmrpInterfaceTable defined
                      in <draft-thaler-dvmrp-mib-09.txt>."
        ::= { rcIpDvmrp 2 }
 
rcIpDvmrpTableEntry OBJECT-TYPE
        SYNTAX        RcIpDvmrpTableEntry
        MAX-ACCESS        not-accessible
        STATUS        current
        DESCRIPTION   "Entry containing Proprietary DVMRP interface
                      information.  An entry is automatically created
                      in this table when an ip address is configured on
                      an interface."
        INDEX         { rcIpDvmrpTableIfIndex }
        ::= { rcIpDvmrpTable 1 }
 
RcIpDvmrpTableEntry ::=
        SEQUENCE {
                rcIpDvmrpTableIfIndex InterfaceIndex,
                rcIpDvmrpTableEnable TruthValue,
                rcIpDvmrpTableMetric INTEGER
        }
 
rcIpDvmrpTableIfIndex OBJECT-TYPE
        SYNTAX        InterfaceIndex
        MAX-ACCESS        read-only
        STATUS        current
        DESCRIPTION   "The index value which uniquely identifies the
                      interface to which this entry is applicable.
                      The interface identified by a particular value
                      of this index is the same interface as
                      identified by the same value of ifIndex."
        ::= { rcIpDvmrpTableEntry 1 }
 
rcIpDvmrpTableEnable OBJECT-TYPE
        SYNTAX         TruthValue
        MAX-ACCESS         read-write
        STATUS         current
        DESCRIPTION
                "The administrative status of DVMRP in the router.  The
                value 'enabled' denotes that the DVMRP is enableed on
                the interface; 'disabled' disables it on the interface."
        ::= { rcIpDvmrpTableEntry 2 }

rcIpDvmrpTableMetric OBJECT-TYPE
        SYNTAX         INTEGER (1..31)
        MAX-ACCESS         read-write
        STATUS         current
        DESCRIPTION    "Dvmrp cost on this interface."
        ::= { rcIpDvmrpTableEntry 3 }


-- Ip UDP Protocol Table
 
rcIpUdp OBJECT IDENTIFIER ::= { rcIp 13 }

rcIpUdpProtocolTableSize OBJECT-TYPE
        SYNTAX        Integer32
        MAX-ACCESS        read-only
        STATUS        current
        DESCRIPTION   "Used to indicate the number of entries in the 
		      rcIpUdpProtocolTable."
        ::= { rcIpUdp 1 }

rcIpUdpProtocolTable OBJECT-TYPE 
        SYNTAX          SEQUENCE OF RcIpUdpProtocolEntry
        MAX-ACCESS          not-accessible 
        STATUS          current 
        DESCRIPTION     "list of UDP protocols. Used to determine whether to
                         forward the UDP broadcast packet or not."
    ::= { rcIpUdp 2 }

rcIpUdpProtocolEntry OBJECT-TYPE
        SYNTAX        	RcIpUdpProtocolEntry
        MAX-ACCESS        	not-accessible
        STATUS        	current
        DESCRIPTION   	"Used to include a particular UDP port in the table.  
		      	An entry in this table indicates that the box might do 
		      	forwarding of UDP broadcast packets if there is a 
                        matching entry for this packet in the 
                        rcIpUdpPortFwdTable."
        INDEX         	{ rcIpUdpProtocolPortNumber }
        ::= { rcIpUdpProtocolTable 1 }
 
RcIpUdpProtocolEntry ::=
        SEQUENCE {
                rcIpUdpProtocolPortNumber      INTEGER,
                rcIpUdpProtocolName    	       DisplayString,
                rcIpUdpProtocolRowStatus       RowStatus
        }
 
rcIpUdpProtocolPortNumber OBJECT-TYPE
        SYNTAX        	INTEGER (1..65535)
        MAX-ACCESS        	read-only
        STATUS        	current
        DESCRIPTION   	"well-known UDP Port number. Pre-assigned port
                         number for this protocol. Port used by the
                         server process as its contact port. It cannot 
                         be BOOTP/DHCP port#s 67, 68."
        ::= { rcIpUdpProtocolEntry 1 }
 
rcIpUdpProtocolName OBJECT-TYPE
        SYNTAX          DisplayString (SIZE(1..15))
        MAX-ACCESS        	read-write
        STATUS        	current
        DESCRIPTION   	"Used to indicate the name of the protocol 
		      	that is running on top of UDP protocol. 
                        cannot change the name once created. This 
                        should be set while creating the entry."  
        ::= { rcIpUdpProtocolEntry 2 }
 
rcIpUdpProtocolRowStatus OBJECT-TYPE
        SYNTAX        	RowStatus
        MAX-ACCESS        	read-write
        STATUS        	current
        DESCRIPTION   	"Rowstatus of this entry."
        ::= { rcIpUdpProtocolEntry 3 }


-- Ip Udp Port Forward Table

rcIpUdpPortFwdTableSize OBJECT-TYPE
        SYNTAX        Integer32
        MAX-ACCESS        read-only
        STATUS        current
        DESCRIPTION   "Used to indicate the number of entries in the
                      rcIpUdpPortFwdTable."
        ::= { rcIpUdp 3 }
 
rcIpUdpPortFwdTable OBJECT-TYPE 
        SYNTAX	      	SEQUENCE OF RcIpUdpPortFwdEntry
        MAX-ACCESS        	not-accessible 
        STATUS        	current 
        DESCRIPTION   	"Udp forward entry table."
    ::= { rcIpUdp 4 }

rcIpUdpPortFwdEntry OBJECT-TYPE
        SYNTAX        	RcIpUdpPortFwdEntry
        MAX-ACCESS        	not-accessible
        STATUS        	current
        DESCRIPTION   	"An entry is configured to specify forwarding policy
                         parameters."
        INDEX         	{ rcIpUdpPortFwdDestPort,
                          rcIpUdpPortFwdDestAddr}
        ::= { rcIpUdpPortFwdTable 1 }
 
RcIpUdpPortFwdEntry ::=
        SEQUENCE {
                rcIpUdpPortFwdDestPort      INTEGER,
                rcIpUdpPortFwdDestAddr      IpAddress,
                rcIpUdpPortFwdId            INTEGER,
                rcIpUdpPortFwdFwdListIdListSize INTEGER (0..32),
                rcIpUdpPortFwdFwdListIdList IdList(SIZE(16)),
                rcIpUdpPortFwdNumFwdPackets Counter32,
                rcIpUdpPortFwdNumDropPacketsTtlExpired Counter32,
                rcIpUdpPortFwdNumDropPacketsDestUnreach Counter32,
                rcIpUdpPortFwdRowStatus     RowStatus
        }
 
rcIpUdpPortFwdDestPort OBJECT-TYPE
        SYNTAX        	INTEGER(1..65535)
        MAX-ACCESS        	read-only
        STATUS        	current
        DESCRIPTION   	"The well-known port number defined for UDP/TCP 
                        depending on the value of IpProtoType field in this
                        entry. This port number has to be defined in the
                        rcIpUdpProtoTable. In order to select this policy the 
                        destination port number has to match the DestPort 
                        value."
        ::= { rcIpUdpPortFwdEntry 1 }
 
rcIpUdpPortFwdDestAddr OBJECT-TYPE
        SYNTAX        	IpAddress
        MAX-ACCESS        	read-only
        STATUS        	current
        DESCRIPTION   	"Destination IP address. The IP addres to which the 
                        UDP/TCP broadcast should be forwarded. This IP address 
                        can be any IP server address or subnet broadcast 
                        address.  If the IP address is one of the routable 
                        interface's address on the router, the frame will be 
                        rebroadcast out as a limited broadcast. If the Ip 
                        address is that of a server then the received 
                        broadcast packet will be sent as a unicast packet to 
                        this address."
        ::= { rcIpUdpPortFwdEntry 2 }

rcIpUdpPortFwdId OBJECT-TYPE
        SYNTAX        Integer32
        MAX-ACCESS        read-only
        STATUS        current
        DESCRIPTION   "Identifier of this entry. Used internally to identify
                      this entry."
        ::= { rcIpUdpPortFwdEntry 3 }

rcIpUdpPortFwdFwdListIdListSize OBJECT-TYPE
        SYNTAX        INTEGER (0..32)
        MAX-ACCESS        read-only
        STATUS        current
        DESCRIPTION   "Used to indicate the number of id(s) in the
                      rcIpUdpPortFwdListId variable."
        ::= { rcIpUdpPortFwdEntry 4 }

rcIpUdpPortFwdFwdListIdList OBJECT-TYPE
        SYNTAX        IdList(SIZE(16))
        MAX-ACCESS        read-only
        STATUS        current
        DESCRIPTION   "Used to indicate zero or more rcIpUdpPortFwdListEntry(s)
                      that are referring to this entry.  Each list-id identifier
                      is stored as two bytes in this array starting from
                      offset zero.  Any unused bytes should be set to zero."
        ::= { rcIpUdpPortFwdEntry 5 }
 
rcIpUdpPortFwdNumFwdPackets OBJECT-TYPE
        SYNTAX        	Counter32
        MAX-ACCESS        	read-only
        STATUS        	current
        DESCRIPTION   	"The total number of UDP/TCP broadcast packets forwarded
                        using this policy."
        ::= { rcIpUdpPortFwdEntry 6 }

rcIpUdpPortFwdNumDropPacketsTtlExpired OBJECT-TYPE
        SYNTAX        	Counter32
        MAX-ACCESS        	read-only
        STATUS        	current
        DESCRIPTION   	"The total number of UDP/TCP broadcast packets dropped
                        because the TTL has expired."
        ::= { rcIpUdpPortFwdEntry 7 }

rcIpUdpPortFwdNumDropPacketsDestUnreach OBJECT-TYPE
        SYNTAX        	Counter32
        MAX-ACCESS        	read-only
        STATUS        	current
        DESCRIPTION   	"The total number of UDP/TCP broadcast packets dropped
                        because the rcIpUdpPortFwdDestAddr specified in
                        this policy was unreachable."
        ::= { rcIpUdpPortFwdEntry 8 }

rcIpUdpPortFwdRowStatus OBJECT-TYPE
        SYNTAX        	RowStatus
        MAX-ACCESS        	read-write
        STATUS        	current
        DESCRIPTION   	"Row status of this entry."
        ::= { rcIpUdpPortFwdEntry 9 }

-- Udp Port Fwd List Table 

rcIpUdpPortFwdListTableSize OBJECT-TYPE
        SYNTAX        Integer32
        MAX-ACCESS        read-only
        STATUS        current
        DESCRIPTION   "Used to indicate the number of entries in the
                      rcIpUdpPortFwdListTable."
        ::= { rcIpUdp 5 }

rcIpUdpPortFwdListTable OBJECT-TYPE
        SYNTAX        SEQUENCE OF RcIpUdpPortFwdListEntry
        MAX-ACCESS        not-accessible
        STATUS        current
        DESCRIPTION   "A table used to group rcIpUdpPortFwdEntry(s) 
                      into a list."
        ::= { rcIpUdp 6 }

rcIpUdpPortFwdListEntry OBJECT-TYPE
        SYNTAX        RcIpUdpPortFwdListEntry
        MAX-ACCESS        not-accessible
        STATUS        current
        DESCRIPTION   "Route entry attributes."
        INDEX         { rcIpUdpPortFwdListId }
        ::= { rcIpUdpPortFwdListTable 1 }
 
RcIpUdpPortFwdListEntry ::= SEQUENCE {
                  rcIpUdpPortFwdListId INTEGER (1..1000),
                  rcIpUdpPortFwdListName DisplayString (SIZE(0..15)),
                  rcIpUdpPortFwdListFwdIdListSize INTEGER (0..16),
                  rcIpUdpPortFwdListFwdIdList OCTET STRING (SIZE(32)),
                  rcIpUdpPortFwdListRowStatus RowStatus
                  }

rcIpUdpPortFwdListId OBJECT-TYPE
        SYNTAX        INTEGER (1..1000)
        MAX-ACCESS        read-only
        STATUS        current
        DESCRIPTION   "A value that uniquely identifies this list of 
                       rcIpUdpPortFwdListEntry."
        ::= { rcIpUdpPortFwdListEntry 1 }
 
rcIpUdpPortFwdListName OBJECT-TYPE
        SYNTAX        DisplayString (SIZE (0..15))
        MAX-ACCESS        read-write
        STATUS        current
        DESCRIPTION   "An administratively-assigned name for this list."
        ::= { rcIpUdpPortFwdListEntry 3 }
 
rcIpUdpPortFwdListFwdIdListSize OBJECT-TYPE
        SYNTAX        INTEGER (0..16)
        MAX-ACCESS        read-only
        STATUS        current
        DESCRIPTION   "Used to indicate the number of rcIpUdpPortFwdNetEntry 
                      id(s) in the rcIpUdpPortFwdListIdList variable."
        ::= { rcIpUdpPortFwdListEntry 4 }
 
rcIpUdpPortFwdListFwdIdList OBJECT-TYPE
        SYNTAX        OCTET STRING (SIZE(32))
        MAX-ACCESS        read-write
        STATUS        current
        DESCRIPTION   "Used to indicate zero or more UdpPortFwd entries 
                      that are associated to this list.  Each entry identifier
                      is stored as two bytes in this array starting from
                      offset zero.  Any unused bytes should be set to zero."
        ::= { rcIpUdpPortFwdListEntry 5 }

rcIpUdpPortFwdListRowStatus OBJECT-TYPE
        SYNTAX          RowStatus
        MAX-ACCESS          read-write
        STATUS          current
        DESCRIPTION     "Row status of this entry."
        ::= { rcIpUdpPortFwdListEntry 6 }
 

-- Ip Config Broadcast Forwarding Table

rcIpUdpConfBroadcastIntfTableSize OBJECT-TYPE
        SYNTAX        Integer32
        MAX-ACCESS        read-only
        STATUS        current
        DESCRIPTION   "Used to indicate the number of entries in the
                      rcIpUdpBroadcastIntfTable."
        ::= { rcIpUdp 7 }
 
rcIpUdpConfBroadcastIntfTable OBJECT-TYPE 
        SYNTAX          SEQUENCE OF RcIpUdpConfBroadcastIntfEntry
        MAX-ACCESS          not-accessible 
        STATUS          current 
        DESCRIPTION     "IP broadcast forward configuration table"
    ::= { rcIpUdp 8 }

rcIpUdpConfBroadcastIntfEntry OBJECT-TYPE
        SYNTAX        	RcIpUdpConfBroadcastIntfEntry
        MAX-ACCESS        	not-accessible
        STATUS        	current
        DESCRIPTION   	"Used to configure UDP broadcast forward on a 
                        particular interface."
        INDEX         	{ rcIpUdpConfBroadcastIntfLocalIfAddr }
        ::= { rcIpUdpConfBroadcastIntfTable 1 }
 
RcIpUdpConfBroadcastIntfEntry ::=
        SEQUENCE {
                rcIpUdpConfBroadcastIntfLocalIfAddr   	    IpAddress,
                rcIpUdpConfBroadcastIntfUdpPortFwdListId    INTEGER (0..100),
                rcIpUdpConfBroadcastIntfMaxTtl    	    INTEGER (1..16),
                rcIpUdpConfBroadcastIntfNumRxPkts           Counter32,
                rcIpUdpConfBroadcastIntfNumFwdPkts          Counter32,
                rcIpUdpConfBroadcastIntfNumDropPktsMaxTtlExpired  Counter32,
                rcIpUdpConfBroadcastIntfNumDropPktsDestUnreach    Counter32,
                rcIpUdpConfBroadcastIntfNumDropPktsUnknownPort    Counter32,
                rcIpUdpConfBroadcastIntfRowStatus 	              RowStatus
 
        }
 
rcIpUdpConfBroadcastIntfLocalIfAddr OBJECT-TYPE
        SYNTAX        	IpAddress 
        MAX-ACCESS        	read-only
        STATUS        	current
        DESCRIPTION   	"The ip address of the local interface that is
           	        partipating in the forwarding UDP broadcast packets."
        ::= { rcIpUdpConfBroadcastIntfEntry 1 }
 
rcIpUdpConfBroadcastIntfUdpPortFwdListId OBJECT-TYPE
        SYNTAX        INTEGER (0..100)
        MAX-ACCESS        read-write
        STATUS        current
        DESCRIPTION   "Used to indicate the number UDP ports that this 
                      interface is configured to forward.

                      A value of '0' indicates that this interface will not
                      forward any UDP broadcast packets. This is a required
                      field to create an entry."
        ::= { rcIpUdpConfBroadcastIntfEntry 2 }

rcIpUdpConfBroadcastIntfMaxTtl OBJECT-TYPE
        SYNTAX        	INTEGER (1..16)
        MAX-ACCESS        	read-write
        STATUS        	current
        DESCRIPTION   	"Used to indicate the maximum number of hops an 
		      	IP broadcast packet can take from the source 
                        device to the destination device."
 	    DEFVAL        	{ 4 }
        ::= { rcIpUdpConfBroadcastIntfEntry 3 }
 
rcIpUdpConfBroadcastIntfNumRxPkts OBJECT-TYPE
        SYNTAX        	Counter32
        MAX-ACCESS        	read-only
        STATUS        	current
        DESCRIPTION   	"The total number of UDP/TCP broadcast packets 
                        received by this local interface."
        ::= { rcIpUdpConfBroadcastIntfEntry 4 }

rcIpUdpConfBroadcastIntfNumFwdPkts OBJECT-TYPE
        SYNTAX        	Counter32
        MAX-ACCESS        	read-only
        STATUS        	current
        DESCRIPTION   	"The total number of UDP/TCP broadcast packets 
                        forwarded."
        ::= { rcIpUdpConfBroadcastIntfEntry 5 }

rcIpUdpConfBroadcastIntfNumDropPktsMaxTtlExpired OBJECT-TYPE
        SYNTAX        	Counter32
        MAX-ACCESS        	read-only
        STATUS        	current
        DESCRIPTION   	"The total number of UDP/TCP broadcast packets 
                        dropped because the TTL has expired."
        ::= { rcIpUdpConfBroadcastIntfEntry 6 }

rcIpUdpConfBroadcastIntfNumDropPktsDestUnreach OBJECT-TYPE
        SYNTAX        	Counter32
        MAX-ACCESS        	read-only
        STATUS        	current
        DESCRIPTION   	"The total number of UDP broadcast packets 
                        dropped because the destination was unreachable."
        ::= { rcIpUdpConfBroadcastIntfEntry 7 }

rcIpUdpConfBroadcastIntfNumDropPktsUnknownPort OBJECT-TYPE
        SYNTAX        	Counter32
        MAX-ACCESS        	read-only
        STATUS        	current
        DESCRIPTION   	"The total number of UDP/TCP broadcast packets 
                        dropped because the destination port/protocol 
                        specified has no matching forwarding policy." 
        ::= { rcIpUdpConfBroadcastIntfEntry 8 }

rcIpUdpConfBroadcastIntfRowStatus OBJECT-TYPE
        SYNTAX        	RowStatus
        MAX-ACCESS        	read-write
        STATUS        	current
        DESCRIPTION   	"Entry row status."
        ::= { rcIpUdpConfBroadcastIntfEntry 9 }

--IP ToS Rule
rcIpTosRule   OBJECT IDENTIFIER       ::= { rcIp 14}

rcIpTosRuleAndMask OBJECT-TYPE
        SYNTAX        INTEGER (0..255)
        MAX-ACCESS        read-write
        STATUS        deprecated
        DESCRIPTION   "And Mask. The Ip ToS byte in the Ip header
                       is logically ANDed with this value, and then logically
                       ORed with the one of the OrRules below."
        ::= { rcIpTosRule 1 }

rcIpTosRuleOrRule1 OBJECT-TYPE
        SYNTAX        INTEGER (0..255)
        MAX-ACCESS        read-write
        STATUS        deprecated
        DESCRIPTION   "Quid/Gid Or rule #1. The Ip ToS byte in the Ip header
                       is logically ORed with this value."
        ::= { rcIpTosRule 2 }

rcIpTosRuleOrRule2 OBJECT-TYPE
        SYNTAX        INTEGER (0..255)
        MAX-ACCESS        read-write
        STATUS        deprecated
        DESCRIPTION   "Quid/Gid Or rule #2. The Ip ToS byte in the Ip header
                       is logically ORed with this value."
        ::= { rcIpTosRule 3 }

rcIpTosRuleOrRule3 OBJECT-TYPE
        SYNTAX        INTEGER (0..255)
        MAX-ACCESS        read-write
        STATUS        deprecated
        DESCRIPTION   "Quid/Gid Or rule #3. The Ip ToS byte in the Ip header
                       is logically ORed with this value."
        ::= { rcIpTosRule 4 }

rcIpTosRuleTosPriorityEnable OBJECT-TYPE
        SYNTAX          TruthValue
        MAX-ACCESS          read-write
        STATUS          current
        DESCRIPTION     "Enable Tos priority."
        ::= { rcIpTosRule 5 }
 
rcIpTosRuleTosThreshold OBJECT-TYPE
        SYNTAX        INTEGER {
                         level0(0),
                         level1(1),
                         level2(2),
                         level3(3),
                         level4(4),
                         level5(5),
                         level6(6),
                         level7(7)
                      }
        MAX-ACCESS        read-only
        STATUS        current
        DESCRIPTION   "tos threshold"
        ::= { rcIpTosRule 6 }

--IP Static Route
rcIpStaticRoute OBJECT IDENTIFIER       ::= { rcIp 15}

rcIpStaticRouteTableSize OBJECT-TYPE
        SYNTAX        Integer32
        MAX-ACCESS        read-only
        STATUS        current
        DESCRIPTION   "size of Ip Static Route Table."
        ::= { rcIpStaticRoute 1 }

rcIpStaticRouteTable OBJECT-TYPE 
        SYNTAX          SEQUENCE OF RcIpStaticRouteEntry
        MAX-ACCESS          not-accessible 
        STATUS          current 
        DESCRIPTION     "This table is used to add static IP routes to
			the device.  Routes added into this table will
			automatically show-up in the 'rcIpRouteTable'
			when the device is actively using the route
			to forward IP traffic." 
    ::= { rcIpStaticRoute 2 }

rcIpStaticRouteEntry OBJECT-TYPE
        SYNTAX        	RcIpStaticRouteEntry
        MAX-ACCESS        	not-accessible
        STATUS        	current
        DESCRIPTION   	"A static route to a particular destination."
        INDEX         	{ rcIpStaticRouteDest,
                          rcIpStaticRouteMask,
                          rcIpStaticRouteNextHop }
        ::= { rcIpStaticRouteTable 1 }
 
RcIpStaticRouteEntry ::=
        SEQUENCE {
                rcIpStaticRouteDest   	      IpAddress,
                rcIpStaticRouteMask   	      IpAddress,
                rcIpStaticRouteNextHop	      IpAddress,
                rcIpStaticRouteMetric         INTEGER (1..'FFFF'h),
                rcIpStaticRouteIfIndex        InterfaceIndex,
                rcIpStaticRoutePreference     INTEGER (1..16),
                rcIpStaticRouteEnable         TruthValue,
                rcIpStaticRouteStatus         INTEGER,
                rcIpStaticRouteRowStatus      RowStatus
 
        }
 
rcIpStaticRouteDest OBJECT-TYPE
        SYNTAX        	IpAddress 
        MAX-ACCESS        	read-only
        STATUS        	current
        DESCRIPTION   	"The destination IP address of this route.  An
                        entry with a value of 0.0.0.0 is considered a
                        default route.  Multiple routes to a single
                        destination can appear in the table, but access to
                        such multiple entries is dependent on the table-
                        access mechanisms defined by the network
                        management protocol in use."
        ::= { rcIpStaticRouteEntry 1 }
 
rcIpStaticRouteMask OBJECT-TYPE
        SYNTAX        	IpAddress 
        MAX-ACCESS        	read-only
        STATUS        	current
        DESCRIPTION   	"Indicate the mask to be logical-ANDed with the
                        destination address before being compared to the
                        value in the rcIpRouteDest field.  For those systems
                        that do not support arbitrary subnet masks, an
                        agent constructs the value of the rcIpRouteMask by
                        determining whether the value of the correspondent
                        rcIpRouteDest field belong to a class-A, B, or C
                        network, and then using one of:
 
                           mask           network
                           255.0.0.0      class-A
                           255.255.0.0    class-B
                           255.255.255.0  class-C
 
                        If the value of the rcIpRouteDest is 0.0.0.0 (a
                        default route), then the mask value is also
                        0.0.0.0.  It should be noted that all IP routing
                        subsystems implicitly use this mechanism."
        ::= { rcIpStaticRouteEntry 2 }
 
rcIpStaticRouteNextHop OBJECT-TYPE
        SYNTAX        	IpAddress 
        MAX-ACCESS        	read-only
        STATUS        	current
        DESCRIPTION   	"The IP address of the next hop of this route.
                        (In the case of a route bound to an interface
                        which is realized via a broadcast media, the value
                        of this field is the agent's IP address on that
                        interface)."
        ::= { rcIpStaticRouteEntry 3 }
 
rcIpStaticRouteMetric OBJECT-TYPE
        SYNTAX        	INTEGER (1..'FFFF'h)
        MAX-ACCESS        	read-write
        STATUS        	current
        DESCRIPTION   	"The primary routing metric for this route.  The
                        semantics of this metric are determined by the
                        routing-protocol specified in the route's
                        rcIpRouteProto value.  If this metric is not used,
                        its value should be set to -1."
	DEFVAL        	{ 1 }
        ::= { rcIpStaticRouteEntry 4 }

rcIpStaticRouteIfIndex OBJECT-TYPE
        SYNTAX        	InterfaceIndex
        MAX-ACCESS        	read-only
        STATUS        	current
        DESCRIPTION   	"The index value which uniquely identifies the
                        local interface through which the next hop of this
                        route should be reached.  The interface identified
                        by a particular value of this index is the same
                        interface as identified by the same value of
                        ifIndex."
        ::= { rcIpStaticRouteEntry 5 }

rcIpStaticRoutePreference OBJECT-TYPE
        SYNTAX        	INTEGER (1..16)
        MAX-ACCESS        	read-write
        STATUS        	current
        DESCRIPTION   	"Used to indicate the route preference of this
			entry.  If there are more than one route that can
			be used to forward IP traffic, the route that has
			a highest preference will be used instead of a
			lower preference one.  

			The higher the number, the higher the preference."
	DEFVAL        	{ 16 }
        ::= { rcIpStaticRouteEntry 6 }

rcIpStaticRouteEnable OBJECT-TYPE
        SYNTAX         	TruthValue
        MAX-ACCESS         	read-write
        STATUS         	current
        DESCRIPTION    	"Used to enable/disable this entry."
	DEFVAL        { true }
        ::= { rcIpStaticRouteEntry 7 }

rcIpStaticRouteStatus OBJECT-TYPE
        SYNTAX        	INTEGER {
		         	inactive(0),
			 	active(1)
		      	}
        MAX-ACCESS        	read-only
        STATUS        	current
        DESCRIPTION   	"Used to indicate the current status of
			this entry."
	DEFVAL        	{ active }
        ::= { rcIpStaticRouteEntry 8 }

rcIpStaticRouteRowStatus OBJECT-TYPE
        SYNTAX          RowStatus
        MAX-ACCESS          read-write
        STATUS          current
        DESCRIPTION     "Used to create/delete entries"
        ::= { rcIpStaticRouteEntry 9 }

--IP PIM

rcIpPim OBJECT IDENTIFIER ::= { rcIp 16 }

rcIpPimGlobal OBJECT IDENTIFIER ::= { rcIpPim 1}

rcIpPimGlobalEnable OBJECT-TYPE
        SYNTAX          TruthValue
        MAX-ACCESS          read-write
        STATUS          current
        DESCRIPTION     "enable feature"
        ::= { rcIpPimGlobal 1 }

rcIpPimTable OBJECT-TYPE 
        SYNTAX          SEQUENCE OF RcIpPimEntry
        MAX-ACCESS          not-accessible 
        STATUS          current 
        DESCRIPTION     "IP Pim table"
    ::= { rcIpPim 2 }

rcIpPimEntry OBJECT-TYPE
        SYNTAX        	RcIpPimEntry
        MAX-ACCESS        	not-accessible
        STATUS        	current
        DESCRIPTION   	"An entry of Ip Pim Table."
        INDEX         	{ rcIpPimIfIndex }
        ::= { rcIpPimTable 1 }
 
RcIpPimEntry ::=
        SEQUENCE {
                rcIpPimIfIndex           InterfaceIndex,
                rcIpPimEnable            TruthValue,
                rcIpPimMode              INTEGER,
                rcIpPimHelloInterval     INTEGER,
                rcIpPimJoinPruneInterval INTEGER,
                rcIpPimCBSRPreference    INTEGER
        }
 
rcIpPimIfIndex OBJECT-TYPE
        SYNTAX        InterfaceIndex
        MAX-ACCESS        read-only
        STATUS        current
        DESCRIPTION   "port"
        ::= { rcIpPimEntry 1 }

rcIpPimEnable OBJECT-TYPE
        SYNTAX         TruthValue
        MAX-ACCESS         read-write
        STATUS         current
        DESCRIPTION    "enable interface"
        ::= { rcIpPimEntry 2 }

rcIpPimMode OBJECT-TYPE
        SYNTAX        INTEGER {
		         dense(1),
			 sparse(2),
			 sparseDense(3)
		      }
        MAX-ACCESS        read-write
        STATUS        current
        DESCRIPTION   ""
        ::= { rcIpPimEntry 3 }

rcIpPimHelloInterval OBJECT-TYPE
        SYNTAX        INTEGER (1..65535)
        MAX-ACCESS        read-write
        STATUS        current
        DESCRIPTION   "frq. at which hello sent."
        ::= { rcIpPimEntry 4 }

rcIpPimJoinPruneInterval OBJECT-TYPE
        SYNTAX        INTEGER (1..65535)
        MAX-ACCESS        read-write
        STATUS        current
        DESCRIPTION   ""
        ::= { rcIpPimEntry 5 }

rcIpPimCBSRPreference OBJECT-TYPE
        SYNTAX        INTEGER (1..65535)
        MAX-ACCESS        read-write
        STATUS        current
        DESCRIPTION   ""
        ::= { rcIpPimEntry 6 }

--IP Multicast Arp table

rcIpMulticastArpTable OBJECT-TYPE 
        SYNTAX          SEQUENCE OF RcIpMulticastArpEntry
        MAX-ACCESS          not-accessible 
        STATUS          current 
        DESCRIPTION     "IP Multicast Arp table"
        ::= { rcIp 17 }

rcIpMulticastArpEntry OBJECT-TYPE
        SYNTAX        	RcIpMulticastArpEntry
        MAX-ACCESS        	not-accessible
        STATUS        	current
        DESCRIPTION   	"An entry of Ip Multicast Arp Table."
        INDEX         	{ rcIpMulticastArpVlanId,
                          rcIpMulticastArpMacAddress,
                          rcIpMulticastArpIpAddress }
        ::= { rcIpMulticastArpTable 1 }
 
RcIpMulticastArpEntry ::=
        SEQUENCE {
                rcIpMulticastArpVlanId     INTEGER,
                rcIpMulticastArpMacAddress MacAddress,
                rcIpMulticastArpIpAddress  IpAddress,
                rcIpMulticastArpPorts      PortSet,
                rcIpMulticastArpNumMltIds  INTEGER,
                rcIpMulticastArpMltIds     IdList,
                rcIpMulticastArpRowStatus  RowStatus
        }
 
rcIpMulticastArpVlanId OBJECT-TYPE
        SYNTAX        Integer32
        MAX-ACCESS        read-only
        STATUS        current
        DESCRIPTION   "vlan id"
        ::= { rcIpMulticastArpEntry 1 }

rcIpMulticastArpMacAddress OBJECT-TYPE
        SYNTAX         MacAddress
        MAX-ACCESS         read-only
        STATUS         current
        DESCRIPTION    "multicast mac address"
        ::= { rcIpMulticastArpEntry 2 }

rcIpMulticastArpIpAddress OBJECT-TYPE
        SYNTAX        IpAddress
        MAX-ACCESS        read-only
        STATUS        current
        DESCRIPTION   "multicast ip address"
        ::= { rcIpMulticastArpEntry 3 }

rcIpMulticastArpPorts OBJECT-TYPE
        SYNTAX        PortSet
        MAX-ACCESS        read-write
        STATUS        current
        DESCRIPTION   "ports within a particular vlan"
        ::= { rcIpMulticastArpEntry 4 }

rcIpMulticastArpNumMltIds OBJECT-TYPE
        SYNTAX        Integer32
        MAX-ACCESS        read-only
        STATUS        current
        DESCRIPTION   "number of mlt ids"
        ::= { rcIpMulticastArpEntry 5 }

rcIpMulticastArpMltIds OBJECT-TYPE
        SYNTAX        IdList
        MAX-ACCESS        read-write
        STATUS        current
        DESCRIPTION   "mlt id"
        ::= { rcIpMulticastArpEntry 6 }

rcIpMulticastArpRowStatus OBJECT-TYPE
        SYNTAX        RowStatus
        MAX-ACCESS        read-write
        STATUS        current
        DESCRIPTION   "row status"
        ::= { rcIpMulticastArpEntry 7 }

--IP Multicast Table

rcIpMulticastTable OBJECT-TYPE
        SYNTAX        SEQUENCE OF RcIpMulticastEntry
        MAX-ACCESS        not-accessible
        STATUS        obsolete
        DESCRIPTION   "Ip multicast table."
        ::= { rcIp 18 }
 
rcIpMulticastEntry OBJECT-TYPE
        SYNTAX        RcIpMulticastEntry
        MAX-ACCESS        not-accessible
        STATUS        current
        DESCRIPTION   "Entry containing Proprietary Ip Multicast information."
        INDEX         { rcIpMulticastIfIndex }
        ::= { rcIpMulticastTable 1 }
 
RcIpMulticastEntry ::=
        SEQUENCE {
                rcIpMulticastIfIndex InterfaceIndex,
                rcIpMulticastMulticastIp IpAddress
        }
 
rcIpMulticastIfIndex OBJECT-TYPE
        SYNTAX          InterfaceIndex
        MAX-ACCESS          read-only
        STATUS          current
        DESCRIPTION     "IfIndex."
        ::= { rcIpMulticastEntry 1 }
 
rcIpMulticastMulticastIp OBJECT-TYPE
        SYNTAX          IpAddress
        MAX-ACCESS          read-write
        STATUS          current
        DESCRIPTION     "IP Address on this IfIndex
                         to be used for all Multicast
                         protocols running on this
                         interface."
        ::= { rcIpMulticastEntry 2 }


--IP Gen Policy

rcIpGenPolicy OBJECT IDENTIFIER ::= { rcIp 100 }

-- Ip As Path Access List Table

rcIpAsPathAccessListTableSize OBJECT-TYPE
        SYNTAX        Integer32
        MAX-ACCESS        read-only
        STATUS        current
        DESCRIPTION   "table size"
        ::= { rcIpGenPolicy 1 }

rcIpAsPathAccessListTable OBJECT-TYPE 
        SYNTAX          SEQUENCE OF RcIpAsPathAccessListEntry
        MAX-ACCESS          not-accessible 
        STATUS          current 
        DESCRIPTION     "IP As Path Access List table"
    ::= { rcIpGenPolicy 2 }

rcIpAsPathAccessListEntry OBJECT-TYPE
        SYNTAX        	RcIpAsPathAccessListEntry
        MAX-ACCESS        	not-accessible
        STATUS        	current
        DESCRIPTION   	"An entry of Ip As Path Access List Table."
        INDEX         	{ rcIpAsPathAccessListId,
                          rcIpAsPathAccessListMemberId }
        ::= { rcIpAsPathAccessListTable 1 }
 
RcIpAsPathAccessListEntry ::=
        SEQUENCE {
                rcIpAsPathAccessListId                  INTEGER,
                rcIpAsPathAccessListMemberId            INTEGER,
                rcIpAsPathAccessListMode                INTEGER,
                rcIpAsPathAccessListAsRegularExpression DisplayString,
                rcIpAsPathAccessListRowStatus           RowStatus
        }
 
rcIpAsPathAccessListId OBJECT-TYPE
        SYNTAX        Integer32
        MAX-ACCESS        read-only
        STATUS        current
        DESCRIPTION   ""
        ::= { rcIpAsPathAccessListEntry 1 }

rcIpAsPathAccessListMemberId OBJECT-TYPE
        SYNTAX        Integer32
        MAX-ACCESS        read-only
        STATUS        current
        DESCRIPTION   "frq. at which hello sent."
        ::= { rcIpAsPathAccessListEntry 2 }

rcIpAsPathAccessListMode OBJECT-TYPE
        SYNTAX        INTEGER {
                          permit(1),
                          deny(2)
                      }
        MAX-ACCESS        read-write
        STATUS        current
        DESCRIPTION   ""
        ::= { rcIpAsPathAccessListEntry 3 }

rcIpAsPathAccessListAsRegularExpression OBJECT-TYPE
        SYNTAX        DisplayString
        MAX-ACCESS        read-write
        STATUS        current
        DESCRIPTION   ""
        ::= { rcIpAsPathAccessListEntry 4 }

rcIpAsPathAccessListRowStatus OBJECT-TYPE
        SYNTAX        RowStatus
        MAX-ACCESS        read-write
        STATUS        current
        DESCRIPTION   ""
        ::= { rcIpAsPathAccessListEntry 5 }

-- Ip Community Access List Table

rcIpCommunityAccessListTableSize OBJECT-TYPE
        SYNTAX        Integer32
        MAX-ACCESS        read-only
        STATUS        current
        DESCRIPTION   "table size"
        ::= { rcIpGenPolicy 3 }

rcIpCommunityAccessListTable OBJECT-TYPE 
        SYNTAX          SEQUENCE OF RcIpCommunityAccessListEntry
        MAX-ACCESS          not-accessible 
        STATUS          current 
        DESCRIPTION     "IP CommunityAccess List table"
    ::= { rcIpGenPolicy 4 }

rcIpCommunityAccessListEntry OBJECT-TYPE
        SYNTAX        	RcIpCommunityAccessListEntry
        MAX-ACCESS        	not-accessible
        STATUS        	current
        DESCRIPTION   	"An entry of Ip CommunityAccess List Table."
        INDEX         	{ rcIpCommunityAccessListId,
                          rcIpCommunityAccessListMemberId }
        ::= { rcIpCommunityAccessListTable 1 }
 
RcIpCommunityAccessListEntry ::=
        SEQUENCE {
                rcIpCommunityAccessListId        INTEGER,
                rcIpCommunityAccessListMemberId  INTEGER,
                rcIpCommunityAccessListMode      INTEGER,
                rcIpCommunityAccessListCommunity DisplayString,
                rcIpCommunityAccessListRowStatus RowStatus
        }
 
rcIpCommunityAccessListId OBJECT-TYPE
        SYNTAX        Integer32
        MAX-ACCESS        read-only
        STATUS        current
        DESCRIPTION   ""
        ::= { rcIpCommunityAccessListEntry 1 }

rcIpCommunityAccessListMemberId OBJECT-TYPE
        SYNTAX        Integer32
        MAX-ACCESS        read-only
        STATUS        current
        DESCRIPTION   "frq. at which hello sent."
        ::= { rcIpCommunityAccessListEntry 2 }

rcIpCommunityAccessListMode OBJECT-TYPE
        SYNTAX        INTEGER {
                          permit(1),
                          deny(2)
                      }
        MAX-ACCESS        read-write
        STATUS        current
        DESCRIPTION   ""
        ::= { rcIpCommunityAccessListEntry 3 }

rcIpCommunityAccessListCommunity OBJECT-TYPE
        SYNTAX        DisplayString
        MAX-ACCESS        read-write
        STATUS        current
        DESCRIPTION   ""
        ::= { rcIpCommunityAccessListEntry 4 }

rcIpCommunityAccessListRowStatus OBJECT-TYPE
        SYNTAX        RowStatus
        MAX-ACCESS        read-write
        STATUS        current
        DESCRIPTION   ""
        ::= { rcIpCommunityAccessListEntry 5 }

-- Ip Access List Table
 
rcIpAccessListTableSize OBJECT-TYPE
        SYNTAX        Integer32
        MAX-ACCESS        read-only
        STATUS        current
        DESCRIPTION   "table size"
        ::= { rcIpGenPolicy 5 }


rcIpAccessListTable OBJECT-TYPE 
        SYNTAX          SEQUENCE OF RcIpAccessListEntry
        MAX-ACCESS          not-accessible 
        STATUS          current 
        DESCRIPTION     "IP Access List table"
    ::= { rcIpGenPolicy 6 }

rcIpAccessListEntry OBJECT-TYPE
        SYNTAX        	RcIpAccessListEntry
        MAX-ACCESS        	not-accessible
        STATUS        	current
        DESCRIPTION   	"An entry of Ip Access List Table."
        INDEX         	{ rcIpAccessListId,
                          rcIpAccessListMode,
                          rcIpAccessListNetwork,
                          rcIpAccessListNetworkMask }
        ::= { rcIpAccessListTable 1 }
 
RcIpAccessListEntry ::=
        SEQUENCE {
                rcIpAccessListId          INTEGER,
                rcIpAccessListMode        INTEGER,
                rcIpAccessListNetwork     IpAddress,
                rcIpAccessListNetworkMask IpAddress,
                rcIpAccessListName        DisplayString,
                rcIpAccessListRowStatus   RowStatus
        }
 
rcIpAccessListId OBJECT-TYPE
        SYNTAX        INTEGER (1..99)
        MAX-ACCESS        read-only
        STATUS        current
        DESCRIPTION   ""
        ::= { rcIpAccessListEntry 1 }

rcIpAccessListMode OBJECT-TYPE
        SYNTAX        INTEGER {
                          permit(1),
                          deny(2)
                      }
        MAX-ACCESS        read-only
        STATUS        current
        DESCRIPTION   ""
        ::= { rcIpAccessListEntry 2 }

rcIpAccessListNetwork OBJECT-TYPE
        SYNTAX        IpAddress
        MAX-ACCESS        read-write
        STATUS        current
        DESCRIPTION   ""
        ::= { rcIpAccessListEntry 3 }

rcIpAccessListNetworkMask OBJECT-TYPE
        SYNTAX        IpAddress
        MAX-ACCESS        read-write
        STATUS        current
        DESCRIPTION   ""
        ::= { rcIpAccessListEntry 4 }

rcIpAccessListName OBJECT-TYPE
        SYNTAX        DisplayString
        MAX-ACCESS        read-write
        STATUS        current
        DESCRIPTION   ""
        ::= { rcIpAccessListEntry 5 }

rcIpAccessListRowStatus OBJECT-TYPE
        SYNTAX        RowStatus
        MAX-ACCESS        read-write
        STATUS        current
        DESCRIPTION   ""
        ::= { rcIpAccessListEntry 6 }

-- Ip Extended Access List Table
 
rcIpExtendedAccessListTableSize OBJECT-TYPE
        SYNTAX        Integer32
        MAX-ACCESS        read-only
        STATUS        current
        DESCRIPTION   "table size"
        ::= { rcIpGenPolicy 7 }


rcIpExtendedAccessListTable OBJECT-TYPE 
        SYNTAX          SEQUENCE OF RcIpExtendedAccessListEntry
        MAX-ACCESS          not-accessible 
        STATUS          current 
        DESCRIPTION     "IP Extended Access List table"
        ::= { rcIpGenPolicy 8 }

rcIpExtendedAccessListEntry OBJECT-TYPE
        SYNTAX        	RcIpExtendedAccessListEntry
        MAX-ACCESS        	not-accessible
        STATUS        	current
        DESCRIPTION   	"An entry of Ip Extended Access List Table."
        INDEX         	{ rcIpExtendedAccessListId,
                          rcIpExtendedAccessListMode,
                          rcIpExtendedAccessListNetwork,
                          rcIpExtendedAccessListNetworkWildCard,
                          rcIpExtendedAccessListNetworkMask,
                          rcIpExtendedAccessListNetworkMaskWildCard }
        ::= { rcIpExtendedAccessListTable 1 }
 
RcIpExtendedAccessListEntry ::=
        SEQUENCE {
                rcIpExtendedAccessListId                  INTEGER,
                rcIpExtendedAccessListMode                INTEGER,
                rcIpExtendedAccessListNetwork             IpAddress,
                rcIpExtendedAccessListNetworkWildCard     IpAddress,
                rcIpExtendedAccessListNetworkMask         IpAddress,
                rcIpExtendedAccessListNetworkMaskWildCard IpAddress,
                rcIpExtendedAccessListName                DisplayString,
                rcIpExtendedAccessListRowStatus           RowStatus
        }
 
rcIpExtendedAccessListId OBJECT-TYPE
        SYNTAX        INTEGER (100..199)
        MAX-ACCESS        read-only
        STATUS        current
        DESCRIPTION   ""
        ::= { rcIpExtendedAccessListEntry 1 }

rcIpExtendedAccessListMode OBJECT-TYPE
        SYNTAX        INTEGER {
                          permit(1),
                          deny(2)
                      }
        MAX-ACCESS        read-only
        STATUS        current
        DESCRIPTION   ""
        ::= { rcIpExtendedAccessListEntry 2 }

rcIpExtendedAccessListNetwork OBJECT-TYPE
        SYNTAX        IpAddress
        MAX-ACCESS        read-only
        STATUS        current
        DESCRIPTION   ""
        ::= { rcIpExtendedAccessListEntry 3 }

rcIpExtendedAccessListNetworkWildCard OBJECT-TYPE
        SYNTAX        IpAddress
        MAX-ACCESS        read-only
        STATUS        current
        DESCRIPTION   ""
        ::= { rcIpExtendedAccessListEntry 4 }

rcIpExtendedAccessListNetworkMask OBJECT-TYPE
        SYNTAX        IpAddress
        MAX-ACCESS        read-only
        STATUS        current
        DESCRIPTION   ""
        ::= { rcIpExtendedAccessListEntry 5 }

rcIpExtendedAccessListNetworkMaskWildCard OBJECT-TYPE
        SYNTAX        IpAddress
        MAX-ACCESS        read-only
        STATUS        current
        DESCRIPTION   ""
        ::= { rcIpExtendedAccessListEntry 6 }

rcIpExtendedAccessListName OBJECT-TYPE
        SYNTAX        DisplayString
        MAX-ACCESS        read-write
        STATUS        current
        DESCRIPTION   ""
        ::= { rcIpExtendedAccessListEntry 7 }

rcIpExtendedAccessListRowStatus OBJECT-TYPE
        SYNTAX        RowStatus
        MAX-ACCESS        read-write
        STATUS        current
        DESCRIPTION   ""
        ::= { rcIpExtendedAccessListEntry 8 }

-- Ip Prefix List Table
 
rcIpPrefixListTableSize OBJECT-TYPE
        SYNTAX        Integer32
        MAX-ACCESS        read-only
        STATUS        current
        DESCRIPTION   "table size"
        ::= { rcIpGenPolicy 9 }


rcIpPrefixListTable OBJECT-TYPE 
        SYNTAX          SEQUENCE OF RcIpPrefixListEntry
        MAX-ACCESS          not-accessible 
        STATUS          current 
        DESCRIPTION     "IP Prefix List table"
        ::= { rcIpGenPolicy 10 }

rcIpPrefixListEntry OBJECT-TYPE
        SYNTAX        	RcIpPrefixListEntry
        MAX-ACCESS        	not-accessible
        STATUS        	current
        DESCRIPTION   	"An entry of Ip Prefix List Table."
        INDEX         	{ rcIpPrefixListId,
                          rcIpPrefixListSequenceNumber,
                          rcIpPrefixListPrefix,
                          rcIpPrefixListPrefixMaskLen }
        ::= { rcIpPrefixListTable 1 }
 
RcIpPrefixListEntry ::=
        SEQUENCE {
                rcIpPrefixListId               INTEGER,
                rcIpPrefixListSequenceNumber   INTEGER,
                rcIpPrefixListMode             INTEGER,
                rcIpPrefixListPrefix           IpAddress,
                rcIpPrefixListPrefixMaskLen    INTEGER,
                rcIpPrefixListGreaterThanValue INTEGER,
                rcIpPrefixListLessThanValue    INTEGER,
                rcIpPrefixListName             DisplayString,
                rcIpPrefixListRowStatus        RowStatus
        }
 
rcIpPrefixListId OBJECT-TYPE
        SYNTAX        Integer32
        MAX-ACCESS        read-only
        STATUS        current
        DESCRIPTION   "ListId"
        ::= { rcIpPrefixListEntry 1 }

rcIpPrefixListSequenceNumber OBJECT-TYPE
        SYNTAX        Integer32
        MAX-ACCESS        read-only
        STATUS        current
        DESCRIPTION   "Sequence Number"
        ::= { rcIpPrefixListEntry 2 }

rcIpPrefixListMode OBJECT-TYPE
        SYNTAX        INTEGER {
                          permit(1),
                          deny(2)
                      }
        MAX-ACCESS        read-only
        STATUS        current
        DESCRIPTION   ""
        ::= { rcIpPrefixListEntry 3 }

rcIpPrefixListPrefix OBJECT-TYPE
        SYNTAX        IpAddress
        MAX-ACCESS        read-only
        STATUS        current
        DESCRIPTION   "prefix number"
        ::= { rcIpPrefixListEntry 4 }

rcIpPrefixListPrefixMaskLen OBJECT-TYPE
        SYNTAX        Integer32
        MAX-ACCESS        read-only
        STATUS        current
        DESCRIPTION   "prefix mask length"
        ::= { rcIpPrefixListEntry 5 }

rcIpPrefixListGreaterThanValue OBJECT-TYPE
        SYNTAX        Integer32
        MAX-ACCESS        read-only
        STATUS        current
        DESCRIPTION   "greater than"
        ::= { rcIpPrefixListEntry 6 }

rcIpPrefixListLessThanValue OBJECT-TYPE
        SYNTAX        Integer32
        MAX-ACCESS        read-only
        STATUS        current
        DESCRIPTION   "less than"
        ::= { rcIpPrefixListEntry 7 }

rcIpPrefixListName OBJECT-TYPE
        SYNTAX        DisplayString
        MAX-ACCESS        read-write
        STATUS        current
        DESCRIPTION   "list name"
        ::= { rcIpPrefixListEntry 8 }

rcIpPrefixListRowStatus OBJECT-TYPE
        SYNTAX        RowStatus
        MAX-ACCESS        read-write
        STATUS        current
        DESCRIPTION   "row status"
        ::= { rcIpPrefixListEntry 9 }


rcIpPrefixListSeqNumberEnable OBJECT-TYPE
        SYNTAX        TruthValue
        MAX-ACCESS        read-write
        STATUS        current
        DESCRIPTION   "Enable automatic seq# generation."
        ::= { rcIpGenPolicy 11 }


-- Ip Route Map Table

rcIpRouteMapTableSize OBJECT-TYPE
        SYNTAX        Integer32
        MAX-ACCESS        read-only
        STATUS        current
        DESCRIPTION   "table size"
        ::= { rcIpGenPolicy 12 }

rcIpRouteMapTable OBJECT-TYPE 
        SYNTAX          SEQUENCE OF RcIpRouteMapEntry
        MAX-ACCESS          not-accessible 
        STATUS          current 
        DESCRIPTION     "IP Route Map table"
        ::= { rcIpGenPolicy 13 }

rcIpRouteMapEntry OBJECT-TYPE
        SYNTAX        	RcIpRouteMapEntry
        MAX-ACCESS        	not-accessible
        STATUS        	current
        DESCRIPTION   	"An entry of Ip Route Map Table."
        INDEX         	{ rcIpRouteMapId, rcIpRouteMapSequenceNumber }
        ::= { rcIpRouteMapTable 1 }
 
RcIpRouteMapEntry ::=
        SEQUENCE {
                rcIpRouteMapId                          INTEGER,
                rcIpRouteMapSequenceNumber              INTEGER,
                rcIpRouteMapName                        DisplayString,
                rcIpRouteMapMode                        INTEGER,
                rcIpRouteMapMatchAsPathListId           INTEGER,
                rcIpRouteMapMatchCommunityListId        INTEGER,
                rcIpRouteMapMatchCommunityExact         EnableValue,
                rcIpRouteMapMatchInterfaceNumber        INTEGER,
                rcIpRouteMapMatchIpAddress              IdList,
                rcIpRouteMapMatchIpRouteSource          IdList,
                rcIpRouteMapMatchNextHop                IdList,
                rcIpRouteMapMatchRouteType              INTEGER,
                rcIpRouteMapMatchMetric                 INTEGER,
                rcIpRouteMapMatchTag                    DisplayString,
                rcIpRouteMapSetAsPath                   DisplayString,
                rcIpRouteMapSetAsPathMode               INTEGER,
                rcIpRouteMapSetAutomaticTag             EnableValue,
                rcIpRouteMapSetCommunityNumber          INTEGER,
                rcIpRouteMapSetCommunityMode            INTEGER,
                rcIpRouteMapSetCommunityDelListId       INTEGER,
                rcIpRouteMapSetDampening                EnableValue,
                rcIpRouteMapSetDampeningHalflife        INTEGER,
                rcIpRouteMapSetDampeningReuse           INTEGER,
                rcIpRouteMapSetDampeningSuppress        INTEGER,
                rcIpRouteMapSetDampeningMaxSuppressTime INTEGER,
                rcIpRouteMapSetMetricTypeInternal       INTEGER,
                rcIpRouteMapSetMetric                   INTEGER,
                rcIpRouteMapSetMetricType               INTEGER,
                rcIpRouteMapSetNextHop                  IpAddress,
                rcIpRouteMapSetOrigin                   INTEGER,
                rcIpRouteMapSetOriginEgpAs              INTEGER,
                rcIpRouteMapSetTag                      INTEGER,
                rcIpRouteMapSetWeight                   INTEGER,
                rcIpRouteMapRowStatus                   RowStatus
        }
 
rcIpRouteMapId OBJECT-TYPE
        SYNTAX        Integer32
        MAX-ACCESS        read-only
        STATUS        current
        DESCRIPTION   "Route map id"
        ::= { rcIpRouteMapEntry 1 }

rcIpRouteMapSequenceNumber OBJECT-TYPE
        SYNTAX        Integer32
        MAX-ACCESS        read-only
        STATUS        current
        DESCRIPTION   "Sequence Number"
        ::= { rcIpRouteMapEntry 2 }

rcIpRouteMapName OBJECT-TYPE
        SYNTAX        DisplayString
        MAX-ACCESS        read-only
        STATUS        current
        DESCRIPTION   "Route map name"
        ::= { rcIpRouteMapEntry 3 }

rcIpRouteMapMode OBJECT-TYPE
        SYNTAX        INTEGER {
                          permit(1),
                          deny(2)
                      }
        MAX-ACCESS        read-write
        STATUS        current
        DESCRIPTION   ""
        ::= { rcIpRouteMapEntry 4 }

rcIpRouteMapMatchAsPathListId OBJECT-TYPE
        SYNTAX        Integer32
        MAX-ACCESS        read-write
        STATUS        current
        DESCRIPTION   ""
        ::= { rcIpRouteMapEntry 5 }

rcIpRouteMapMatchCommunityListId OBJECT-TYPE
        SYNTAX        Integer32
        MAX-ACCESS        read-write
        STATUS        current
        DESCRIPTION   ""
        ::= { rcIpRouteMapEntry 6 }

rcIpRouteMapMatchCommunityExact OBJECT-TYPE
        SYNTAX        EnableValue
        MAX-ACCESS        read-write
        STATUS        current
        DESCRIPTION   ""
        ::= { rcIpRouteMapEntry 7 }

rcIpRouteMapMatchInterfaceNumber OBJECT-TYPE
        SYNTAX        Integer32
        MAX-ACCESS        read-write
        STATUS        current
        DESCRIPTION   ""
        ::= { rcIpRouteMapEntry 8 }

rcIpRouteMapMatchIpAddress OBJECT-TYPE
        SYNTAX        IdList
        MAX-ACCESS        read-write
        STATUS        current
        DESCRIPTION   ""
        ::= { rcIpRouteMapEntry 9 }

rcIpRouteMapMatchIpRouteSource OBJECT-TYPE
        SYNTAX        IdList
        MAX-ACCESS        read-write
        STATUS        current
        DESCRIPTION   ""
        ::= { rcIpRouteMapEntry 10 }

rcIpRouteMapMatchNextHop OBJECT-TYPE
        SYNTAX        IdList
        MAX-ACCESS        read-write
        STATUS        current
        DESCRIPTION   ""
        ::= { rcIpRouteMapEntry 11 }

rcIpRouteMapMatchRouteType OBJECT-TYPE
        SYNTAX        INTEGER {
                          none(0),
                          local(1),
                          internal(2),
                          external(3),
                          externaltype1(4),
                          externaltype2(5)
                      }
        MAX-ACCESS        read-write
        STATUS        current
        DESCRIPTION   ""
        ::= { rcIpRouteMapEntry 12 }

rcIpRouteMapMatchMetric OBJECT-TYPE
        SYNTAX        Integer32
        MAX-ACCESS        read-write
        STATUS        current
        DESCRIPTION   "Match metric of the route."
        ::= { rcIpRouteMapEntry 13 }

rcIpRouteMapMatchTag OBJECT-TYPE
        SYNTAX        DisplayString
        MAX-ACCESS        read-write
        STATUS        current
        DESCRIPTION   "contains one or more tag values.."
        ::= { rcIpRouteMapEntry 14 }

rcIpRouteMapSetAsPath OBJECT-TYPE
        SYNTAX        DisplayString
        MAX-ACCESS        read-write
        STATUS        current
        DESCRIPTION   "as-path string.."
        ::= { rcIpRouteMapEntry 15 }

rcIpRouteMapSetAsPathMode OBJECT-TYPE
        SYNTAX        INTEGER {
                          tag(1),
                          prepend(2)
                      }
        MAX-ACCESS        read-write
        STATUS        current
        DESCRIPTION   ""
        ::= { rcIpRouteMapEntry 16 }

rcIpRouteMapSetAutomaticTag OBJECT-TYPE
        SYNTAX        EnableValue
        MAX-ACCESS        read-write
        STATUS        current
        DESCRIPTION   ""
        ::= { rcIpRouteMapEntry 17 }

rcIpRouteMapSetCommunityNumber OBJECT-TYPE
        SYNTAX        Integer32
        MAX-ACCESS        read-write
        STATUS        current
        DESCRIPTION   "community number."
        ::= { rcIpRouteMapEntry 18 }

rcIpRouteMapSetCommunityMode OBJECT-TYPE
        SYNTAX        INTEGER {
                          none(0),
                          append(1)
                      }
        MAX-ACCESS        read-write
        STATUS        current
        DESCRIPTION   ""
        ::= { rcIpRouteMapEntry 19 }

rcIpRouteMapSetCommunityDelListId OBJECT-TYPE
        SYNTAX        Integer32
        MAX-ACCESS        read-write
        STATUS        current
        DESCRIPTION   ""
        ::= { rcIpRouteMapEntry 20 }

rcIpRouteMapSetDampening OBJECT-TYPE
        SYNTAX        EnableValue
        MAX-ACCESS        read-write
        STATUS        current
        DESCRIPTION   "enable/disable route dampening
                       for the routes that passed match
                       criteria"
        ::= { rcIpRouteMapEntry 21 }

rcIpRouteMapSetDampeningHalflife OBJECT-TYPE
        SYNTAX        INTEGER (1..45)
        MAX-ACCESS        read-write
        STATUS        current
        DESCRIPTION   ""
        DEFVAL        { 15 }
        ::= { rcIpRouteMapEntry 22 }

rcIpRouteMapSetDampeningReuse OBJECT-TYPE
        SYNTAX        INTEGER (1..20000)
        MAX-ACCESS        read-write
        STATUS        current
        DESCRIPTION   "penalty value"
        DEFVAL        { 750 }
        ::= { rcIpRouteMapEntry 23 }

rcIpRouteMapSetDampeningSuppress OBJECT-TYPE
        SYNTAX        INTEGER (1..20000)
        MAX-ACCESS        read-write
        STATUS        current
        DESCRIPTION   "penalty value"
        DEFVAL        { 2000 }
        ::= { rcIpRouteMapEntry 24 }

rcIpRouteMapSetDampeningMaxSuppressTime OBJECT-TYPE
        SYNTAX        Integer32
        MAX-ACCESS        read-write
        STATUS        current
        DESCRIPTION   "time in minutes."
        DEFVAL        { 60 }
        ::= { rcIpRouteMapEntry 25 }

rcIpRouteMapSetMetricTypeInternal OBJECT-TYPE
        SYNTAX        Integer32
        MAX-ACCESS        read-write
        STATUS        current
        DESCRIPTION   ""
        ::= { rcIpRouteMapEntry 26 }

rcIpRouteMapSetMetric OBJECT-TYPE
        SYNTAX        Integer32
        MAX-ACCESS        read-write
        STATUS        current
        DESCRIPTION   ""
        ::= { rcIpRouteMapEntry 27 }

rcIpRouteMapSetMetricType OBJECT-TYPE
        SYNTAX        INTEGER {
                          type1(1),
                          type2(2)
                      }
        MAX-ACCESS        read-write
        STATUS        current
        DESCRIPTION   ""
        ::= { rcIpRouteMapEntry 28 }

rcIpRouteMapSetNextHop OBJECT-TYPE
        SYNTAX        IpAddress
        MAX-ACCESS        read-write
        STATUS        current
        DESCRIPTION   "IpAddress of the next hop router."
        ::= { rcIpRouteMapEntry 29 }

rcIpRouteMapSetOrigin OBJECT-TYPE
        SYNTAX        INTEGER {
                          igp(1),
                          egp(2),
                          incomplete(3)
                      }
        MAX-ACCESS        read-write
        STATUS        current
        DESCRIPTION   ""
        ::= { rcIpRouteMapEntry 30 }

rcIpRouteMapSetOriginEgpAs OBJECT-TYPE
        SYNTAX        Integer32
        MAX-ACCESS        read-write
        STATUS        current
        DESCRIPTION   "Remote Autonomous system number."
        ::= { rcIpRouteMapEntry 31 }

rcIpRouteMapSetTag OBJECT-TYPE
        SYNTAX        Integer32
        MAX-ACCESS        read-write
        STATUS        current
        DESCRIPTION   ""
        ::= { rcIpRouteMapEntry 32 }

rcIpRouteMapSetWeight OBJECT-TYPE
        SYNTAX        Integer32
        MAX-ACCESS        read-write
        STATUS        current
        DESCRIPTION   ""
        ::= { rcIpRouteMapEntry 33 }

rcIpRouteMapRowStatus OBJECT-TYPE
        SYNTAX        RowStatus
        MAX-ACCESS        read-write
        STATUS        current
        DESCRIPTION   "row status"
        ::= { rcIpRouteMapEntry 34 }


-- Ip Redistribute Table

rcIpRedistributeTableSize OBJECT-TYPE
        SYNTAX        Integer32
        MAX-ACCESS        read-only
        STATUS        current
        DESCRIPTION   "table size"
        ::= { rcIpGenPolicy 14 }

rcIpRedistributeTable OBJECT-TYPE 
        SYNTAX          SEQUENCE OF RcIpRedistributeEntry
        MAX-ACCESS          not-accessible 
        STATUS          current 
        DESCRIPTION     "IP Redistribute table"
        ::= { rcIpGenPolicy 15 }

rcIpRedistributeEntry OBJECT-TYPE
        SYNTAX        	RcIpRedistributeEntry
        MAX-ACCESS        	not-accessible
        STATUS        	current
        DESCRIPTION   	"An entry of Ip Redistribute Table."
        INDEX         	{ rcIpRedistributeRouteSource,
                          rcIpRedistributeProtocol }
        ::= { rcIpRedistributeTable 1 }
 
RcIpRedistributeEntry ::=
        SEQUENCE {
                rcIpRedistributeRouteSource      INTEGER,
                rcIpRedistributeProtocol         INTEGER,
                rcIpRedistributeMetric           INTEGER,
                rcIpRedistributeMetricType       INTEGER,
                rcIpRedistributeMatchRouteType   INTEGER,
                rcIpRedistributeSetTag           INTEGER,
                rcIpRedistributeSubnets          INTEGER,
                rcIpRedistributeRouteMap         DisplayString,
                rcIpRedistributeASNumber         INTEGER,
                rcIpRedistributeWeight           INTEGER,
                rcIpRedistributeDefaultOriginate INTEGER,
                rcIpRedistributeRowStatus        RowStatus
        }
 
rcIpRedistributeRouteSource OBJECT-TYPE
        SYNTAX        INTEGER {
                          connected(1),
                          static(2),
                          rip(3),
                          ospf(4),
                          bgp(5)
                      }
        MAX-ACCESS        read-only
        STATUS        current
        DESCRIPTION   "Route map id"
        ::= { rcIpRedistributeEntry 1 }

rcIpRedistributeProtocol OBJECT-TYPE
        SYNTAX        INTEGER {
                          rip(1),
                          ospf(2),
                          bgp(3)
                      }
        MAX-ACCESS        read-only
        STATUS        current
        DESCRIPTION   "Protocol"
        ::= { rcIpRedistributeEntry 2 }

rcIpRedistributeMetric OBJECT-TYPE
        SYNTAX        Integer32
        MAX-ACCESS        read-write
        STATUS        current
        DESCRIPTION   ""
        ::= { rcIpRedistributeEntry 3 }

rcIpRedistributeMetricType OBJECT-TYPE
        SYNTAX        INTEGER {
                          type1(1),
                          type2(2)
                      }
        MAX-ACCESS        read-write
        STATUS        current
        DESCRIPTION   ""
        ::= { rcIpRedistributeEntry 4 }

rcIpRedistributeMatchRouteType OBJECT-TYPE
        SYNTAX        INTEGER {
                          internal(1),
                          external1(2),
                          external2(3)
                      }
        MAX-ACCESS        read-write
        STATUS        current
        DESCRIPTION   ""
        ::= { rcIpRedistributeEntry 5 }

rcIpRedistributeSetTag OBJECT-TYPE
        SYNTAX        Integer32
        MAX-ACCESS        read-write
        STATUS        current
        DESCRIPTION   ""
        ::= { rcIpRedistributeEntry 6 }

rcIpRedistributeSubnets OBJECT-TYPE
        SYNTAX        Integer32
        MAX-ACCESS        read-write
        STATUS        current
        DESCRIPTION   "for OSPF only"
        ::= { rcIpRedistributeEntry 7 }

rcIpRedistributeRouteMap OBJECT-TYPE
        SYNTAX        DisplayString
        MAX-ACCESS        read-write
        STATUS        current
        DESCRIPTION   "Route map name"
        ::= { rcIpRedistributeEntry 8 }

rcIpRedistributeASNumber OBJECT-TYPE
        SYNTAX        Integer32
        MAX-ACCESS        read-write
        STATUS        current
        DESCRIPTION   "Autonomous system number"
        ::= { rcIpRedistributeEntry 9 }

rcIpRedistributeWeight OBJECT-TYPE
        SYNTAX        Integer32
        MAX-ACCESS        read-write
        STATUS        current
        DESCRIPTION   ""
        ::= { rcIpRedistributeEntry 10 }

rcIpRedistributeDefaultOriginate OBJECT-TYPE
        SYNTAX        Integer32
        MAX-ACCESS        read-write
        STATUS        current
        DESCRIPTION   ""
        ::= { rcIpRedistributeEntry 11 }

rcIpRedistributeRowStatus OBJECT-TYPE
        SYNTAX        RowStatus
        MAX-ACCESS        read-write
        STATUS        current
        DESCRIPTION   "row status"
        ::= { rcIpRedistributeEntry 12 }

-- IP Distribute In Table

rcIpDistributeInTableSize OBJECT-TYPE
        SYNTAX        Integer32
        MAX-ACCESS        read-only
        STATUS        current
        DESCRIPTION   "table size"
        ::= { rcIpGenPolicy 16 }

rcIpDistributeInTable OBJECT-TYPE 
        SYNTAX          SEQUENCE OF RcIpDistributeInEntry
        MAX-ACCESS          not-accessible 
        STATUS          current 
        DESCRIPTION     "IP Distribute In table"
        ::= { rcIpGenPolicy 17 }

rcIpDistributeInEntry OBJECT-TYPE
        SYNTAX        	RcIpDistributeInEntry
        MAX-ACCESS        	not-accessible
        STATUS        	current
        DESCRIPTION   	"An entry of Ip Distribute In Table."
        INDEX         	{ rcIpDistributeInProtocol,
                          rcIpDistributeInInterfaceNumber }
        ::= { rcIpDistributeInTable 1 }
 
RcIpDistributeInEntry ::=
        SEQUENCE {
                rcIpDistributeInProtocol        INTEGER,
                rcIpDistributeInInterfaceNumber InterfaceIndex,
                rcIpDistributeInIpAccessListId  INTEGER
        }
 
rcIpDistributeInProtocol OBJECT-TYPE
        SYNTAX        INTEGER {
                          rip(1),
                          ospf(2),
                          bgp(3)
                      }
        MAX-ACCESS        read-only
        STATUS        current
        DESCRIPTION   "Protocol"
        ::= { rcIpDistributeInEntry 1 }

rcIpDistributeInInterfaceNumber OBJECT-TYPE
        SYNTAX        InterfaceIndex
        MAX-ACCESS        read-write
        STATUS        current
        DESCRIPTION   "IfIndex"
        ::= { rcIpDistributeInEntry 2 }

rcIpDistributeInIpAccessListId OBJECT-TYPE
        SYNTAX        Integer32
        MAX-ACCESS        read-write
        STATUS        current
        DESCRIPTION   ""
        ::= { rcIpDistributeInEntry 3 }

-- IP Distribute Out Table

rcIpDistributeOutTableSize OBJECT-TYPE
        SYNTAX        Integer32
        MAX-ACCESS        read-only
        STATUS        current
        DESCRIPTION   "table size"
        ::= { rcIpGenPolicy 18 }

rcIpDistributeOutTable OBJECT-TYPE 
        SYNTAX          SEQUENCE OF RcIpDistributeOutEntry
        MAX-ACCESS          not-accessible 
        STATUS          current 
        DESCRIPTION     "IP Distribute Out table"
        ::= { rcIpGenPolicy 19 }

rcIpDistributeOutEntry OBJECT-TYPE
        SYNTAX        	RcIpDistributeOutEntry
        MAX-ACCESS        	not-accessible
        STATUS        	current
        DESCRIPTION   	"An entry of Ip Distribute In Table."
        INDEX         	{ rcIpDistributeOutProtocol,
                          rcIpDistributeOutInterfaceNumber,
                          rcIpDistributeOutRouteSource }
        ::= { rcIpDistributeOutTable 1 }
 
RcIpDistributeOutEntry ::=
        SEQUENCE {
                rcIpDistributeOutProtocol        INTEGER,
                rcIpDistributeOutInterfaceNumber InterfaceIndex,
                rcIpDistributeOutRouteSource     INTEGER,
                rcIpDistributeOutIpAccessListId  INTEGER
        }
 
rcIpDistributeOutProtocol OBJECT-TYPE
        SYNTAX        INTEGER {
                          rip(1),
                          ospf(2),
                          bgp(3)
                      }
        MAX-ACCESS        read-only
        STATUS        current
        DESCRIPTION   "Protocol"
        ::= { rcIpDistributeOutEntry 1 }

rcIpDistributeOutInterfaceNumber OBJECT-TYPE
        SYNTAX        InterfaceIndex
        MAX-ACCESS        read-write
        STATUS        current
        DESCRIPTION   "IfIndex"
        ::= { rcIpDistributeOutEntry 2 }

rcIpDistributeOutRouteSource OBJECT-TYPE
        SYNTAX        INTEGER {
                          static(1),
                          connected(2),
                          rip(3),
                          ospf(4),
                          bgp(5)
                      }
        MAX-ACCESS        read-write
        STATUS        current
        DESCRIPTION   ""
        ::= { rcIpDistributeOutEntry 3 }

rcIpDistributeOutIpAccessListId OBJECT-TYPE
        SYNTAX        Integer32
        MAX-ACCESS        read-write
        STATUS        current
        DESCRIPTION   ""
        ::= { rcIpDistributeOutEntry 4 }


-- Ip BGP

rcIpBgp OBJECT IDENTIFIER ::= { rcIp 101 }

rcIpBgpGeneralGroup OBJECT IDENTIFIER ::= { rcIpBgp 1 }

rcIpBgpGeneralGroupLocalAs OBJECT-TYPE
        SYNTAX        Integer32
        MAX-ACCESS        read-write
        STATUS        current
        DESCRIPTION   "Autonomous system number"
        ::= { rcIpBgpGeneralGroup 1 }

rcIpBgpGeneralGroupAdminStatus OBJECT-TYPE
        SYNTAX        EnableValue
        MAX-ACCESS        read-write
        STATUS        current
        DESCRIPTION   ""
        ::= { rcIpBgpGeneralGroup 2 }

rcIpBgpGeneralGroupSynchronization OBJECT-TYPE
        SYNTAX        EnableValue
        MAX-ACCESS        read-write
        STATUS        current
        DESCRIPTION   ""
        ::= { rcIpBgpGeneralGroup 3 }

rcIpBgpGeneralGroupAction OBJECT-TYPE
        SYNTAX        INTEGER {
                          none(0),
                          resetallpeers(1)
                      }
        MAX-ACCESS        read-write
        STATUS        current
        DESCRIPTION   ""
        ::= { rcIpBgpGeneralGroup 4 }

rcIpBgpGeneralGroupDefaultMetric OBJECT-TYPE
        SYNTAX        Integer32
        MAX-ACCESS        read-write
        STATUS        current
        DESCRIPTION   "Set the value to MED."
        ::= { rcIpBgpGeneralGroup 5 }

rcIpBgpGeneralGroupFastExternalFallover OBJECT-TYPE
        SYNTAX        TruthValue
        MAX-ACCESS        read-write
        STATUS        current
        DESCRIPTION   "Automatically reset the ebgp session
                       upon detecting link failure."
        ::= { rcIpBgpGeneralGroup 6 }

rcIpBgpGeneralGroupTableMap OBJECT-TYPE
        SYNTAX        DisplayString
        MAX-ACCESS        read-write
        STATUS        current
        DESCRIPTION   "RouteMap name to be applied while
                       updating the IP routing table with
                       bgp routes. (modify metric & tag)."
        ::= { rcIpBgpGeneralGroup 7 }

rcIpBgpGeneralGroupKeepAliveTimer OBJECT-TYPE
        SYNTAX        Integer32
        MAX-ACCESS        read-write
        STATUS        current
        DESCRIPTION   "Global KeepAlive Timer value."
        ::= { rcIpBgpGeneralGroup 8 }

rcIpBgpGeneralGroupHoldDownTimer OBJECT-TYPE
        SYNTAX        Integer32
        MAX-ACCESS        read-write
        STATUS        current
        DESCRIPTION   "Global HoldDown Timer value."
        ::= { rcIpBgpGeneralGroup 9 }

rcIpBgpGeneralGroupDefaultLocalPreference OBJECT-TYPE
        SYNTAX        Integer32
        MAX-ACCESS        read-write
        STATUS        current
        DESCRIPTION   "Local preference Attribute value."
        ::= { rcIpBgpGeneralGroup 10 }

rcIpBgpGeneralGroupDefaultInformationOriginate OBJECT-TYPE
        SYNTAX        TruthValue
        MAX-ACCESS        read-write
        STATUS        current
        DESCRIPTION   "allow the redist ri-bution of
                       default route into BGP."
        ::= { rcIpBgpGeneralGroup 11 }

rcIpBgpGeneralGroupBestPathAsPathComp OBJECT-TYPE
        SYNTAX        EnableValue
        MAX-ACCESS        read-write
        STATUS        current
        DESCRIPTION   ""
        ::= { rcIpBgpGeneralGroup 12 }

rcIpBgpGeneralGroupBestPathMissingAsWorst OBJECT-TYPE
        SYNTAX        EnableValue
        MAX-ACCESS        read-write
        STATUS        current
        DESCRIPTION   "enable indicates a path missing MED
                       means AsPathLenght of infinity this
                       makes the path least desirable."
        ::= { rcIpBgpGeneralGroup 13 }

rcIpBgpGeneralGroupBestPathMedConfed OBJECT-TYPE
        SYNTAX        EnableValue
        MAX-ACCESS        read-write
        STATUS        current
        DESCRIPTION   "consider MED in selecting a path."
        ::= { rcIpBgpGeneralGroup 14 }

rcIpBgpGeneralGroupAlwaysCompareMed OBJECT-TYPE
        SYNTAX        EnableValue
        MAX-ACCESS        read-write
        STATUS        current
        DESCRIPTION   ""
        ::= { rcIpBgpGeneralGroup 15 }

rcIpBgpGeneralGroupDeterministicMed OBJECT-TYPE
        SYNTAX        EnableValue
        MAX-ACCESS        read-write
        STATUS        current
        DESCRIPTION   ""
        ::= { rcIpBgpGeneralGroup 16 }


rcIpBgpAdminstrativeDistanceGroup OBJECT IDENTIFIER ::= { rcIpBgp 2 }

rcIpBgpAdminstrativeDistanceExternalDistance OBJECT-TYPE
        SYNTAX        Integer32
        MAX-ACCESS        read-write
        STATUS        current
        DESCRIPTION   "routes learned from external bgp nbrs"
        ::= { rcIpBgpAdminstrativeDistanceGroup 1 }

rcIpBgpAdminstrativeDistanceInternalDistance OBJECT-TYPE
        SYNTAX        Integer32
        MAX-ACCESS        read-write
        STATUS        current
        DESCRIPTION   "routes learned from internal bgp nbrs"
        ::= { rcIpBgpAdminstrativeDistanceGroup 2 }

rcIpBgpAdminstrativeDistanceLocalDistance OBJECT-TYPE
        SYNTAX        Integer32
        MAX-ACCESS        read-write
        STATUS        current
        DESCRIPTION   "routes local bgp routes (part of localAS)"
        ::= { rcIpBgpAdminstrativeDistanceGroup 3 }


rcIpBgpAggregateAddressGroup OBJECT IDENTIFIER ::= { rcIpBgp 3 }

rcIpBgpAggregateAddressEnable OBJECT-TYPE
        SYNTAX        TruthValue
        MAX-ACCESS        read-write
        STATUS        current
        DESCRIPTION   "True/False - aggregation"
        ::= { rcIpBgpAggregateAddressGroup 1 }

rcIpBgpAggregateAddressMask OBJECT-TYPE
        SYNTAX        IpAddress
        MAX-ACCESS        read-write
        STATUS        current
        DESCRIPTION   "mask value"
        ::= { rcIpBgpAggregateAddressGroup 2 }

rcIpBgpAggregateAddressAsSetGenerate OBJECT-TYPE
        SYNTAX        EnableValue
        MAX-ACCESS        read-write
        STATUS        current
        DESCRIPTION   ""
        ::= { rcIpBgpAggregateAddressGroup 3 }

rcIpBgpAggregateAddressSummaryOnly OBJECT-TYPE
        SYNTAX        EnableValue
        MAX-ACCESS        read-write
        STATUS        current
        DESCRIPTION   ""
        ::= { rcIpBgpAggregateAddressGroup 4 }

rcIpBgpAggregateAddressSuppressMap OBJECT-TYPE
        SYNTAX        DisplayString
        MAX-ACCESS        read-write
        STATUS        current
        DESCRIPTION   ""
        ::= { rcIpBgpAggregateAddressGroup 5 }

rcIpBgpAggregateAddressAdvertiseMap OBJECT-TYPE
        SYNTAX        DisplayString
        MAX-ACCESS        read-write
        STATUS        current
        DESCRIPTION   ""
        ::= { rcIpBgpAggregateAddressGroup 6 }

rcIpBgpAggregateAddressAttributeMap OBJECT-TYPE
        SYNTAX        DisplayString
        MAX-ACCESS        read-write
        STATUS        current
        DESCRIPTION   ""
        ::= { rcIpBgpAggregateAddressGroup 7 }


rcIpBgpConfederationGroup OBJECT IDENTIFIER ::= { rcIpBgp 4 }

rcIpBgponfederationIdentifier OBJECT-TYPE
        SYNTAX        Integer32
        MAX-ACCESS        read-write
        STATUS        current
        DESCRIPTION   "TAutonomous system number"
        ::= { rcIpBgpConfederationGroup 1 }

rcIpBgponfederationPeerASList OBJECT-TYPE
        SYNTAX        Integer32
        MAX-ACCESS        read-write
        STATUS        current
        DESCRIPTION   ""
        ::= { rcIpBgpConfederationGroup 2 }


rcIpBgpRouteReflectorGroup OBJECT IDENTIFIER ::= { rcIpBgp 5 }

rcIpBgpRouteReflectorClusterId OBJECT-TYPE
        SYNTAX        IpAddress
        MAX-ACCESS        read-write
        STATUS        current
        DESCRIPTION   "4-byte clusterID"
        ::= { rcIpBgpRouteReflectorGroup 1 }

rcIpBgpRouteReflectorClientToClientReflection OBJECT-TYPE
        SYNTAX        EnableValue
        MAX-ACCESS        read-write
        STATUS        current
        DESCRIPTION   ""
        ::= { rcIpBgpRouteReflectorGroup 2 }


rcIpBgpRouteDampeningGroup OBJECT IDENTIFIER ::= { rcIpBgp 6 }

rcIpBgpRouteDampeningEnable OBJECT-TYPE
        SYNTAX        TruthValue
        MAX-ACCESS        read-write
        STATUS        current
        DESCRIPTION   ""
        ::= { rcIpBgpRouteDampeningGroup 1 }

rcIpBgpRouteDampeningHalfLifeValue OBJECT-TYPE
        SYNTAX        INTEGER (1..45)
        MAX-ACCESS        read-write
        STATUS        current
        DESCRIPTION   "Time in minutes"
	DEFVAL        { 15 }
        ::= { rcIpBgpRouteDampeningGroup 2 }

rcIpBgpRouteDampeningReUseValue OBJECT-TYPE
        SYNTAX        INTEGER (1..20000)
        MAX-ACCESS        read-write
        STATUS        current
        DESCRIPTION   "Penalty value"
	DEFVAL        { 750 }
        ::= { rcIpBgpRouteDampeningGroup 3 }

rcIpBgpRouteDampeningSuppress OBJECT-TYPE
        SYNTAX        Integer32
        MAX-ACCESS        read-write
        STATUS        current
        DESCRIPTION   "Suppress Value"
	DEFVAL        { 2000 }
        ::= { rcIpBgpRouteDampeningGroup 4 }

rcIpBgpRouteDampeningSuppressMax OBJECT-TYPE
        SYNTAX        INTEGER (1..20000)
        MAX-ACCESS        read-write
        STATUS        current
        DESCRIPTION   "time in minutes"
	DEFVAL        { 60 }
        ::= { rcIpBgpRouteDampeningGroup 5 }

rcIpBgpRouteDampeningRouteMap OBJECT-TYPE
        SYNTAX        DisplayString
        MAX-ACCESS        read-write
        STATUS        current
        DESCRIPTION   "Route map name to be used to"
        ::= { rcIpBgpRouteDampeningGroup 6 }


-- IP Bdp Networks Table

rcIpBgpNetworkTableSize OBJECT-TYPE
        SYNTAX        Integer32
        MAX-ACCESS        read-only
        STATUS        current
        DESCRIPTION   "table size"
        ::= { rcIpBgp 7 }

rcIpBgpNetworkTable OBJECT-TYPE 
        SYNTAX          SEQUENCE OF RcIpBgpNetworkEntry
        MAX-ACCESS          not-accessible 
        STATUS          current 
        DESCRIPTION     "IP Bdp Networks table"
        ::= { rcIpBgp 8 }

rcIpBgpNetworkEntry OBJECT-TYPE
        SYNTAX        	RcIpBgpNetworkEntry
        MAX-ACCESS        	not-accessible
        STATUS        	current
        DESCRIPTION   	"An entry of Ip Bdp In Table."
        INDEX         	{ rcIpBgpNetworkNetAddr,
                          rcIpBgpNetworkMask }
        ::= { rcIpBgpNetworkTable 1 }
 
RcIpBgpNetworkEntry ::=
        SEQUENCE {
                rcIpBgpNetworkNetAddr  IpAddress,
                rcIpBgpNetworkMask     IpAddress,
                rcIpBgpNetworkWeight   INTEGER,
                rcIpBgpNetworkRouteMap DisplayString
        }
 
rcIpBgpNetworkNetAddr OBJECT-TYPE
        SYNTAX        IpAddress
        MAX-ACCESS        read-only
        STATUS        current
        DESCRIPTION   ""
        ::= { rcIpBgpNetworkEntry 1 }

rcIpBgpNetworkMask OBJECT-TYPE
        SYNTAX        IpAddress
        MAX-ACCESS        read-only
        STATUS        current
        DESCRIPTION   ""
        ::= { rcIpBgpNetworkEntry 2 }

rcIpBgpNetworkWeight OBJECT-TYPE
        SYNTAX        Integer32
        MAX-ACCESS        read-write
        STATUS        current
        DESCRIPTION   ""
        ::= { rcIpBgpNetworkEntry 3 }

rcIpBgpNetworkRouteMap OBJECT-TYPE
        SYNTAX        DisplayString
        MAX-ACCESS        read-write
        STATUS        current
        DESCRIPTION   "route-map name"
        ::= { rcIpBgpNetworkEntry 4 }

-- IP Bdp Peers Table

rcIpBgpPeerTableSize OBJECT-TYPE
        SYNTAX        Integer32
        MAX-ACCESS        read-only
        STATUS        current
        DESCRIPTION   "table size"
        ::= { rcIpBgp 9 }

rcIpBgpPeerTable OBJECT-TYPE 
        SYNTAX          SEQUENCE OF RcIpBgpPeerEntry
        MAX-ACCESS          not-accessible 
        STATUS          current 
        DESCRIPTION     "IP Bdp Peers table"
        ::= { rcIpBgp 10 }

rcIpBgpPeerEntry OBJECT-TYPE
        SYNTAX        	RcIpBgpPeerEntry
        MAX-ACCESS        	not-accessible
        STATUS        	current
        DESCRIPTION   	"An entry of Ip Bdp In Table."
        INDEX         	{ rcIpBgpPeerIpAddress }
        ::= { rcIpBgpPeerTable 1 }
 
RcIpBgpPeerEntry ::=
        SEQUENCE {
                rcIpBgpPeerIpAddress             IpAddress,
                rcIpBgpPeerRemoteAs              INTEGER,
                rcIpBgpPeerDiscription           DisplayString,
                rcIpBgpPeerPeerGroupName         DisplayString,
                rcIpBgpPeerDefaultOriginate      EnableValue,
                rcIpBgpPeerSendCommunity         EnableValue,
                rcIpBgpPeerUpdateSource          IpAddress,
                rcIpBgpPeerEbgpMultiHop          EnableValue,
                rcIpBgpPeerAdvertisementInterval INTEGER,
                rcIpBgpPeerPassword              DisplayString,
                rcIpBgpPeerWeight                INTEGER,
                rcIpBgpPeerAction                INTEGER,
                rcIpBgpPeerFilterInListId        INTEGER,
                rcIpBgpPeerFilterOutListId       INTEGER,
                rcIpBgpPeerFilterWeightListId    INTEGER,
                rcIpBgpPeerFilterWeight          INTEGER,
                rcIpBgpPeerDistributeInListId    INTEGER,
                rcIpBgpPeerDistributeOutListId   INTEGER,
                rcIpBgpPeerPrefixInListId        INTEGER,
                rcIpBgpPeerPrefixOutListId       INTEGER,
                rcIpBgpPeerNextHopSelf           EnableValue,
                rcIpBgpPeerRouteMapIn            DisplayString,
                rcIpBgpPeerRouteMapOut           DisplayString,
                rcIpBgpPeerRouteReflectorClient  TruthValue,
                rcIpBgpPeerShutDown              TruthValue,
                rcIpBgpPeerKeepAliveTimer        INTEGER,
                rcIpBgpPeerHoldDownTimer         INTEGER
        }
 
rcIpBgpPeerIpAddress OBJECT-TYPE
        SYNTAX        IpAddress
        MAX-ACCESS        read-only
        STATUS        current
        DESCRIPTION   ""
        ::= { rcIpBgpPeerEntry 1 }

rcIpBgpPeerRemoteAs OBJECT-TYPE
        SYNTAX        Integer32
        MAX-ACCESS        read-write
        STATUS        current
        DESCRIPTION   "Remote Autonomous system number"
        ::= { rcIpBgpPeerEntry 2 }

rcIpBgpPeerDiscription OBJECT-TYPE
        SYNTAX        DisplayString
        MAX-ACCESS        read-write
        STATUS        current
        DESCRIPTION   "Neighbor discription"
        ::= { rcIpBgpPeerEntry 3 }

rcIpBgpPeerPeerGroupName OBJECT-TYPE
        SYNTAX        DisplayString
        MAX-ACCESS        read-write
        STATUS        current
        DESCRIPTION   "Peer group name"
        ::= { rcIpBgpPeerEntry 4 }

rcIpBgpPeerDefaultOriginate OBJECT-TYPE
        SYNTAX        EnableValue
        MAX-ACCESS        read-write
        STATUS        current
        DESCRIPTION   ""
        ::= { rcIpBgpPeerEntry 5 }

rcIpBgpPeerSendCommunity OBJECT-TYPE
        SYNTAX        EnableValue
        MAX-ACCESS        read-write
        STATUS        current
        DESCRIPTION   ""
        ::= { rcIpBgpPeerEntry 6 }

rcIpBgpPeerUpdateSource OBJECT-TYPE
        SYNTAX        IpAddress
        MAX-ACCESS        read-only
        STATUS        current
        DESCRIPTION   "Loop back interface."
        ::= { rcIpBgpPeerEntry 7 }

rcIpBgpPeerEbgpMultiHop OBJECT-TYPE
        SYNTAX        EnableValue
        MAX-ACCESS        read-write
        STATUS        current
        DESCRIPTION   ""
        ::= { rcIpBgpPeerEntry 8 }

rcIpBgpPeerAdvertisementInterval OBJECT-TYPE
        SYNTAX        Integer32
        MAX-ACCESS        read-write
        STATUS        current
        DESCRIPTION   "min interval between advert"
        ::= { rcIpBgpPeerEntry 9 }

rcIpBgpPeerPassword OBJECT-TYPE
        SYNTAX        DisplayString
        MAX-ACCESS        read-write
        STATUS        current
        DESCRIPTION   "simple password/MD5"
        ::= { rcIpBgpPeerEntry 10 }

rcIpBgpPeerWeight OBJECT-TYPE
        SYNTAX        Integer32
        MAX-ACCESS        read-write
        STATUS        current
        DESCRIPTION   ""
        ::= { rcIpBgpPeerEntry 11 }

rcIpBgpPeerAction OBJECT-TYPE
        SYNTAX        INTEGER {
                          none(0),
                          reset(1),
                          shutdown(2)
                      }
        MAX-ACCESS        read-write
        STATUS        current
        DESCRIPTION   ""
        ::= { rcIpBgpPeerEntry 12 }

rcIpBgpPeerFilterInListId OBJECT-TYPE
        SYNTAX        Integer32
        MAX-ACCESS        read-write
        STATUS        current
        DESCRIPTION   ""
        ::= { rcIpBgpPeerEntry 13 }

rcIpBgpPeerFilterOutListId OBJECT-TYPE
        SYNTAX        Integer32
        MAX-ACCESS        read-write
        STATUS        current
        DESCRIPTION   ""
        ::= { rcIpBgpPeerEntry 14 }

rcIpBgpPeerFilterWeightListId OBJECT-TYPE
        SYNTAX        Integer32
        MAX-ACCESS        read-write
        STATUS        current
        DESCRIPTION   ""
        ::= { rcIpBgpPeerEntry 15 }

rcIpBgpPeerFilterWeight OBJECT-TYPE
        SYNTAX        Integer32
        MAX-ACCESS        read-write
        STATUS        current
        DESCRIPTION   "Weight to be assigned."
        ::= { rcIpBgpPeerEntry 16 }

rcIpBgpPeerDistributeInListId OBJECT-TYPE
        SYNTAX        Integer32
        MAX-ACCESS        read-write
        STATUS        current
        DESCRIPTION   ""
        ::= { rcIpBgpPeerEntry 17 }

rcIpBgpPeerDistributeOutListId OBJECT-TYPE
        SYNTAX        Integer32
        MAX-ACCESS        read-write
        STATUS        current
        DESCRIPTION   ""
        ::= { rcIpBgpPeerEntry 18 }

rcIpBgpPeerPrefixInListId OBJECT-TYPE
        SYNTAX        Integer32
        MAX-ACCESS        read-write
        STATUS        current
        DESCRIPTION   ""
        ::= { rcIpBgpPeerEntry 19 }

rcIpBgpPeerPrefixOutListId OBJECT-TYPE
        SYNTAX        Integer32
        MAX-ACCESS        read-write
        STATUS        current
        DESCRIPTION   ""
        ::= { rcIpBgpPeerEntry 20 }

rcIpBgpPeerNextHopSelf OBJECT-TYPE
        SYNTAX        EnableValue
        MAX-ACCESS        read-write
        STATUS        current
        DESCRIPTION   ""
        ::= { rcIpBgpPeerEntry 21 }

rcIpBgpPeerRouteMapIn OBJECT-TYPE
        SYNTAX        DisplayString
        MAX-ACCESS        read-write
        STATUS        current
        DESCRIPTION   ""
        ::= { rcIpBgpPeerEntry 22 }

rcIpBgpPeerRouteMapOut OBJECT-TYPE
        SYNTAX        DisplayString
        MAX-ACCESS        read-write
        STATUS        current
        DESCRIPTION   ""
        ::= { rcIpBgpPeerEntry 23 }

rcIpBgpPeerRouteReflectorClient OBJECT-TYPE
        SYNTAX        TruthValue
        MAX-ACCESS        read-write
        STATUS        current
        DESCRIPTION   ""
        ::= { rcIpBgpPeerEntry 24 }

rcIpBgpPeerShutDown OBJECT-TYPE
        SYNTAX        TruthValue
        MAX-ACCESS        read-write
        STATUS        current
        DESCRIPTION   ""
        ::= { rcIpBgpPeerEntry 25 }

rcIpBgpPeerKeepAliveTimer OBJECT-TYPE
        SYNTAX        Integer32
        MAX-ACCESS        read-write
        STATUS        current
        DESCRIPTION   "KeepAlive Timer value."
        ::= { rcIpBgpPeerEntry 26 }

rcIpBgpPeerHoldDownTimer OBJECT-TYPE
        SYNTAX        Integer32
        MAX-ACCESS        read-write
        STATUS        current
        DESCRIPTION   "HoldDown Timer value."
        ::= { rcIpBgpPeerEntry 27 }

-- IP Bdp Peer Group Table

rcIpBgpPeerGroupTableSize OBJECT-TYPE
        SYNTAX        Integer32
        MAX-ACCESS        read-only
        STATUS        current
        DESCRIPTION   "table size"
        ::= { rcIpBgp 11 }

rcIpBgpPeerGroupTable OBJECT-TYPE 
        SYNTAX          SEQUENCE OF RcIpBgpPeerGroupEntry
        MAX-ACCESS          not-accessible 
        STATUS          current 
        DESCRIPTION     "IP Bdp Peer Group table"
        ::= { rcIpBgp 12 }

rcIpBgpPeerGroupEntry OBJECT-TYPE
        SYNTAX        	RcIpBgpPeerGroupEntry
        MAX-ACCESS        	not-accessible
        STATUS        	current
        DESCRIPTION   	"An entry of Ip Bdp Peer Group Table."
        INDEX         	{ rcIpBgpPeerGroupId, rcIpBgpPeerGroupMemberIpAddr }
        ::= { rcIpBgpPeerGroupTable 1 }
 
RcIpBgpPeerGroupEntry ::=
        SEQUENCE {
                rcIpBgpPeerGroupId            INTEGER,
                rcIpBgpPeerGroupMemberIpAddr  IpAddress,
                rcIpBgpPeerGroupMemberListId  INTEGER,
                rcIpBgpPeerGroupName          DisplayString
        }
 
rcIpBgpPeerGroupId OBJECT-TYPE
        SYNTAX        Integer32
        MAX-ACCESS        read-only
        STATUS        current
        DESCRIPTION   "Peer Group id"
        ::= { rcIpBgpPeerGroupEntry 1 }

rcIpBgpPeerGroupMemberIpAddr OBJECT-TYPE
        SYNTAX        IpAddress
        MAX-ACCESS        read-only
        STATUS        current
        DESCRIPTION   "IpAddress of the member"
        ::= { rcIpBgpPeerGroupEntry 2 }

rcIpBgpPeerGroupMemberListId OBJECT-TYPE
        SYNTAX        Integer32
        MAX-ACCESS        read-write
        STATUS        current
        DESCRIPTION   ""
        ::= { rcIpBgpPeerGroupEntry 3 }

rcIpBgpPeerGroupName OBJECT-TYPE
        SYNTAX        DisplayString
        MAX-ACCESS        read-write
        STATUS        current
        DESCRIPTION   "Name of the peer group"
        ::= { rcIpBgpPeerGroupEntry 4 }


-- IP Bdp Debug Table

rcIpBgpDebugTableSize OBJECT-TYPE
        SYNTAX        Integer32
        MAX-ACCESS        read-only
        STATUS        current
        DESCRIPTION   "table size"
        ::= { rcIpBgp 13 }

rcIpBgpDebugTable OBJECT-TYPE 
        SYNTAX          SEQUENCE OF RcIpBgpDebugEntry
        MAX-ACCESS          not-accessible 
        STATUS          current 
        DESCRIPTION     "IP Bdp Debug table"
        ::= { rcIpBgp 14 }

rcIpBgpDebugEntry OBJECT-TYPE
        SYNTAX        	RcIpBgpDebugEntry
        MAX-ACCESS        	not-accessible
        STATUS        	current
        DESCRIPTION   	"An entry of Ip Bdp Debug Table."
        INDEX         	{ rcIpBgpDebugLocalAddr, rcIpBgpDebugRemoteAddr }
        ::= { rcIpBgpDebugTable 1 }
 
RcIpBgpDebugEntry ::=
        SEQUENCE {
                rcIpBgpDebugLocalAddr        EnableValue,
                rcIpBgpDebugRemoteAddr       EnableValue,
                rcIpBgpDebugEvents           EnableValue,
                rcIpBgpDebugKeepAlives       EnableValue,
                rcIpBgpDebugUpdates          EnableValue,
                rcIpBgpDebugUpdatesListId    INTEGER,
                rcIpBgpDebugDampening        EnableValue,
                rcIpBgpDebugDampeningListId  INTEGER
        }
 
rcIpBgpDebugLocalAddr OBJECT-TYPE
        SYNTAX        EnableValue
        MAX-ACCESS        read-write
        STATUS        current
        DESCRIPTION   ""
        ::= { rcIpBgpDebugEntry 1 }

rcIpBgpDebugRemoteAddr OBJECT-TYPE
        SYNTAX        EnableValue
        MAX-ACCESS        read-write
        STATUS        current
        DESCRIPTION   ""
        ::= { rcIpBgpDebugEntry 2 }

rcIpBgpDebugEvents OBJECT-TYPE
        SYNTAX        EnableValue
        MAX-ACCESS        read-write
        STATUS        current
        DESCRIPTION   ""
        ::= { rcIpBgpDebugEntry 3 }

rcIpBgpDebugKeepAlives OBJECT-TYPE
        SYNTAX        EnableValue
        MAX-ACCESS        read-write
        STATUS        current
        DESCRIPTION   ""
        ::= { rcIpBgpDebugEntry 4 }

rcIpBgpDebugUpdates OBJECT-TYPE
        SYNTAX        EnableValue
        MAX-ACCESS        read-write
        STATUS        current
        DESCRIPTION   ""
        ::= { rcIpBgpDebugEntry 5 }

rcIpBgpDebugUpdatesListId OBJECT-TYPE
        SYNTAX        Integer32
        MAX-ACCESS        read-write
        STATUS        current
        DESCRIPTION   ""
        ::= { rcIpBgpDebugEntry 6 }

rcIpBgpDebugDampening OBJECT-TYPE
        SYNTAX        EnableValue
        MAX-ACCESS        read-write
        STATUS        current
        DESCRIPTION   ""
        ::= { rcIpBgpDebugEntry 7 }

rcIpBgpDebugDampeningListId OBJECT-TYPE
        SYNTAX        Integer32
        MAX-ACCESS        read-write
        STATUS        current
        DESCRIPTION   ""
        ::= { rcIpBgpDebugEntry 8 }


-- ARP Group

rcArpExtLifeTime OBJECT-TYPE
        SYNTAX        Integer32
        MAX-ACCESS        read-write
        STATUS        current
        DESCRIPTION   "The lifetime in minutues of an ARP entry within the 
                      system."
        ::= { rcArp 1 }

rcArpExtTable OBJECT-TYPE
        SYNTAX        SEQUENCE OF RcArpExtEntry
        MAX-ACCESS        not-accessible
        STATUS        current
        DESCRIPTION   "ARP extension table.  This table augments the
		      standard ipNetToMediaTable defined in RFC1213."
        ::= { rcArp 2 }

rcArpExtEntry OBJECT-TYPE
        SYNTAX        RcArpExtEntry
        MAX-ACCESS        not-accessible
        STATUS        current
        DESCRIPTION   "Entry containing Proprietary ARP information.  
                      An entry is automatically created in this table 
                      when an ip address is configured on an interface." 
        INDEX         { rcArpExtEntIfIndex }
        ::= { rcArpExtTable 1 }

RcArpExtEntry ::=
        SEQUENCE {
                rcArpExtEntIfIndex InterfaceIndex,
                rcArpExtEntDoProxy INTEGER,
                rcArpExtEntDoResp INTEGER
        }

rcArpExtEntIfIndex OBJECT-TYPE
        SYNTAX        InterfaceIndex
        MAX-ACCESS        read-only
        STATUS        current
        DESCRIPTION   "The index value which uniquely identifies the
                      interface to which this entry is applicable.
                      The interface identified by a particular value
                      of this index is the same interface as 
                      identified by the same value of ifIndex."
        ::= { rcArpExtEntry 1 }
 
rcArpExtEntDoProxy OBJECT-TYPE
        SYNTAX        INTEGER {
		         disable(1),
			 enable(2)
		      }
        MAX-ACCESS        read-write
        STATUS        current
        DESCRIPTION   "Enable or disable ARP proxy responses on the
		      specified interface."
	DEFVAL        { disable }
        ::= { rcArpExtEntry 2 }
 
rcArpExtEntDoResp OBJECT-TYPE
        SYNTAX        INTEGER {
			 disable(1),
			 enable(2)
		      }
        MAX-ACCESS        read-write
        STATUS        current
        DESCRIPTION   "Enable or disable the sending of ARP responses
		      on the specified interface."
	DEFVAL        { enable }
        ::= { rcArpExtEntry 3 }

-- rcArpExtV2Table

rcArpExtV2Table OBJECT-TYPE
        SYNTAX        SEQUENCE OF RcArpExtV2Entry
        MAX-ACCESS        not-accessible
        STATUS        current
        DESCRIPTION   "ARP extension table.  This table augments the
		      standard ipNetToMediaTable defined in RFC1213."
        ::= { rcArp 3 }

rcArpExtV2Entry OBJECT-TYPE
        SYNTAX        RcArpExtV2Entry
        MAX-ACCESS        not-accessible
        STATUS        current
        DESCRIPTION   "Entry containing Proprietary ARP information.  
                      An entry is automatically created in this table 
                      when an ip address is configured on an interface." 
        INDEX         { rcArpExtV2EntIfIndex, rcArpExtV2EntIpIfAddr }
        ::= { rcArpExtV2Table 1 }

RcArpExtV2Entry ::=
        SEQUENCE {
                rcArpExtV2EntIfIndex InterfaceIndex,
                rcArpExtV2EntIpIfAddr IpAddress,
                rcArpExtV2EntDoProxy INTEGER,
                rcArpExtV2EntDoResp INTEGER
        }

rcArpExtV2EntIfIndex OBJECT-TYPE
        SYNTAX        InterfaceIndex
        MAX-ACCESS        read-only
        STATUS        current
        DESCRIPTION   "The index value which uniquely identifies the
                      interface to which this entry is applicable.
                      The interface identified by a particular value
                      of this index is the same interface as 
                      identified by the same value of ifIndex."
        ::= { rcArpExtV2Entry 1 }
 
rcArpExtV2EntIpIfAddr OBJECT-TYPE
        SYNTAX        IpAddress
        MAX-ACCESS        read-only
        STATUS        current
        DESCRIPTION   "Ip Address"
        ::= { rcArpExtV2Entry 2 }
 
rcArpExtV2EntDoProxy OBJECT-TYPE
        SYNTAX        INTEGER {
		         disable(1),
			 enable(2)
		      }
        MAX-ACCESS        read-write
        STATUS        current
        DESCRIPTION   "Enable or disable ARP proxy responses on the
		      specified interface."
	DEFVAL        { disable }
        ::= { rcArpExtV2Entry 3 }
 
rcArpExtV2EntDoResp OBJECT-TYPE
        SYNTAX        INTEGER {
			 disable(1),
			 enable(2)
		      }
        MAX-ACCESS        read-write
        STATUS        current
        DESCRIPTION   "Enable or disable the sending of ARP responses
		      on the specified interface."
	DEFVAL        { enable }
        ::= { rcArpExtV2Entry 4 }


-- RIP Group

rcRipExtOperation OBJECT-TYPE
        SYNTAX        INTEGER	{
                         disable(1),
                         enable(2)
	 	      }
        MAX-ACCESS        read-write
        STATUS        current
        DESCRIPTION   "Enable or disable the operation of RIP on all
		      Interfaces."
        ::= { rcRip 1 }

rcRipExtUpdateTime OBJECT-TYPE
        SYNTAX        Integer32
        MAX-ACCESS        read-write
        STATUS        current
        DESCRIPTION   "The time between transmission of RIP updates
		      on all interfaces."
        ::= { rcRip 2 }

rcRipExtTable OBJECT-TYPE
        SYNTAX        SEQUENCE OF RcRipExtEntry
        MAX-ACCESS        not-accessible
        STATUS        current
        DESCRIPTION   "RIP extension table.  This table augments the
		      standard IfConfTable table in RFC1389."
        ::= { rcRip 3 }

rcRipExtEntry OBJECT-TYPE
        SYNTAX        RcRipExtEntry
        MAX-ACCESS        not-accessible
        STATUS        current
        DESCRIPTION   "Entry containing Proprietary RIP information.  
	  	      An entry is automatically created in this table 
                      when an ip address is configured on an interface."
        INDEX         { rcRipExtEntIfIndex }
        ::= { rcRipExtTable 1 }

RcRipExtEntry ::=
        SEQUENCE {
                rcRipExtEntIfIndex InterfaceIndex,
                rcRipExtEntTalk INTEGER,
                rcRipExtEntListen INTEGER,
                rcRipExtEntPoison INTEGER
        }

rcRipExtEntIfIndex OBJECT-TYPE
        SYNTAX        InterfaceIndex
        MAX-ACCESS        read-only
        STATUS        current
        DESCRIPTION   "The index value which uniquely identifies the
                      interface to which this entry is applicable.
                      The interface identified by a particular value
                      of this index is the same interface as 
                      identified by the same value of ifIndex."
        ::= { rcRipExtEntry 1 }
 
rcRipExtEntTalk OBJECT-TYPE
        SYNTAX       INTEGER {
                        disable(1),
                        enable(2)
		      }	
        MAX-ACCESS        read-write
        STATUS        current
        DESCRIPTION   "Enable or disable RIP transmission on the
		      specified interface."
	DEFVAL        { enable }
        ::= { rcRipExtEntry 2 }
 
rcRipExtEntListen OBJECT-TYPE
        SYNTAX        INTEGER {
                         disable(1),
                         enable(2)
		      }
        MAX-ACCESS        read-write
        STATUS        current
        DESCRIPTION   "Enable or disable RIP reception on the specified
		      interface."
	DEFVAL        { enable }
        ::= { rcRipExtEntry 3 }

rcRipExtEntPoison OBJECT-TYPE
        SYNTAX        INTEGER {
                         disable(1),
                         enable(2)
                      } 
        MAX-ACCESS        read-write
        STATUS        current
        DESCRIPTION   "Enable or disable operation of poison reverse
		      on the specified interface.  If poison is
		      disabled, split-horizon operation is enabled."
	DEFVAL        { disable }
        ::= { rcRipExtEntry 4 }

-- rcRipExtV2Table

rcRipExtV2Table OBJECT-TYPE
        SYNTAX        SEQUENCE OF RcRipExtV2Entry
        MAX-ACCESS        not-accessible
        STATUS        current
        DESCRIPTION   "RIP extension table.  This table augments the
		      standard IfConfTable table in RFC1389."
        ::= { rcRip 4 }

rcRipExtV2Entry OBJECT-TYPE
        SYNTAX        RcRipExtV2Entry
        MAX-ACCESS        not-accessible
        STATUS        current
        DESCRIPTION   "Entry containing Proprietary RIP information.  
	  	      An entry is automatically created in this table 
                      when an ip address is configured on an interface."
        INDEX         { rcRipExtV2EntIfIndex, rcRipExtV2EntIpIfAddr }
        ::= { rcRipExtV2Table 1 }

RcRipExtV2Entry ::=
        SEQUENCE {
                rcRipExtV2EntIfIndex InterfaceIndex,
                rcRipExtV2EntIpIfAddr IpAddress,
                rcRipExtV2EntTalk INTEGER,
                rcRipExtV2EntListen INTEGER,
                rcRipExtV2EntPoison INTEGER
        }

rcRipExtV2EntIfIndex OBJECT-TYPE
        SYNTAX        InterfaceIndex
        MAX-ACCESS        read-only
        STATUS        current
        DESCRIPTION   "The index value which uniquely identifies the
                      interface to which this entry is applicable.
                      The interface identified by a particular value
                      of this index is the same interface as 
                      identified by the same value of ifIndex."
        ::= { rcRipExtV2Entry 1 }
 
rcRipExtV2EntIpIfAddr OBJECT-TYPE
        SYNTAX        IpAddress
        MAX-ACCESS        read-only
        STATUS        current
        DESCRIPTION   "Ip Address."
        ::= { rcRipExtV2Entry 2 }
 
rcRipExtV2EntTalk OBJECT-TYPE
        SYNTAX       INTEGER {
                        disable(1),
                        enable(2)
		      }	
        MAX-ACCESS        read-write
        STATUS        current
        DESCRIPTION   "Enable or disable RIP transmission on the
		      specified interface."
	DEFVAL        { enable }
        ::= { rcRipExtV2Entry 3 }
 
rcRipExtV2EntListen OBJECT-TYPE
        SYNTAX        INTEGER {
                         disable(1),
                         enable(2)
		      }
        MAX-ACCESS        read-write
        STATUS        current
        DESCRIPTION   "Enable or disable RIP reception on the specified
		      interface."
	DEFVAL        { enable }
        ::= { rcRipExtV2Entry 4 }

rcRipExtV2EntPoison OBJECT-TYPE
        SYNTAX        INTEGER {
                         disable(1),
                         enable(2)
                      } 
        MAX-ACCESS        read-write
        STATUS        current
        DESCRIPTION   "Enable or disable operation of poison reverse
		      on the specified interface.  If poison is
		      disabled, split-horizon operation is enabled."
	DEFVAL        { disable }
        ::= { rcRipExtV2Entry 5 }

-- Test Group

rcTestExtTable OBJECT-TYPE
        SYNTAX        SEQUENCE OF RcTestEntry
        MAX-ACCESS        not-accessible
        STATUS        current
        DESCRIPTION   "Test extension table.  This table augments the
                      standard ifTestTable table in RFC1573."
        ::= { rcTest 1 }
 
rcTestEntry OBJECT-TYPE
        SYNTAX        RcTestEntry
        MAX-ACCESS        not-accessible
        STATUS        current    
        DESCRIPTION   "Proprietary test variables."
        INDEX         { rcTestExtIfIndex }
        ::= { rcTestExtTable 1 }
 
RcTestEntry ::=
        SEQUENCE {
                rcTestExtIfIndex InterfaceIndex,
                rcTestExtPassCount INTEGER,  
                rcTestExtFailCount INTEGER
        }
 
rcTestExtIfIndex OBJECT-TYPE
        SYNTAX        InterfaceIndex
        MAX-ACCESS        read-only
        STATUS        current
        DESCRIPTION   "The index value which uniquely identifies the
                      interface to which this entry is applicable.
                      The interface identified by a particular value
                      of this index is the same interface as
                      identified by the same value of ifIndex."
        ::= { rcTestEntry 1 }

rcTestExtPassCount OBJECT-TYPE
	SYNTAX        Integer32
	MAX-ACCESS	      read-only
	STATUS	      current
	DESCRIPTION   "The number of iterations of the test case that
		      completed successfully."
	::= { rcTestEntry 2}

rcTestExtFailCount OBJECT-TYPE
        SYNTAX        Integer32
        MAX-ACCESS        read-only
        STATUS        current
        DESCRIPTION   "The number of iterations of the test case that
                      failed."
        ::= { rcTestEntry 3}


rcTestTypes		OBJECT IDENTIFIER	::= { rcTest 2}
rcTestTypesFabric	OBJECT IDENTIFIER	::= { rcTestTypes 1 }
rcTestTypesArTable	OBJECT IDENTIFIER	::= { rcTestTypes 2 }
rcTestTypesExtLoopBack	OBJECT IDENTIFIER	::= { rcTestTypes 3 }


rcTestCodes		OBJECT IDENTIFIER	::= { rcTest 3 }
rcTestCodesNoReceive	OBJECT IDENTIFIER	::= { rcTestCodes 1 }
rcTestCodesBadSeq	OBJECT IDENTIFIER	::= { rcTestCodes 2 }
rcTestCodesBadLen	OBJECT IDENTIFIER	::= { rcTestCodes 3 }
rcTestCodesBadData	OBJECT IDENTIFIER	::= { rcTestCodes 4 }


-- Statistics

rcStatTable OBJECT-TYPE
        SYNTAX        SEQUENCE OF RcStatEntry
        MAX-ACCESS        not-accessible
        STATUS        current
        DESCRIPTION   "A table used to store port statistics."
        ::= { rcStat 1 }
 
rcStatEntry OBJECT-TYPE
        SYNTAX        RcStatEntry
        MAX-ACCESS        not-accessible
        STATUS        current
        DESCRIPTION   "interface counters"
        INDEX         { rcStatPortIndex }
        ::= { rcStatTable 1 }
 
RcStatEntry ::= SEQUENCE {
                rcStatPortIndex            	InterfaceIndex,
                rcStatFrameTooShorts       	Counter32,
 		rcStatBridgeInUnicastFrames	Counter32,
 		rcStatBridgeInMulticastFrames	Counter32,
 		rcStatBridgeInBroadcastFrames	Counter32,
 		rcStatBridgeInDiscards		Counter32,
 		rcStatBridgeOutUnicastFrames	Counter32,
 		rcStatBridgeOutMulticastFrames	Counter32,
 		rcStatBridgeOutBroadcastFrames	Counter32,
 		rcStatRouteInUnicastFrames	Counter32,
 		rcStatRouteInMulticastFrames	Counter32,
 		rcStatRouteInDiscards		Counter32,
 		rcStatRouteOutUnicastFrames	Counter32,
 		rcStatRouteOutMulticastFrames 	Counter32,
		rcStatStgForwardTransitions     Counter32,
		rcStatStgInConfigBpdus          Counter32,
		rcStatStgInTcnBpdus             Counter32,
		rcStatStgInBadBpdus             Counter32,
		rcStatStgOutConfigBpdus         Counter32,
		rcStatStgOutTcnBpdus            Counter32,
		rcStatBridgeOutFrames           Counter32
        }
 
rcStatPortIndex OBJECT-TYPE
        SYNTAX        InterfaceIndex
        MAX-ACCESS        read-only
        STATUS        current
        DESCRIPTION   "An index value that uniquely identifies a port.
                      This value is similar to ifIndex in MIB2."
        ::= { rcStatEntry 1 }
 
rcStatFrameTooShorts OBJECT-TYPE
        SYNTAX        Counter32
        MAX-ACCESS        read-only
        STATUS        current
        DESCRIPTION   "The total number of frames that are too short 
                      that were encountered on this interface."
        ::= { rcStatEntry 2 }

rcStatBridgeInUnicastFrames OBJECT-TYPE
        SYNTAX        Counter32
        MAX-ACCESS        read-only
        STATUS        current
        DESCRIPTION   "The total number of incoming unicast frames that 
		      were bridged."
        ::= { rcStatEntry 3 }

rcStatBridgeInMulticastFrames OBJECT-TYPE 
        SYNTAX        Counter32 
        MAX-ACCESS        read-only
        STATUS        current 
        DESCRIPTION   "The total number of incoming multicast frames that 
                      were bridged."
        ::= { rcStatEntry 4 }

rcStatBridgeInBroadcastFrames OBJECT-TYPE 
        SYNTAX        Counter32 
        MAX-ACCESS        read-only
        STATUS        current 
        DESCRIPTION   "The total number of incoming broadcast frames that 
                      were bridged."
        ::= { rcStatEntry 5 }

rcStatBridgeInDiscards OBJECT-TYPE 
        SYNTAX        Counter32 
        MAX-ACCESS        read-only
        STATUS        current 
        DESCRIPTION   "The total number of frames that were discarded by
		      the bridging entity."
        ::= { rcStatEntry 6 }

rcStatBridgeOutUnicastFrames OBJECT-TYPE 
        SYNTAX        Counter32 
        MAX-ACCESS        read-only
        STATUS        current 
        DESCRIPTION   "The total number of outgoing unicast frames that 
                      were bridged."
        ::= { rcStatEntry 7 }

rcStatBridgeOutMulticastFrames OBJECT-TYPE 
        SYNTAX        Counter32 
        MAX-ACCESS        read-only
        STATUS        current 
        DESCRIPTION   "The total number of outgoing multicast frames that 
                      were bridged."
        ::= { rcStatEntry 8 }

rcStatBridgeOutBroadcastFrames OBJECT-TYPE 
        SYNTAX        Counter32 
        MAX-ACCESS        read-only
        STATUS        current 
        DESCRIPTION   "The total number of outgoing broadcast frames that 
                      were bridged."
        ::= { rcStatEntry 9 }

rcStatRouteInUnicastFrames OBJECT-TYPE 
        SYNTAX        Counter32 
        MAX-ACCESS        read-only
        STATUS        current 
        DESCRIPTION   "The total number of incoming unicast frames that
                      were routed."
        ::= { rcStatEntry 10 }

rcStatRouteInMulticastFrames OBJECT-TYPE 
        SYNTAX        Counter32 
        MAX-ACCESS        read-only
        STATUS        current 
        DESCRIPTION   "The total number of incoming multicast frames that
                      were routed."
        ::= { rcStatEntry 11 }

rcStatRouteInDiscards OBJECT-TYPE 
        SYNTAX        Counter32 
        MAX-ACCESS        read-only
        STATUS        current 
        DESCRIPTION   "The total number of frames that were discarded by
		      the routing entity."
        ::= { rcStatEntry 12 }

rcStatRouteOutUnicastFrames OBJECT-TYPE 
        SYNTAX        Counter32 
        MAX-ACCESS        read-only
        STATUS        current 
        DESCRIPTION   "The total number of outgoing unicast frames that
                      were routed."
        ::= { rcStatEntry 13 }

rcStatRouteOutMulticastFrames OBJECT-TYPE 
        SYNTAX        Counter32 
        MAX-ACCESS        read-only
        STATUS        current 
        DESCRIPTION   "The total number of outgoing multicast frames that
                      were routed."
        ::= { rcStatEntry 14 }

rcStatStgForwardTransitions OBJECT-TYPE 
        SYNTAX        Counter32 
        MAX-ACCESS        read-only
        STATUS        current 
        DESCRIPTION   "The number of times this port has transitioned
                      from the Learning state to the Forwarding state."
        ::= { rcStatEntry 15 }

rcStatStgInConfigBpdus OBJECT-TYPE 
        SYNTAX        Counter32 
        MAX-ACCESS        read-only
        STATUS        current 
        DESCRIPTION   ""
        ::= { rcStatEntry 16 }

rcStatStgInTcnBpdus OBJECT-TYPE 
        SYNTAX        Counter32 
        MAX-ACCESS        read-only
        STATUS        current 
        DESCRIPTION   ""
        ::= { rcStatEntry 17 }

rcStatStgInBadBpdus OBJECT-TYPE 
        SYNTAX        Counter32 
        MAX-ACCESS        read-only
        STATUS        current 
        DESCRIPTION   ""
        ::= { rcStatEntry 18 }

rcStatStgOutConfigBpdus OBJECT-TYPE 
        SYNTAX        Counter32 
        MAX-ACCESS        read-only
        STATUS        current 
        DESCRIPTION   ""
        ::= { rcStatEntry 19 }

rcStatStgOutTcnBpdus OBJECT-TYPE 
        SYNTAX        Counter32 
        MAX-ACCESS        read-only
        STATUS        current 
        DESCRIPTION   ""
        ::= { rcStatEntry 20 }

rcStatBridgeOutFrames OBJECT-TYPE 
        SYNTAX        Counter32 
        MAX-ACCESS        read-only
        STATUS        current 
        DESCRIPTION     "Used by the Accelar 8000 product family to account
                        for all transmitted bridge unicast, broadcast, and
                        multicast packets.  The individual counters are not
                        supported."

        ::= { rcStatEntry 21 }


-- rcStatGigTable

rcStatGigTable OBJECT-TYPE
        SYNTAX        SEQUENCE OF RcStatGigEntry
        MAX-ACCESS        not-accessible
        STATUS        current
        DESCRIPTION   "A table used to store Gigport error statistics."
        ::= { rcStat 2 } 
 
rcStatGigEntry OBJECT-TYPE  
        SYNTAX        RcStatGigEntry
        MAX-ACCESS        not-accessible
        STATUS        current
        DESCRIPTION   "Gigabit interface error counters"
        INDEX         { rcStatGigPortIndex }
        ::= { rcStatGigTable 1 }
 
RcStatGigEntry ::= SEQUENCE {
		rcStatGigPortIndex            InterfaceIndex,
		rcStatGigLinkFailures         Counter32,
		rcStatGigPacketErrors         Counter32,
		rcStatGigCarrierErrors        Counter32,
		rcStatGigLinkInactiveErrors   Counter32,
                rcStatGigInFlowCtrlPkts       Counter32,
                rcStatGigOutFlowCtrlPkts      Counter32
        }

rcStatGigPortIndex OBJECT-TYPE
        SYNTAX        InterfaceIndex
        MAX-ACCESS        read-only
        STATUS        current
        DESCRIPTION   "An index value that uniquely identifies a port.
                      This value is similar to ifIndex in MIB2."
        ::= { rcStatGigEntry 1 }

rcStatGigLinkFailures OBJECT-TYPE
        SYNTAX        Counter32
        MAX-ACCESS        read-only
        STATUS        current
        DESCRIPTION   "The total number of link failures encountered on 
                      this interface."
        ::= { rcStatGigEntry 2 }

rcStatGigPacketErrors OBJECT-TYPE
        SYNTAX        Counter32
        MAX-ACCESS        read-only
        STATUS        current
        DESCRIPTION   "The total number of packet errors encountered on 
                      this interface."
        ::= { rcStatGigEntry 3 }

rcStatGigCarrierErrors OBJECT-TYPE
        SYNTAX        Counter32
        MAX-ACCESS        read-only
        STATUS        current
        DESCRIPTION   "The total number of carrier errors encountered on 
                      this interface."
        ::= { rcStatGigEntry 4 }

rcStatGigLinkInactiveErrors OBJECT-TYPE
        SYNTAX        Counter32
        MAX-ACCESS        read-only
        STATUS        current
        DESCRIPTION   "The total number of link inactive errors encountered 
                       on this interface."
        ::= { rcStatGigEntry 5 }

rcStatGigInFlowCtrlPkts OBJECT-TYPE
        SYNTAX        Counter32
        MAX-ACCESS        read-only
        STATUS        current
        DESCRIPTION   "The total number of flow control packets received
                         by this interface."
        ::= { rcStatGigEntry 6 }

rcStatGigOutFlowCtrlPkts OBJECT-TYPE
        SYNTAX        Counter32
        MAX-ACCESS        read-only
        STATUS        current
        DESCRIPTION   "The total number of flow control packets transmitted 
                       by this interface."
        ::= { rcStatGigEntry 7 }

rcStatOspf   OBJECT IDENTIFIER       ::= { rcStat 3}
 
rcStatOspfBuffersAllocated OBJECT-TYPE
        SYNTAX        Counter32
        MAX-ACCESS        read-only
        STATUS        current
        DESCRIPTION   "Used to indicate the number of buffers
                      allocated for OSPF."
        ::= { rcStatOspf 1 }
 
rcStatOspfBuffersFreed OBJECT-TYPE
        SYNTAX        Counter32
        MAX-ACCESS        read-only
        STATUS        current
        DESCRIPTION   "Used to indicate the number of buffers
                      that are freed by the OSPF."
        ::= { rcStatOspf 2 }
 
rcStatOspfBufferAllocFailures OBJECT-TYPE
        SYNTAX        Counter32
        MAX-ACCESS        read-only
        STATUS        current
        DESCRIPTION   "Used to indicate the number of times
                      that OSPF has failed to allocate buffers."
        ::= { rcStatOspf 3 }
 
rcStatOspfBufferFreeFailures OBJECT-TYPE
        SYNTAX        Counter32
        MAX-ACCESS        read-only
        STATUS        current
        DESCRIPTION   "Used to indicate the number of times
                      that OSPF has failed to free buffers."
        ::= { rcStatOspf 4 }
 
rcStatOspfTxPackets OBJECT-TYPE
        SYNTAX        Counter32
        MAX-ACCESS        read-only
        STATUS        current
        DESCRIPTION   "Used to indicate the number of packets
                      transmitted by OSPF."
        ::= { rcStatOspf 5 }
 
 
rcStatOspfRxPackets OBJECT-TYPE
        SYNTAX        Counter32
        MAX-ACCESS        read-only
        STATUS        current
        DESCRIPTION   "Used to indicate the number of packets
                      received by OSPF."
        ::= { rcStatOspf 6 }
 
rcStatOspfTxDropPackets OBJECT-TYPE
        SYNTAX        Counter32
        MAX-ACCESS        read-only
        STATUS        current
        DESCRIPTION   "Used to indicate the number of packets
                      dropped before transmitted by OSPF."
        ::= { rcStatOspf 7 }
 
 
rcStatOspfRxDropPackets OBJECT-TYPE
        SYNTAX        Counter32
        MAX-ACCESS        read-only
        STATUS        current
        DESCRIPTION   "Used to indicate the number of packets
                      dropped before received by OSPF."
        ::= { rcStatOspf 8 }
 
rcStatOspfRxBadPackets OBJECT-TYPE
        SYNTAX        Counter32
        MAX-ACCESS        read-only
        STATUS        current
        DESCRIPTION   "Used to indicate the number of packets
                      received by OSPF that are bad."
        ::= { rcStatOspf 9 }
 
rcStatOspfSpfRuns OBJECT-TYPE
        SYNTAX        Counter32
        MAX-ACCESS        read-only
        STATUS        current
        DESCRIPTION   "Used to indicate the number of SPF
                      calculatations performed by OSPF."
        ::= { rcStatOspf 10 }
 
rcStatOspfLastSpfRun OBJECT-TYPE
        SYNTAX        TimeTicks
        MAX-ACCESS        read-only
        STATUS        current
        DESCRIPTION   "Used to indicate the time(SysUpTime) since
                      the last spf calculated by OSPF."
        ::= { rcStatOspf 11 }
 
rcStatIgmp   OBJECT IDENTIFIER       ::= { rcStat 4}

rcStatIgmpInMsgs OBJECT-TYPE
        SYNTAX          Counter32
        MAX-ACCESS          read-only
        STATUS          current
        DESCRIPTION     "Used to indicate the number of Igmp packets
                         received by the device."
        ::= { rcStatIgmp 1 }

rcStatIgmpInErrors OBJECT-TYPE
        SYNTAX          Counter32
        MAX-ACCESS          read-only
        STATUS          current
        DESCRIPTION     "Used to indicate the number of Igmp packets
                         received that are with checksum errors."
        ::= { rcStatIgmp 2 }

rcStatIgmpInQueries OBJECT-TYPE
        SYNTAX          Counter32
        MAX-ACCESS          read-only
        STATUS          current
        DESCRIPTION     "Used to indicate the number of Igmp queries
                         received by the device."
        ::= { rcStatIgmp 3 }

rcStatIgmpInReports OBJECT-TYPE
        SYNTAX          Counter32
        MAX-ACCESS          read-only
        STATUS          current
        DESCRIPTION     "Used to indicate the number of Igmp reports
                         received by the device."
        ::= { rcStatIgmp 4 }


rcStatIgmpInLeaves OBJECT-TYPE
        SYNTAX          Counter32
        MAX-ACCESS          read-only
        STATUS          current
        DESCRIPTION     "Used to indicate the number of Igmp Leaves
                         received by the device."
        ::= { rcStatIgmp 5 }

rcStatIgmpInvalid OBJECT-TYPE
        SYNTAX          Counter32
        MAX-ACCESS          read-only
        STATUS          current
        DESCRIPTION     "Used to indicate the number of Igmp packets
                         received by the device that contained invalid
                         type."
        ::= { rcStatIgmp 6 }

rcStatIgmpOutMsgs OBJECT-TYPE
        SYNTAX          Counter32
        MAX-ACCESS          read-only
        STATUS          current
        DESCRIPTION     "Used to indicate the number of Igmp queries
                         sent by the device."
        ::= { rcStatIgmp 7 }

rcStatOspfLsdbTblSize OBJECT-TYPE
        SYNTAX        Counter32
        MAX-ACCESS        read-only
        STATUS        current
        DESCRIPTION   "Used to indicate the number of entries in
                      the linkstate database table."
        ::= { rcStatOspf 12 }
 
 
rcStatOspfIfTable OBJECT-TYPE
        SYNTAX        SEQUENCE OF RcStatOspfIfEntry
        MAX-ACCESS        not-accessible
        STATUS        current
        DESCRIPTION   "A table used to store OSPF interface
                      statistics."
        ::= { rcStat 5 }
 
rcStatOspfIfEntry OBJECT-TYPE
        SYNTAX        RcStatOspfIfEntry
        MAX-ACCESS        not-accessible
        STATUS        current
        DESCRIPTION   "Ospf interface statistics"
        INDEX         { rcStatOspfIfIndex }
        ::= { rcStatOspfIfTable 1 }
 
RcStatOspfIfEntry ::= SEQUENCE {
                rcStatOspfIfIndex                   InterfaceIndex,
                rcStatOspfIfRxHellos                Counter32,
                rcStatOspfIfRxDBDescrs              Counter32,
                rcStatOspfIfRxLSUpdates             Counter32,
                rcStatOspfIfRxLSReqs                Counter32,
                rcStatOspfIfRxLSAcks                Counter32,
                rcStatOspfIfTxHellos                Counter32,
                rcStatOspfIfTxDBDescrs              Counter32,
                rcStatOspfIfTxLSUpdates             Counter32,
                rcStatOspfIfTxLSReqs                Counter32,
                rcStatOspfIfTxLSAcks                Counter32,
                rcStatOspfIfVersionMismatches       Counter32,
                rcStatOspfIfAreaMismatches          Counter32,
                rcStatOspfIfAuthTypeMismatches      Counter32,
                rcStatOspfIfAuthFailures            Counter32,
                rcStatOspfIfNetMaskMismatches       Counter32,
                rcStatOspfIfHelloIntervalMismatches Counter32,
                rcStatOspfIfDeadIntervalMismatches  Counter32,
                rcStatOspfIfOptionMismatches        Counter32
        }
 
rcStatOspfIfIndex OBJECT-TYPE
        SYNTAX        InterfaceIndex (0..4094)
        MAX-ACCESS        read-only
        STATUS        current
        DESCRIPTION   "An unique value that is used to identify a
                      physical interface."
        ::= { rcStatOspfIfEntry 1 }
 
rcStatOspfIfRxHellos OBJECT-TYPE
        SYNTAX        Counter32
        MAX-ACCESS        read-only
        STATUS        current
        DESCRIPTION   "Used to indicate the number hello packets
                      received by this interface."
        ::= { rcStatOspfIfEntry 2 }

rcStatOspfIfRxDBDescrs OBJECT-TYPE
        SYNTAX        Counter32
        MAX-ACCESS        read-only
        STATUS        current
        DESCRIPTION   "Used to indicate the number database descriptor
                      packets received by this interface."
        ::= { rcStatOspfIfEntry 3 }
 
rcStatOspfIfRxLSUpdates OBJECT-TYPE
        SYNTAX        Counter32
        MAX-ACCESS        read-only
        STATUS        current
        DESCRIPTION   "Used to indicate the number Link state update
                      packets received by this interface."
        ::= { rcStatOspfIfEntry 4 }
 
rcStatOspfIfRxLSReqs OBJECT-TYPE
        SYNTAX        Counter32
        MAX-ACCESS        read-only
        STATUS        current
        DESCRIPTION   "Used to indicate the number Link state request
                      packets received by this interface."
        ::= { rcStatOspfIfEntry 5 }
 
rcStatOspfIfRxLSAcks OBJECT-TYPE
        SYNTAX        Counter32
        MAX-ACCESS        read-only
        STATUS        current
        DESCRIPTION   "Used to indicate the number Link state acknowlege
                      packets received by this interface."
        ::= { rcStatOspfIfEntry 6 }
 
rcStatOspfIfTxHellos OBJECT-TYPE
        SYNTAX        Counter32
        MAX-ACCESS        read-only
        STATUS        current
        DESCRIPTION   "Used to indicate the number hello packets
                      transmitted by this interface."
        ::= { rcStatOspfIfEntry 7 }
 
rcStatOspfIfTxDBDescrs OBJECT-TYPE
        SYNTAX        Counter32
        MAX-ACCESS        read-only
        STATUS        current
        DESCRIPTION   "Used to indicate the number database descriptor
                      packets transmitted by this interface."
        ::= { rcStatOspfIfEntry 8 }
 
rcStatOspfIfTxLSUpdates OBJECT-TYPE
        SYNTAX        Counter32
        MAX-ACCESS        read-only
        STATUS        current
        DESCRIPTION   "Used to indicate the number Link state update
                      packets transmitted by this interface."
        ::= { rcStatOspfIfEntry 9 }
 
rcStatOspfIfTxLSReqs OBJECT-TYPE
        SYNTAX        Counter32
        MAX-ACCESS        read-only
        STATUS        current
        DESCRIPTION   "Used to indicate the number Link state request
                      packets transmitted by this interface."
        ::= { rcStatOspfIfEntry 10 }
 
rcStatOspfIfTxLSAcks OBJECT-TYPE
        SYNTAX        Counter32
        MAX-ACCESS        read-only
        STATUS        current
        DESCRIPTION   "Used to indicate the number Link state acknowlege
                      packets transmitted by this interface."
        ::= { rcStatOspfIfEntry 11 }

rcStatOspfIfVersionMismatches OBJECT-TYPE 
        SYNTAX        Counter32
        MAX-ACCESS        read-only
        STATUS        current
        DESCRIPTION   "Used to indicate the number version
                      mismatches received by this interface."
        ::= { rcStatOspfIfEntry 12 }

rcStatOspfIfAreaMismatches OBJECT-TYPE 
        SYNTAX        Counter32
        MAX-ACCESS        read-only
        STATUS        current
        DESCRIPTION   "Used to indicate the number area
                      mismatches received by this interface."
        ::= { rcStatOspfIfEntry 13 }

rcStatOspfIfAuthTypeMismatches OBJECT-TYPE 
        SYNTAX        Counter32
        MAX-ACCESS        read-only
        STATUS        current
        DESCRIPTION   "Used to indicate the number AuthType 
                      mismatches received by this interface."
        ::= { rcStatOspfIfEntry 14 }

rcStatOspfIfAuthFailures OBJECT-TYPE 
        SYNTAX        Counter32
        MAX-ACCESS        read-only
        STATUS        current
        DESCRIPTION   "Used to indicate the number Authentication
                      failures."
        ::= { rcStatOspfIfEntry 15 }

rcStatOspfIfNetMaskMismatches OBJECT-TYPE 
        SYNTAX        Counter32
        MAX-ACCESS        read-only
        STATUS        current
        DESCRIPTION   "Used to indicate the number net mask
                      mismatches received by this interface."
        ::= { rcStatOspfIfEntry 16 }

rcStatOspfIfHelloIntervalMismatches OBJECT-TYPE 
        SYNTAX        Counter32
        MAX-ACCESS        read-only
        STATUS        current
        DESCRIPTION   "Used to indicate the number hello interval
                      mismatches received by this interface."
        ::= { rcStatOspfIfEntry 17 }

rcStatOspfIfDeadIntervalMismatches OBJECT-TYPE 
        SYNTAX        Counter32
        MAX-ACCESS        read-only
        STATUS        current
        DESCRIPTION   "Used to indicate the number dead interval
                      mismatches received by this interface."
        ::= { rcStatOspfIfEntry 18 }

rcStatOspfIfOptionMismatches OBJECT-TYPE 
        SYNTAX        Counter32
        MAX-ACCESS        read-only
        STATUS        current
        DESCRIPTION   "Used to indicate the number options
                      mismatches received by this interface."
        ::= { rcStatOspfIfEntry 19 }

-- rcStatMlt Group

rcStatMlt      OBJECT IDENTIFIER ::= { rcStat 6 }
 
rcStatMltIfExtnTable OBJECT-TYPE
        SYNTAX        SEQUENCE OF RcStatMltIfExtnEntry
        MAX-ACCESS        not-accessible
        STATUS        current
        DESCRIPTION   "A table used to store Mlt interface
                      statistics."
        ::= { rcStatMlt 1 }
 
rcStatMltIfExtnEntry OBJECT-TYPE
        SYNTAX        RcStatMltIfExtnEntry
        MAX-ACCESS        not-accessible
        STATUS        current
        DESCRIPTION   "Mlt interface statistics"
        INDEX         { rcStatMltIfExtnMltId }
        ::= { rcStatMltIfExtnTable 1 }
 
RcStatMltIfExtnEntry ::= SEQUENCE {
                rcStatMltIfExtnMltId                  INTEGER,
                rcStatMltIfExtnIfInMulticastPkts      Counter32,
                rcStatMltIfExtnIfInBroadcastPkts      Counter32,
                rcStatMltIfExtnIfOutMulticastPkts     Counter32,
                rcStatMltIfExtnIfOutBroadcastPkts     Counter32,
                rcStatMltIfExtnIfHCInOctets           Counter64,
                rcStatMltIfExtnIfHCInUcastPkts        Counter64,
                rcStatMltIfExtnIfHCInMulticastPkt     Counter64,
                rcStatMltIfExtnIfHCInBroadcastPkt     Counter64,
                rcStatMltIfExtnIfHCOutOctets          Counter64,
                rcStatMltIfExtnIfHCOutUcastPkts       Counter64,
                rcStatMltIfExtnIfHCOutMulticast       Counter64,
                rcStatMltIfExtnIfHCOutBroadcast       Counter64
        }
 
rcStatMltIfExtnMltId OBJECT-TYPE
        SYNTAX        INTEGER (1..32)
        MAX-ACCESS        read-only
        STATUS        current
        DESCRIPTION   "Mlt Id"
        ::= { rcStatMltIfExtnEntry 1 }
 
rcStatMltIfExtnIfInMulticastPkts OBJECT-TYPE
        SYNTAX        Counter32
        MAX-ACCESS        read-only
        STATUS        current
        DESCRIPTION   "multi-pkts to upper"
        ::= { rcStatMltIfExtnEntry 2 }

rcStatMltIfExtnIfInBroadcastPkts OBJECT-TYPE
        SYNTAX        Counter32
        MAX-ACCESS        read-only
        STATUS        current
        DESCRIPTION   "broad-pkts to upper"
        ::= { rcStatMltIfExtnEntry 3 }
 
rcStatMltIfExtnIfOutMulticastPkts OBJECT-TYPE
        SYNTAX        Counter32
        MAX-ACCESS        read-only
        STATUS        current
        DESCRIPTION   "multi-pkts from upper"
        ::= { rcStatMltIfExtnEntry 4 }
 
rcStatMltIfExtnIfOutBroadcastPkts OBJECT-TYPE
        SYNTAX        Counter32
        MAX-ACCESS        read-only
        STATUS        current
        DESCRIPTION   "broad-pkts from upper"
        ::= { rcStatMltIfExtnEntry 5 }
 
rcStatMltIfExtnIfHCInOctets OBJECT-TYPE
        SYNTAX        Counter64
        MAX-ACCESS        read-only
        STATUS        current
        DESCRIPTION   "The total number of octets received 
                       on the MLT interface, including framing 
                       characters."
        ::= { rcStatMltIfExtnEntry 6 }
 
rcStatMltIfExtnIfHCInUcastPkts OBJECT-TYPE
        SYNTAX        Counter64
        MAX-ACCESS        read-only
        STATUS        current
        DESCRIPTION   "The number of packets delivered by this
                       MLT to a higher MLT that were not addressed
                       to a nulticast or broadcase address at this
                       sublayer."
        ::= { rcStatMltIfExtnEntry 7 }
 
rcStatMltIfExtnIfHCInMulticastPkt OBJECT-TYPE
        SYNTAX        Counter64
        MAX-ACCESS        read-only
        STATUS        current
        DESCRIPTION   "The number of packets delivered to this MLT that
                       were addressed to a nulticast address at this
                       sublayer.  For a MAC layer protocol, this number
                       includes both Group and Functional addresses."
        ::= { rcStatMltIfExtnEntry 8 }
 
rcStatMltIfExtnIfHCInBroadcastPkt OBJECT-TYPE
        SYNTAX        Counter64
        MAX-ACCESS        read-only
        STATUS        current
        DESCRIPTION   "The number of packets delivered to this MLT that
 		       were addressed to a broadcast address at this
 		       sublayer."
        ::= { rcStatMltIfExtnEntry 9 }
 
rcStatMltIfExtnIfHCOutOctets OBJECT-TYPE
        SYNTAX        Counter64
        MAX-ACCESS        read-only
        STATUS        current
        DESCRIPTION   "The total number of octets transmitted 
                       out of the MLT interface, including 
                       framing characters."
        ::= { rcStatMltIfExtnEntry 10 }
 
rcStatMltIfExtnIfHCOutUcastPkts OBJECT-TYPE
        SYNTAX        Counter64
        MAX-ACCESS        read-only
        STATUS        current
        DESCRIPTION   "The number of packets that hight-level protocols
                       requested be transmitted that were not addressed 
                       to a multicast address at this MLT.  This total
                       number includes those packets discarded or unsent."
        ::= { rcStatMltIfExtnEntry 11 }

rcStatMltIfExtnIfHCOutMulticast OBJECT-TYPE 
        SYNTAX        Counter64
        MAX-ACCESS        read-only
        STATUS        current
        DESCRIPTION   "The total number of packets that hight-level
                       protocols requested be transmitted, and that 
                       were addressed to a multicast address at this
                       MLT, including those that were discarded or 
                       not sent.  For a MAC layer protocol, this
                       number includes both Group and Functional
                       addresses."
        ::= { rcStatMltIfExtnEntry 12 }

rcStatMltIfExtnIfHCOutBroadcast OBJECT-TYPE 
        SYNTAX        Counter64
        MAX-ACCESS        read-only
        STATUS        current
        DESCRIPTION   "The total number of packets that hight-level
		       protocols requested be transmitted, and that
		       were addressed to a broadcase address at this	
		       MLT, including those that were discarded or 
		       not sent."
        ::= { rcStatMltIfExtnEntry 13 }

-- Mlt Ether table

rcStatMltEtherTable OBJECT-TYPE
        SYNTAX        SEQUENCE OF RcStatMltEtherEntry
        MAX-ACCESS        not-accessible
        STATUS        current
        DESCRIPTION   "A table used to store Mlt Ethernet
                      statistics."
        ::= { rcStatMlt 2 }
 
rcStatMltEtherEntry OBJECT-TYPE
        SYNTAX        RcStatMltEtherEntry
        MAX-ACCESS        not-accessible
        STATUS        current
        DESCRIPTION   "Mlt enternet statistics"
        INDEX         { rcStatMltEtherMltId }
        ::= { rcStatMltEtherTable 1 }
 
RcStatMltEtherEntry ::= SEQUENCE {
                rcStatMltEtherMltId              INTEGER,
                rcStatMltEtherAlignmentErrors    Counter32,
                rcStatMltEtherFCSErrors          Counter32,
                rcStatMltEtherSingleCollFrames   Counter32,
                rcStatMltEtherMultipleCollFrames Counter32,
                rcStatMltEtherSQETestError       Counter32,
                rcStatMltEtherDeferredTransmiss  Counter32,
                rcStatMltEtherLateCollisions     Counter32,
                rcStatMltEtherExcessiveCollis    Counter32,
                rcStatMltEtherIMacTransmitError  Counter32,
                rcStatMltEtherCarrierSenseError  Counter32,
                rcStatMltEtherFrameTooLong       Counter32,
                rcStatMltEtherIMacReceiveError   Counter32
        }
 
rcStatMltEtherMltId OBJECT-TYPE
        SYNTAX        INTEGER (1..32)
        MAX-ACCESS        read-only
        STATUS        current
        DESCRIPTION   "A value that uniquely identifies the Multi-Link 
                       Trunk associated with this entry."
        ::= { rcStatMltEtherEntry 1 }
 
rcStatMltEtherAlignmentErrors OBJECT-TYPE
        SYNTAX        Counter32
        MAX-ACCESS        read-only
        STATUS        current
        DESCRIPTION   "A count of frames received on a particular MLT
 		       that are not an integral number of octets in
		       length and do not pass the FCS check.  The count
		       represented by an instance of this object is
		       incremented when the alignmentError status is
		       returned by the MAC service to the LLC (or other
		       MAC user).  Received frames for which multiple
	 	       error conditions occur are, according to the 
		       conventions of IEEE 802.3 Layer Management, 
		       counted exclusively according to the error status
		       presented to the LLC."
        ::= { rcStatMltEtherEntry 2 }

rcStatMltEtherFCSErrors OBJECT-TYPE
        SYNTAX        Counter32
        MAX-ACCESS        read-only
        STATUS        current
        DESCRIPTION   "A count of frames received on an MLT that are an
	               integral number of octets in length but do not pass
                       the FCS check.  The count represented by an instance
                       of this object is incremented when the frameCheckError
                       status is returned by the MAC service to the LLC
                       (or other MAC user).  Received frames for which
		       multiple error conditions occur are, according to 
                       the conventions of IEEE 802.3 Layer Management, 
		       counted exclusively according to the error status
		       presented to the LLC."
        ::= { rcStatMltEtherEntry 3 }
 
rcStatMltEtherSingleCollFrames OBJECT-TYPE
        SYNTAX        Counter32
        MAX-ACCESS        read-only
        STATUS        current
        DESCRIPTION   "A count of successfully transmitted frames on 
                       a particular MLT for which transmission is 
                       inhibited by exactly one collision.  A frame 
                       that is counted by an instance of this objects 
                       is also counted by the corresponding instance 
                       of either the ifOutUcastPkts, ifOutMulticastPkts, 
                       or ifOutBroadcastPkts, and it not counted by the 
                       corresponding instance of the MultipleCollisionFrames 
                       object."
        ::= { rcStatMltEtherEntry 4 }
 
rcStatMltEtherMultipleCollFrames OBJECT-TYPE
        SYNTAX        Counter32
        MAX-ACCESS        read-only
        STATUS        current
        DESCRIPTION   "A count of successfully transmitted frames on 
                       a particular MLT for which transmission is 
                       inhibited by more than one collision.  A frame 
                       that is counted by an instance of this object 
                       is also counted by the corresponding instance 
                       of either the ifOutUcastPkts, ifOutMulticastPkts, 
                       or ifOutBroadcastPkts, and is not counted by the 
                       corresponding instance of the SingleCollisionFrames 
                       objects."
        ::= { rcStatMltEtherEntry 5 }
 
rcStatMltEtherSQETestError OBJECT-TYPE
        SYNTAX        Counter32
        MAX-ACCESS        read-only
        STATUS        current
        DESCRIPTION   "A count of times that the SQE TEST ERROR message
		       is generated by the PLS sublayer for a particular
	               MLT. SQE stands for Signal Quality Error."
        ::= { rcStatMltEtherEntry 6 }
 
rcStatMltEtherDeferredTransmiss OBJECT-TYPE
        SYNTAX        Counter32
        MAX-ACCESS        read-only
        STATUS        current
        DESCRIPTION   "A count of frames for which the first transmission
	               attempt on a particular MLT is delayed because the
                       medium is busy.  The count represented by an 
	               instance of this object does not include frames
		       involved in collisions."
        ::= { rcStatMltEtherEntry 7 }
 
rcStatMltEtherLateCollisions OBJECT-TYPE
        SYNTAX        Counter32
        MAX-ACCESS        read-only
        STATUS        current
        DESCRIPTION   "The number of times that a collision is detected 
                       on a particular MLT later than 512 bit-times 
                       (64 octets) into the transmission of a packet. 
                       Five hundred and twelve bit-times corresponds to 
                       51.2 microseconds on a 10 mb/s system.  A (late) 
                       collision included in a count represented by an 
                       instance of this object is also considered as a
                       (generic) collision for purposes of other 
                       collision-related statistics."
        ::= { rcStatMltEtherEntry 8 }
 
rcStatMltEtherExcessiveCollis OBJECT-TYPE
        SYNTAX        Counter32
        MAX-ACCESS        read-only
        STATUS        current
        DESCRIPTION   "A count of frames for which transmission on a 
	               particular MLT fails due to excessive collisions."
        ::= { rcStatMltEtherEntry 9 }
 
rcStatMltEtherIMacTransmitError OBJECT-TYPE
        SYNTAX        Counter32
        MAX-ACCESS        read-only
        STATUS        current
        DESCRIPTION   "A count of frames for which transmission on a 
	               particular MLT fails due to an internal MAC 
                       sublayer transmit error.  A frame is only counted 
                       by an instance of this object if it is not counted
                       by the corresponding instance of either the 
		       LateCollisions object, the ExcessiveCollisions
		       object, or the CarrierSenseError object."
        ::= { rcStatMltEtherEntry 10 }
 
rcStatMltEtherCarrierSenseError OBJECT-TYPE
        SYNTAX        Counter32
        MAX-ACCESS        read-only
        STATUS        current
        DESCRIPTION   "The number of times that the carrier sense 
                       condition was lost or never asserted when 
                       attempting to transmit a frame on a particular
                       MLT.  The count represented by an instance of
	               this object is incremented at most once per
		       transmission attempt, even if the carrier
		       sense condition fluctuates during a 
		       transmission attempt."
        ::= { rcStatMltEtherEntry 11 }

rcStatMltEtherFrameTooLong OBJECT-TYPE 
        SYNTAX        Counter32
        MAX-ACCESS        read-only
        STATUS        current
        DESCRIPTION   "A count of frames received on a particular MLT
                       that exceed the maximum permitted size (1518 
                       octets).  The count represented by an instance
		       os this object is incremented when the frame
	               TooLong status is returned by the MAC service
		       to the LLC (or other MAC user).  Received frames
		       for which multiple error conditions occur are, 
		       according to the conventions of IEEE 802.3 
                       Layer Management, counted exclusively according
		       to the error status presented to the LLC."
        ::= { rcStatMltEtherEntry 12 }

rcStatMltEtherIMacReceiveError OBJECT-TYPE 
        SYNTAX        Counter32
        MAX-ACCESS        read-only
        STATUS        current
        DESCRIPTION   "A count of frames for which reception on a 
		       particular MLT fails due to an internal MAC
		       sublayer receive error.  A frame is only
		       counted by an instance of this object if it 
		       is not counted by the corresponding instance 
		       of either the FrameTooLongs object, the
	               AlignmentErrors object, of the FCSErrors
	               objects.
                       The precise meaning of the count represented
		       by an instance of this object is implementation
	               specific.  In particular, an instance of this
	               object may represent a count of receive errors
                       on a particular interface that are not otherwise
		       counted."
        ::= { rcStatMltEtherEntry 13 }


-- Mlt Ip table

rcStatMltIpTable OBJECT-TYPE
        SYNTAX        SEQUENCE OF RcStatMltIpEntry
        MAX-ACCESS        not-accessible
        STATUS        current
        DESCRIPTION   "A table used to store Mlt Ip statistics."
        ::= { rcStatMlt 3 }
 
rcStatMltIpEntry OBJECT-TYPE
        SYNTAX        RcStatMltIpEntry
        MAX-ACCESS        not-accessible
        STATUS        current
        DESCRIPTION   "Mlt enternet statistics"
        INDEX         { rcStatMltIpMltId }
        ::= { rcStatMltIpTable 1 }
 
RcStatMltIpEntry ::= SEQUENCE {
                rcStatMltIpMltId            INTEGER,
                rcStatMltIpInReceives       Counter32,
                rcStatMltIpInHdrErrors      Counter32,
                rcStatMltIpInAddrErrors     Counter32,
                rcStatMltIpForwDatagrams    Counter32,
                rcStatMltIpInUnknownProtos  Counter32,
                rcStatMltIpInDiscards       Counter32,
                rcStatMltIpInDelivers       Counter32,
                rcStatMltIpOutRequest       Counter32,
                rcStatMltIpOutDiscards      Counter32,
                rcStatMltIpOutNoRoutes      Counter32,
                rcStatMltIpReasmReqds       Counter32,
                rcStatMltIpReasmOKs         Counter32,
                rcStatMltIpReasmFails       Counter32,
                rcStatMltIpFragOKs          Counter32,
                rcStatMltIpFragFails        Counter32,
                rcStatMltIpFragCreates      Counter32,
                rcStatMltIpRoutingDiscards  Counter32
        }
 
rcStatMltIpMltId OBJECT-TYPE
        SYNTAX        INTEGER (1..8)
        MAX-ACCESS        read-only
        STATUS        current
        DESCRIPTION   "Mlt Id"
        ::= { rcStatMltIpEntry 1 }
 
rcStatMltIpInReceives OBJECT-TYPE
        SYNTAX        Counter32
        MAX-ACCESS        read-only
        STATUS        current
        DESCRIPTION   "all incoming packets"
        ::= { rcStatMltIpEntry 2 }

rcStatMltIpInHdrErrors OBJECT-TYPE
        SYNTAX        Counter32
        MAX-ACCESS        read-only
        STATUS        current
        DESCRIPTION   "hdr errors detected"
        ::= { rcStatMltIpEntry 3 }
 
rcStatMltIpInAddrErrors OBJECT-TYPE
        SYNTAX        Counter32
        MAX-ACCESS        read-only
        STATUS        current
        DESCRIPTION   "bad dest. ip addr"
        ::= { rcStatMltIpEntry 4 }
 
rcStatMltIpForwDatagrams OBJECT-TYPE
        SYNTAX        Counter32
        MAX-ACCESS        read-only
        STATUS        current
        DESCRIPTION   "packets forwarded"
        ::= { rcStatMltIpEntry 5 }
 
rcStatMltIpInUnknownProtos OBJECT-TYPE
        SYNTAX        Counter32
        MAX-ACCESS        read-only
        STATUS        current
        DESCRIPTION   "unsupported protocol"
        ::= { rcStatMltIpEntry 6 }
 
rcStatMltIpInDiscards OBJECT-TYPE
        SYNTAX        Counter32
        MAX-ACCESS        read-only
        STATUS        current
        DESCRIPTION   "good, but no buffer"
        ::= { rcStatMltIpEntry 7 }
 
rcStatMltIpInDelivers OBJECT-TYPE
        SYNTAX        Counter32
        MAX-ACCESS        read-only
        STATUS        current
        DESCRIPTION   "pkts delivered to upper"
        ::= { rcStatMltIpEntry 8 }
 
rcStatMltIpOutRequest OBJECT-TYPE
        SYNTAX        Counter32
        MAX-ACCESS        read-only
        STATUS        current
        DESCRIPTION   "pkts received from upper"
        ::= { rcStatMltIpEntry 9 }
 
rcStatMltIpOutDiscards OBJECT-TYPE
        SYNTAX        Counter32
        MAX-ACCESS        read-only
        STATUS        current
        DESCRIPTION   "good, but no buffer"
        ::= { rcStatMltIpEntry 10 }
 
rcStatMltIpOutNoRoutes OBJECT-TYPE
        SYNTAX        Counter32
        MAX-ACCESS        read-only
        STATUS        current
        DESCRIPTION   "no route to destination"
        ::= { rcStatMltIpEntry 11 }

rcStatMltIpReasmReqds OBJECT-TYPE 
        SYNTAX        Counter32
        MAX-ACCESS        read-only
        STATUS        current
        DESCRIPTION   "fragments to reassem"
        ::= { rcStatMltIpEntry 12 }

rcStatMltIpReasmOKs OBJECT-TYPE 
        SYNTAX        Counter32
        MAX-ACCESS        read-only
        STATUS        current
        DESCRIPTION   "reassembled successfully"
        ::= { rcStatMltIpEntry 13 }

rcStatMltIpReasmFails OBJECT-TYPE 
        SYNTAX        Counter32
        MAX-ACCESS        read-only
        STATUS        current
        DESCRIPTION   "reassembly failures"
        ::= { rcStatMltIpEntry 14 }

rcStatMltIpFragOKs OBJECT-TYPE 
        SYNTAX        Counter32
        MAX-ACCESS        read-only
        STATUS        current
        DESCRIPTION   "fragment successfully"
        ::= { rcStatMltIpEntry 15 }

rcStatMltIpFragFails OBJECT-TYPE 
        SYNTAX        Counter32
        MAX-ACCESS        read-only
        STATUS        current
        DESCRIPTION   "fragment failure"
        ::= { rcStatMltIpEntry 16 }

rcStatMltIpFragCreates OBJECT-TYPE 
        SYNTAX        Counter32
        MAX-ACCESS        read-only
        STATUS        current
        DESCRIPTION   "pkts due to fragmenting"
        ::= { rcStatMltIpEntry 17 }

rcStatMltIpRoutingDiscards OBJECT-TYPE 
        SYNTAX        Counter32
        MAX-ACCESS        read-only
        STATUS        current
        DESCRIPTION   "Route entries removed"
        ::= { rcStatMltIpEntry 18 }


-- Stat Ospf Ip Interface Table
-- replaces Stat Ospf Interface Table

rcStatOspfIfV2Table OBJECT-TYPE
        SYNTAX        SEQUENCE OF RcStatOspfIfV2Entry
        MAX-ACCESS        not-accessible
        STATUS        current
        DESCRIPTION   "A table used to store OSPF interface
                      statistics."
        ::= { rcStat 7 }
 
rcStatOspfIfV2Entry OBJECT-TYPE
        SYNTAX        RcStatOspfIfV2Entry
        MAX-ACCESS        not-accessible
        STATUS        current
        DESCRIPTION   "Ospf interface statistics"
        INDEX         { rcStatOspfIfV2Index, rcStatOspfIfV2Addr }
        ::= { rcStatOspfIfV2Table 1 }
 
RcStatOspfIfV2Entry ::= SEQUENCE {
                rcStatOspfIfV2Index                   InterfaceIndex,
                rcStatOspfIfV2Addr                    IpAddress,
                rcStatOspfIfV2RxHellos                Counter32,
                rcStatOspfIfV2RxDBDescrs              Counter32,
                rcStatOspfIfV2RxLSUpdates             Counter32,
                rcStatOspfIfV2RxLSReqs                Counter32,
                rcStatOspfIfV2RxLSAcks                Counter32,
                rcStatOspfIfV2TxHellos                Counter32,
                rcStatOspfIfV2TxDBDescrs              Counter32,
                rcStatOspfIfV2TxLSUpdates             Counter32,
                rcStatOspfIfV2TxLSReqs                Counter32,
                rcStatOspfIfV2TxLSAcks                Counter32,
                rcStatOspfIfV2VersionMismatches       Counter32,
                rcStatOspfIfV2AreaMismatches          Counter32,
                rcStatOspfIfV2AuthTypeMismatches      Counter32,
                rcStatOspfIfV2AuthFailures            Counter32,
                rcStatOspfIfV2NetMaskMismatches       Counter32,
                rcStatOspfIfV2HelloIntervalMismatches Counter32,
                rcStatOspfIfV2DeadIntervalMismatches  Counter32,
                rcStatOspfIfV2OptionMismatches        Counter32
        }
 
rcStatOspfIfV2Index OBJECT-TYPE
        SYNTAX        InterfaceIndex (0..4094)
        MAX-ACCESS        read-only
        STATUS        current
        DESCRIPTION   "An unique value that is used to identify a
                      physical interface."
        ::= { rcStatOspfIfV2Entry 1 }
 
rcStatOspfIfV2Addr OBJECT-TYPE
        SYNTAX        IpAddress
        MAX-ACCESS        read-only
        STATUS        current
        DESCRIPTION   "Ip Address"
        ::= { rcStatOspfIfV2Entry 2 }
 
rcStatOspfIfV2RxHellos OBJECT-TYPE
        SYNTAX        Counter32
        MAX-ACCESS        read-only
        STATUS        current
        DESCRIPTION   "Used to indicate the number hello packets
                      received by this interface."
        ::= { rcStatOspfIfV2Entry 3 }

rcStatOspfIfV2RxDBDescrs OBJECT-TYPE
        SYNTAX        Counter32
        MAX-ACCESS        read-only
        STATUS        current
        DESCRIPTION   "Used to indicate the number database descriptor
                      packets received by this interface."
        ::= { rcStatOspfIfV2Entry 4 }
 
rcStatOspfIfV2RxLSUpdates OBJECT-TYPE
        SYNTAX        Counter32
        MAX-ACCESS        read-only
        STATUS        current
        DESCRIPTION   "Used to indicate the number Link state update
                      packets received by this interface."
        ::= { rcStatOspfIfV2Entry 5 }
 
rcStatOspfIfV2RxLSReqs OBJECT-TYPE
        SYNTAX        Counter32
        MAX-ACCESS        read-only
        STATUS        current
        DESCRIPTION   "Used to indicate the number Link state request
                      packets received by this interface."
        ::= { rcStatOspfIfV2Entry 6 }
 
rcStatOspfIfV2RxLSAcks OBJECT-TYPE
        SYNTAX        Counter32
        MAX-ACCESS        read-only
        STATUS        current
        DESCRIPTION   "Used to indicate the number Link state acknowlege
                      packets received by this interface."
        ::= { rcStatOspfIfV2Entry 7 }
 
rcStatOspfIfV2TxHellos OBJECT-TYPE
        SYNTAX        Counter32
        MAX-ACCESS        read-only
        STATUS        current
        DESCRIPTION   "Used to indicate the number hello packets
                      transmitted by this interface."
        ::= { rcStatOspfIfV2Entry 8 }
 
rcStatOspfIfV2TxDBDescrs OBJECT-TYPE
        SYNTAX        Counter32
        MAX-ACCESS        read-only
        STATUS        current
        DESCRIPTION   "Used to indicate the number database descriptor
                      packets transmitted by this interface."
        ::= { rcStatOspfIfV2Entry 9 }
 
rcStatOspfIfV2TxLSUpdates OBJECT-TYPE
        SYNTAX        Counter32
        MAX-ACCESS        read-only
        STATUS        current
        DESCRIPTION   "Used to indicate the number Link state update
                      packets transmitted by this interface."
        ::= { rcStatOspfIfV2Entry 10 }
 
rcStatOspfIfV2TxLSReqs OBJECT-TYPE
        SYNTAX        Counter32
        MAX-ACCESS        read-only
        STATUS        current
        DESCRIPTION   "Used to indicate the number Link state request
                      packets transmitted by this interface."
        ::= { rcStatOspfIfV2Entry 11 }
 
rcStatOspfIfV2TxLSAcks OBJECT-TYPE
        SYNTAX        Counter32
        MAX-ACCESS        read-only
        STATUS        current
        DESCRIPTION   "Used to indicate the number Link state acknowlege
                      packets transmitted by this interface."
        ::= { rcStatOspfIfV2Entry 12 }

rcStatOspfIfV2VersionMismatches OBJECT-TYPE 
        SYNTAX        Counter32
        MAX-ACCESS        read-only
        STATUS        current
        DESCRIPTION   "Used to indicate the number version
                      mismatches received by this interface."
        ::= { rcStatOspfIfV2Entry 13 }

rcStatOspfIfV2AreaMismatches OBJECT-TYPE 
        SYNTAX        Counter32
        MAX-ACCESS        read-only
        STATUS        current
        DESCRIPTION   "Used to indicate the number area
                      mismatches received by this interface."
        ::= { rcStatOspfIfV2Entry 14 }

rcStatOspfIfV2AuthTypeMismatches OBJECT-TYPE 
        SYNTAX        Counter32
        MAX-ACCESS        read-only
        STATUS        current
        DESCRIPTION   "Used to indicate the number AuthType 
                      mismatches received by this interface."
        ::= { rcStatOspfIfV2Entry 15 }

rcStatOspfIfV2AuthFailures OBJECT-TYPE 
        SYNTAX        Counter32
        MAX-ACCESS        read-only
        STATUS        current
        DESCRIPTION   "Used to indicate the number Authentication
                      failures."
        ::= { rcStatOspfIfV2Entry 16 }

rcStatOspfIfV2NetMaskMismatches OBJECT-TYPE 
        SYNTAX        Counter32
        MAX-ACCESS        read-only
        STATUS        current
        DESCRIPTION   "Used to indicate the number net mask
                      mismatches received by this interface."
        ::= { rcStatOspfIfV2Entry 17 }

rcStatOspfIfV2HelloIntervalMismatches OBJECT-TYPE 
        SYNTAX        Counter32
        MAX-ACCESS        read-only
        STATUS        current
        DESCRIPTION   "Used to indicate the number hello interval
                      mismatches received by this interface."
        ::= { rcStatOspfIfV2Entry 18 }

rcStatOspfIfV2DeadIntervalMismatches OBJECT-TYPE 
        SYNTAX        Counter32
        MAX-ACCESS        read-only
        STATUS        current
        DESCRIPTION   "Used to indicate the number dead interval
                      mismatches received by this interface."
        ::= { rcStatOspfIfV2Entry 19 }

rcStatOspfIfV2OptionMismatches OBJECT-TYPE 
        SYNTAX        Counter32
        MAX-ACCESS        read-only
        STATUS        current
        DESCRIPTION   "Used to indicate the number options
                      mismatches received by this interface."
        ::= { rcStatOspfIfV2Entry 20 }

-- Spanning Tree Group (STG)

rcStgMaxStgs OBJECT-TYPE
        SYNTAX        Integer32
        MAX-ACCESS        read-write
        STATUS        current
        DESCRIPTION   "The maximum number of spanning tree groups this
		      device can support concurrently."
        ::= { rcStg 1 }

rcStgNumStgs OBJECT-TYPE
        SYNTAX        Integer32
        MAX-ACCESS        read-only
        STATUS        current
        DESCRIPTION   "The number of spanning tree groups that are
		      currently defined."
        ::= { rcStg 2 }

rcStgUnassignedPorts OBJECT-TYPE
        SYNTAX        PortSet
        MAX-ACCESS        read-only
        STATUS        current
        DESCRIPTION   "A bitfield used to identify which ports in
                      the system currently not assigned to any STG.

                      The bitfield is 32 octets long representing 
                      ports 0 to 255 (inclusive)."
        ::= { rcStg 3 }


-- STG Table

rcStgTable OBJECT-TYPE
        SYNTAX        SEQUENCE OF RcStgEntry
        MAX-ACCESS        not-accessible
        STATUS        current
        DESCRIPTION   "A table used to store Spanning Tree Group (STG)
		      information.  Each row in the table specifies
		      a different STG in the device."
        ::= { rcStg 4 } 
 
rcStgEntry OBJECT-TYPE  
        SYNTAX        RcStgEntry
        MAX-ACCESS        not-accessible
        STATUS        current
        DESCRIPTION   "STG attributes"
        INDEX  { rcStgId }
        ::= { rcStgTable 1 }
 
RcStgEntry ::= SEQUENCE {
		rcStgId INTEGER,
		rcStgTaggedBpduAddress MacAddress,
		rcStgTaggedBpduVlanId INTEGER,
		rcStgBridgeAddress MacAddress,
		rcStgNumPorts INTEGER,
		rcStgProtocolSpecification INTEGER,
		rcStgPriority INTEGER,
		rcStgTimeSinceTopologyChange TimeTicks,
		rcStgTopChanges Counter32,
		rcStgDesignatedRoot BridgeId,
		rcStgRootCost INTEGER,
		rcStgRootPort INTEGER,
		rcStgMaxAge Timeout,
		rcStgHelloTime Timeout,
		rcStgHoldTime INTEGER,
		rcStgForwardDelay Timeout,
		rcStgBridgeMaxAge Timeout,
		rcStgBridgeHelloTime Timeout,
		rcStgBridgeForwardDelay Timeout,
		rcStgEnableStp TruthValue,
		rcStgStpTrapEnable TruthValue,
		rcStgPortMembers OCTET STRING,
		rcStgRowStatus RowStatus,
		rcStgPortStgState OCTET STRING
        }

rcStgId OBJECT-TYPE 
        SYNTAX  	INTEGER (1..25)
        MAX-ACCESS  	read-only
        STATUS  	current
        DESCRIPTION 	"An identifier used to identify a STG in the device."
        ::= { rcStgEntry 1 }

rcStgTaggedBpduAddress OBJECT-TYPE
        SYNTAX  	MacAddress
        MAX-ACCESS  	read-write
        STATUS  	current
        DESCRIPTION 	"The MAC address to be assigned to the destination
      	       		mac address field in tagged BPDUs.  

	       		The default address is the well known multicast 
	       		group address 01-80-c2-00-00-00."
        DEFVAL          { "01:80:c2:00:00:00" }
  	::= { rcStgEntry 2 }

rcStgTaggedBpduVlanId OBJECT-TYPE 
        SYNTAX  	Integer32  
        MAX-ACCESS  	read-write 
        STATUS  	current  
        DESCRIPTION 	"The VLAN ID to be used for tagging BPDUs." 
        ::= { rcStgEntry 3 }

rcStgBridgeAddress OBJECT-TYPE
        SYNTAX  	MacAddress
        MAX-ACCESS  	read-only
        STATUS  	current
        DESCRIPTION 	"The MAC address used by this bridge when it must
		       	be referred to in a unique fashion.   It is
		       	recommended that this be the numerically smallest
		       	MAC address of all ports that belong to this
		       	bridge.  However it is only required to be unique.
		       	When concatenated with rcStgPriority a unique
		       	BridgeIdentifier is formed which is used in the
		       	Spanning Tree Protocol."
        REFERENCE 	"IEEE 802.1D-1990: Sections 6.4.1.1.3 and 3.12.5"
        ::= { rcStgEntry 4 }

rcStgNumPorts OBJECT-TYPE
        SYNTAX        Integer32
        MAX-ACCESS  	read-only
        STATUS  	current
        DESCRIPTION 	"The number of ports controlled by this bridging entity."
        REFERENCE 	"IEEE 802.1D-1990: Section 6.4.1.1.3"
        ::= { rcStgEntry 5 }

rcStgProtocolSpecification OBJECT-TYPE
        SYNTAX  	INTEGER {
			      unknown(1),
			      decLb100(2),
			      ieee8021d(3)
		        }
        MAX-ACCESS  	read-only
        STATUS  	current
        DESCRIPTION 	"An indication of what version of the Spanning
                     	Tree Protocol is being run.  The value
                     	'decLb100(2)' indicates the DEC LANbridge 100
                     	Spanning Tree protocol.  IEEE 802.1d
                     	implementations will return 'ieee8021d(3)'.  If
                     	future versions of the IEEE Spanning Tree Protocol
                     	are released that are incompatible with the
                     	current version a new value will be defined."
        ::= { rcStgEntry 6 }

rcStgPriority OBJECT-TYPE
        SYNTAX  	INTEGER (0..65535)
        MAX-ACCESS  	read-write
        STATUS  	current
        DESCRIPTION 	"The value of the write-able portion of the Bridge
	      	       	ID, i.e., the first two octets of the (8 octet
      		       	long) Bridge ID.  The other (last) 6 octets of the
      	       		Bridge ID are given by the value of rcStgBridgeAddress."
        REFERENCE 	"IEEE 802.1D-1990: Section 4.5.3.7"
        DEFVAL          { 32768 }
        ::= { rcStgEntry 7 }

rcStgTimeSinceTopologyChange OBJECT-TYPE
        SYNTAX  	TimeTicks
        MAX-ACCESS  	read-only
        STATUS  	current
        DESCRIPTION 	"The time (in hundredths of a second) since the
	       		last time a topology change was detected by the
	       		bridge entity."
        REFERENCE 	"IEEE 802.1D-1990: Section 6.8.1.1.3"
        ::= { rcStgEntry 8 }

rcStgTopChanges OBJECT-TYPE
        SYNTAX  	Counter32
        MAX-ACCESS  	read-only
        STATUS  	current
        DESCRIPTION 	"The total number of topology changes detected by
	       		this bridge since the management entity was last
	       		reset or initialized."
        REFERENCE 	"IEEE 802.1D-1990: Section 6.8.1.1.3"
        ::= { rcStgEntry 9 }

rcStgDesignatedRoot OBJECT-TYPE
        SYNTAX  	BridgeId
        MAX-ACCESS  	read-only
        STATUS  	current
        DESCRIPTION 	"The bridge identifier of the root of the spanning
	       		tree as determined by the Spanning Tree Protocol
	       		as executed by this node.  This value is used as
                        the Root Identifier parameter in all Configuration
                        Bridge PDUs originated by this node."
        REFERENCE 	"IEEE 802.1D-1990: Section 4.5.3.1"
        ::= { rcStgEntry 10 }

rcStgRootCost OBJECT-TYPE
        SYNTAX        Integer32
        MAX-ACCESS  	read-only
        STATUS  	current
        DESCRIPTION 	"The cost of the path to the root as seen from
	       		this bridge."
        REFERENCE 	"IEEE 802.1D-1990: Section 4.5.3.2"
        ::= { rcStgEntry 11 }

rcStgRootPort OBJECT-TYPE
        SYNTAX        Integer32
        MAX-ACCESS  	read-only
        STATUS  	current
        DESCRIPTION 	"The port number of the port which offers the
	  		lowest cost path from this bridge to the root
               		bridge."
        REFERENCE 	"IEEE 802.1D-1990: Section 4.5.3.3"
        ::= { rcStgEntry 12 }

rcStgMaxAge OBJECT-TYPE
        SYNTAX  	Timeout
        MAX-ACCESS  	read-only
        STATUS  	current
        DESCRIPTION 	"The maximum age of Spanning Tree Protocol
	       		information learned from the network on any port
	       		before it is discarded, in units of hundredths of
	       		a second.  This is the actual value that this
	       		bridge is currently using."
        REFERENCE 	"IEEE 802.1D-1990: Section 4.5.3.4"
        ::= { rcStgEntry 13 }

rcStgHelloTime OBJECT-TYPE
        SYNTAX  	Timeout
        MAX-ACCESS  	read-only
        STATUS  	current
        DESCRIPTION 	"The amount of time between the transmission of
	       		Configuration bridge PDUs by this node on any port
	       		when it is the root of the spanning tree or trying
	       		to become so, in units of hundredths of a second.
	       		This is the actual value that this bridge is
                        currently using."
        REFERENCE 	"IEEE 802.1D-1990: Section 4.5.3.5"
        ::= { rcStgEntry 14 }

rcStgHoldTime OBJECT-TYPE
        SYNTAX        Integer32
        MAX-ACCESS  	read-only
        STATUS  	current
        DESCRIPTION     "This time value determines the interval length
	                during which no more than two Configuration bridge
	                PDUs shall be transmitted by this node, in units
	             	of hundredths of a second."
        REFERENCE 	"IEEE 802.1D-1990: Section 4.5.3.14"
        ::= { rcStgEntry 15 }

rcStgForwardDelay OBJECT-TYPE
        SYNTAX  	Timeout
        MAX-ACCESS  	read-only
        STATUS  	current
        DESCRIPTION 	"This time value, measured in units of hundredths
	             	of a second, controls how fast a port changes its
	             	spanning state when moving towards the Forwarding
	             	state.  The value determines how long the port
	             	stays in each of the Listening and Learning
	             	states, which precede the Forwarding state.  This
	             	value is also used, when a topology change has
	             	been detected and is underway, to age all dynamic
	             	entries in the Forwarding Database.  [Note that
	             	this value is the one that this bridge is
	             	currently using, in contrast to
	             	rcStgBridgeForwardDelay which is the value that
	             	this bridge and all others would start using
	             	if/when this bridge were to become the root.]"
        REFERENCE 	"IEEE 802.1D-1990: Section 4.5.3.6"
        ::= { rcStgEntry 16 }

rcStgBridgeMaxAge OBJECT-TYPE
        SYNTAX  	Timeout (600..4000)
        MAX-ACCESS  	read-write
        STATUS  	current
        DESCRIPTION 	"The value that all bridges use for MaxAge when
	             	this bridge is acting as the root.  Note that
	             	802.1D-1990 specifies that the range for this
	             	parameter is related to the value of
	             	rcStgBridgeHelloTime. The granularity of this
	             	timer is specified by 802.1D-1990 to be 1 second.
	             	An agent may return a badValue error if a set is
	             	attempted to a value which is not a whole number
	             	of seconds."
        REFERENCE 	"IEEE 802.1D-1990: Section 4.5.3.8"
        DEFVAL          { 2000 }
        ::= { rcStgEntry 17 }

rcStgBridgeHelloTime OBJECT-TYPE
        SYNTAX  	Timeout (100..1000)
        MAX-ACCESS  	read-write
        STATUS  	current
        DESCRIPTION 	"The value that all bridges use for HelloTime when
	             	this bridge is acting as the root.  The
	             	granularity of this timer is specified by 802.1D-
	             	1990 to be 1 second.  An agent may return a
	             	badValue error if a set is attempted to a value
	             	which is not a whole number of seconds."
        REFERENCE 	"IEEE 802.1D-1990: Section 4.5.3.9"
        DEFVAL          { 200 }
        ::= { rcStgEntry 18 }

rcStgBridgeForwardDelay OBJECT-TYPE
        SYNTAX  	Timeout (400..3000)
        MAX-ACCESS  	read-write
        STATUS  	current
        DESCRIPTION 	"The value that all bridges use for ForwardDelay
	             	when this bridge is acting as the root.  Note that
	             	802.1D-1990 specifies that the range for this
	             	parameter is related to the value of
	             	rcStgBridgeMaxAge.  The granularity of this
	             	timer is specified by 802.1D-1990 to be 1 second.
	             	An agent may return a badValue error if a set is
	             	attempted to a value which is not a whole number
	             	of seconds."
        REFERENCE 	"IEEE 802.1D-1990: Section 4.5.3.10"
        DEFVAL          { 1500 }
        ::= { rcStgEntry 19 }

rcStgEnableStp OBJECT-TYPE
        SYNTAX  	TruthValue
        MAX-ACCESS  	read-write
        STATUS  	current
        DESCRIPTION 	"Indicate whether the spanning tree protocol 
	       		should be active in this STG."
        DEFVAL         { true }
        ::= { rcStgEntry 20 }

rcStgStpTrapEnable OBJECT-TYPE
        SYNTAX 	 	TruthValue
        MAX-ACCESS  	read-write
        STATUS  	current
        DESCRIPTION 	"Indicate whether traps relating to the spanning
	       		tree protocol should be sent for this STG."
        DEFVAL         { true }
        ::= { rcStgEntry 21 }

rcStgPortMembers OBJECT-TYPE
        SYNTAX          OCTET STRING (SIZE(88))
        MAX-ACCESS          read-write
        STATUS          current
        DESCRIPTION     "A bitfield used to identify which ports in
		   	the system are members this STG.

		   	The bitfield is 32 octets long representing
		   	ports 0 to 255 (inclusive)."
        ::= { rcStgEntry 22 }

rcStgRowStatus OBJECT-TYPE
        SYNTAX  	RowStatus
        MAX-ACCESS  	read-write
        STATUS  	current
        DESCRIPTION 	"Row status."
        ::= { rcStgEntry 23 }

rcStgPortStgState OBJECT-TYPE
        SYNTAX          OCTET STRING (SIZE(176))
        MAX-ACCESS          read-only
        STATUS          current
        DESCRIPTION     "Every 2 bitfields used to identify a port state
                        in this STG. Port state is cataloged as non-stp(0),
                        blocking(1), learning(2), and forwarding(3)."
        ::= { rcStgEntry 24 }


-- STG Port Table

rcStgPortTable OBJECT-TYPE
        SYNTAX        SEQUENCE OF RcStgPortEntry
        MAX-ACCESS        not-accessible
        STATUS        current    
        DESCRIPTION   "A table used to store Spanning Tree Group (STG)
                      port related information.  If a port is 
                      associated with more than one STGs, the port  
                      will have one entry in this table for each STG 
                      it assigned to." 
        ::= { rcStg 5 }
 
rcStgPortEntry OBJECT-TYPE
        SYNTAX        RcStgPortEntry
        MAX-ACCESS        not-accessible
        STATUS        current
        DESCRIPTION   "STG Port attributes" 
        INDEX         { rcStgPort, rcStgPortStgId }
        ::= { rcStgPortTable 1 }
 
RcStgPortEntry ::= SEQUENCE {
                  rcStgPort InterfaceIndex,
                  rcStgPortStgId INTEGER,
                  rcStgPortPriority INTEGER,
                  rcStgPortState INTEGER,
                  rcStgPortEnableStp TruthValue,
                  rcStgPortFastStart TruthValue,
                  rcStgPortPathCost INTEGER,
                  rcStgPortDesignatedRoot BridgeId,
                  rcStgPortDesignatedCost INTEGER,
                  rcStgPortDesignatedBridge BridgeId,
                  rcStgPortDesignatedPort OCTET STRING,
                  rcStgPortForwardTransitions Counter32,
                  rcStgPortInConfigBpdus Counter32,
                  rcStgPortInTcnBpdus Counter32,
                  rcStgPortInBadBpdus Counter32,
                  rcStgPortOutConfigBpdus Counter32,
                  rcStgPortOutTcnBpdus Counter32,
		  rcStgPortRowStatus RowStatus
              }

rcStgPort OBJECT-TYPE
        SYNTAX  	InterfaceIndex
        MAX-ACCESS  	read-only
        STATUS  	current
        DESCRIPTION 	"The port number of the port for which this entry
                     	contains Spanning Tree Protocol management
                     	information."
        REFERENCE 	"IEEE 802.1D-1990: Section 6.8.2.1.2"
        ::= { rcStgPortEntry 1 }

rcStgPortStgId OBJECT-TYPE
        SYNTAX  	INTEGER (1..128)
        MAX-ACCESS  	read-only
        STATUS  	current
	DESCRIPTION 	"The STG identifier this port is assigned to."
        ::= { rcStgPortEntry 2 }

rcStgPortPriority OBJECT-TYPE
        SYNTAX  	INTEGER (0..255)
        MAX-ACCESS  	read-write
        STATUS  	current
        DESCRIPTION 	"The value of the priority field which is
                     	contained in the first (in network byte order)
                     	octet of the (2 octet long) Port ID.  The other
                     	octet of the Port ID is given by the value of
                     	rcStgPort."
        REFERENCE 	"IEEE 802.1D-1990: Section 4.5.5.1"
        DEFVAL          { 128 }
        ::= { rcStgPortEntry 3 }

rcStgPortState OBJECT-TYPE
        SYNTAX  	INTEGER {
	                	disabled(1),
       		         	blocking(2),
       	        		listening(3),
		                learning(4),
               		 	forwarding(5),
                		broken(6)
        		}
        MAX-ACCESS  	read-only
        STATUS  	current
        DESCRIPTION 	"The port's current state as defined by
                     	application of the Spanning Tree Protocol.  This
                     	state controls what action a port takes on
                     	reception of a frame.  If the bridge has detected
                     	a port that is malfunctioning it will place that
                     	port into the broken(6) state.  For ports which
                     	are disabled (see rcStgPortEnable), this object
                     	will have a value of disabled(1)."
        REFERENCE 	"IEEE 802.1D-1990: Section 4.5.5.2"
        ::= { rcStgPortEntry 4 }


rcStgPortEnableStp OBJECT-TYPE
        SYNTAX  	TruthValue
        MAX-ACCESS  	read-write
        STATUS  	current
        DESCRIPTION 	"The enabled/disabled status of the port."
        REFERENCE 	"IEEE 802.1D-1990: Section 4.5.5.2"
        DEFVAL           { true }
        ::= { rcStgPortEntry 5 }

rcStgPortFastStart OBJECT-TYPE
        SYNTAX     	TruthValue
        MAX-ACCESS     	read-write
        STATUS     	current
        DESCRIPTION 	"When this flag is set, the port is moved 
                     	straight to the forwarding(5) state upon 
                     	being enabled."
        DEFVAL          { false }
        ::= { rcStgPortEntry 6 }

rcStgPortPathCost OBJECT-TYPE
        SYNTAX  	INTEGER (1..65535)
        MAX-ACCESS  	read-write
        STATUS  	current
        DESCRIPTION 	"The contribution of this port to the path cost of
                     	paths towards the spanning tree root which include
                     	this port.  802.1D-1990 recommends that the
                     	default value of this parameter be in inverse
                     	proportion to the speed of the attached LAN."
        REFERENCE 	"IEEE 802.1D-1990: Section 4.5.5.3"
        ::= { rcStgPortEntry 7 }

rcStgPortDesignatedRoot OBJECT-TYPE
        SYNTAX  	BridgeId
        MAX-ACCESS  	read-only
        STATUS  	current
        DESCRIPTION 	"The unique Bridge Identifier of the Bridge
                     	recorded as the Root in the Configuration BPDUs
                     	transmitted by the Designated Bridge for the
                     	segment to which the port is attached."
        REFERENCE 	"IEEE 802.1D-1990: Section 4.5.5.4"
        ::= { rcStgPortEntry 8 }

rcStgPortDesignatedCost OBJECT-TYPE
        SYNTAX        Integer32
        MAX-ACCESS  	read-only
        STATUS  	current
        DESCRIPTION 	"The path cost of the Designated Port of the
                     	segment connected to this port.  This value is
                     	compared to the Root Path Cost field in received
                     	bridge PDUs."
        REFERENCE 	"IEEE 802.1D-1990: Section 4.5.5.5"
        ::= { rcStgPortEntry 9 }

rcStgPortDesignatedBridge OBJECT-TYPE
        SYNTAX  	BridgeId
        MAX-ACCESS  	read-only
        STATUS  	current
        DESCRIPTION 	"The Bridge Identifier of the bridge which this
                     	port considers to be the Designated Bridge for
                     	this port's segment."
        REFERENCE 	"IEEE 802.1D-1990: Section 4.5.5.6"
        ::= { rcStgPortEntry 10 }

rcStgPortDesignatedPort OBJECT-TYPE
        SYNTAX  	OCTET STRING (SIZE (2))
        MAX-ACCESS  	read-only
        STATUS  	current
        DESCRIPTION 	"The Port Identifier of the port on the Designated
                     	Bridge for this port's segment."
        REFERENCE 	"IEEE 802.1D-1990: Section 4.5.5.7"
        ::= { rcStgPortEntry 11 }

rcStgPortForwardTransitions OBJECT-TYPE
        SYNTAX  	Counter32
        MAX-ACCESS  	read-only
        STATUS  	current
        DESCRIPTION 	"The number of times this port has transitioned
                     	from the Learning state to the Forwarding state."
        ::= { rcStgPortEntry 12 }

rcStgPortInConfigBpdus OBJECT-TYPE
        SYNTAX  	Counter32
        MAX-ACCESS  	read-only
        STATUS  	current
        DESCRIPTION 	"The number of Config BPUDs received by
                     	this port."
        ::= { rcStgPortEntry 13 }

rcStgPortInTcnBpdus OBJECT-TYPE
        SYNTAX  	Counter32
        MAX-ACCESS  	read-only
        STATUS  	current
        DESCRIPTION 	"The number of Topology Change Notification
                     	BPUDs received by this port."
        ::= { rcStgPortEntry 14 }

rcStgPortInBadBpdus OBJECT-TYPE
        SYNTAX  	Counter32
        MAX-ACCESS  	read-only
        STATUS  	current
        DESCRIPTION 	"The number of Bad BPUDs received by this port."
        ::= { rcStgPortEntry 15 }

rcStgPortOutConfigBpdus OBJECT-TYPE
        SYNTAX  	Counter32
        MAX-ACCESS  	read-only
        STATUS  	current
        DESCRIPTION 	"The number of Config BPUDs transmitted by this port."
        ::= { rcStgPortEntry 16 }


rcStgPortOutTcnBpdus OBJECT-TYPE
        SYNTAX  	Counter32
        MAX-ACCESS  	read-only
        STATUS  	current
        DESCRIPTION 	"The number of Topology Change Notification
                     	BPUDs transmitted by this port."
        ::= { rcStgPortEntry 17 }

rcStgPortRowStatus OBJECT-TYPE
        SYNTAX  	RowStatus
        MAX-ACCESS  	read-write
        STATUS  	current
        DESCRIPTION 	"Row status."
        ::= { rcStgPortEntry 18 }


rcStgNotAllowedPorts OBJECT-TYPE 
        SYNTAX        PortSet  
        MAX-ACCESS        read-only
        STATUS        current 
        DESCRIPTION   "A bitfield used to identify which ports in 
                      the system that cannot be assigned to any STG
                      (i.e., which ports are single routable ports). 
 
                      The bitfield is 32 octets long representing 
                      ports 0 to 255 (inclusive)." 
        ::= { rcStg 6 } 


-- rcBridge Group
-- Forwarding Database for Transparent Bridges

rcBridgeFdbTable OBJECT-TYPE
	SYNTAX  	SEQUENCE OF RcBridgeFdbEntry
	MAX-ACCESS  	not-accessible
	STATUS  	current
	DESCRIPTION 	"This table is an replacement to the standard 
                     	dot1dTpFdbTable in rfc1493."
	::= { rcBridge 1 }

rcBridgeFdbEntry OBJECT-TYPE
	SYNTAX  	RcBridgeFdbEntry
	MAX-ACCESS  	not-accessible
	STATUS  	current
        DESCRIPTION 	"Information about a specific unicast MAC address
                     	for which the bridge has some forwarding information."
	INDEX { rcBridgeFdbStatus, rcBridgeFdbAddress }
	::= { rcBridgeFdbTable 1 }

RcBridgeFdbEntry ::=
	SEQUENCE {
                  rcBridgeFdbStatus INTEGER,
                  rcBridgeFdbAddress MacAddress,
                  rcBridgeFdbPort InterfaceIndex,
                  rcBridgeFdbMonitor TruthValue,
                  rcBridgeFdbPriority INTEGER,
                  rcBridgeFdbQosLevel INTEGER
                 }
 
rcBridgeFdbStatus OBJECT-TYPE
        SYNTAX  	INTEGER {
			      other(1),
			      invalid(2),
			      learned(3),
			      self(4),
			      mgmt(5)
			}
        MAX-ACCESS 	 	read-only
        STATUS 	 	current
        DESCRIPTION 	"This object indicates the status of this entry."
        ::= { rcBridgeFdbEntry 1 }

rcBridgeFdbAddress OBJECT-TYPE
        SYNTAX  	MacAddress
        MAX-ACCESS  	read-only
        STATUS  	current
        DESCRIPTION 	"A unicast MAC address for which the bridge 
	             	has forwarding and/or filtering information."
        REFERENCE "IEEE 802.1D-1990: Section 3.9.1, 3.9.2"
        ::= { rcBridgeFdbEntry 2 }

rcBridgeFdbPort OBJECT-TYPE
        SYNTAX  	InterfaceIndex
        MAX-ACCESS  	read-only
        STATUS  	current
        DESCRIPTION 	"Either the value '0', or the port number of the
      	             	port on which a frame having a source address
		        equal to the value of the corresponding instance
		        of rcBridgeFdbAddress has been seen.  A value of
		        '0' indicates that the port number has not been
		        learned but that the bridge does have some
		        forwarding/filtering information about this
		        address (e.g. in the dot1dStaticTable).
		        Implementors are encouraged to assign the port
		        value to this object whenever it is learned even
		        for addresses for which the corresponding value of
		        rcBridgeFdbStatus is not learned(3)."
        ::= { rcBridgeFdbEntry 3 }

rcBridgeFdbMonitor OBJECT-TYPE
        SYNTAX  	TruthValue
        MAX-ACCESS  	read-write
        STATUS  	current
        DESCRIPTION 	"Used to indicate whether monitoring should be
      	             	performed on this unicast MAC address.  If
	             	monitoring is enabled, any packet received
	             	with a matching destination MAC address
	             	will be forwarded to the port configured to
	             	receive monitor traffic."
        ::= { rcBridgeFdbEntry 4 }

rcBridgeFdbPriority OBJECT-TYPE
        SYNTAX  	INTEGER {
				low(0),
		            	high(1)
		        }
        MAX-ACCESS  	read-write
        STATUS  	deprecated
        DESCRIPTION   	"Used to indicate the priority of the incoming
                       	frames with this destination Mac Address."
        DEFVAL         { low }
        ::= { rcBridgeFdbEntry 5 }

rcBridgeFdbQosLevel OBJECT-TYPE
        SYNTAX  	INTEGER {
                            level0(0),
                            level1(1),
                            level2(2),
                            level3(3),
                            level4(4),
                            level5(5),
                            level6(6),
                            level7(7)
                        }
        MAX-ACCESS  	read-write
        STATUS  	current
        DESCRIPTION   	"Used to indicate the qos level of the incoming
                       	frames with this destination Mac Address."
	DEFVAL		{ level1 }
        ::= { rcBridgeFdbEntry 6 }

rcBridgeFdbTblSize OBJECT-TYPE  
        SYNTAX         	Integer32  
        MAX-ACCESS         	read-only  
        STATUS        	current  
        DESCRIPTION   	"Used to indicate the number of entries in 
                       	the bridge forwarding database table."    
        ::= { rcBridge 2 }


-- The Static (Destination-Address) Database
 
rcBridgeStaticTable OBJECT-TYPE
	SYNTAX  	SEQUENCE OF RcBridgeStaticEntry
	MAX-ACCESS  	not-accessible
	STATUS  	current
	DESCRIPTION 	"This table is a proprietary replacement to the standard
                     	dot1dStaticTable in rfc1493."
	::= { rcBridge 3 }
 
rcBridgeStaticEntry OBJECT-TYPE
	SYNTAX  	RcBridgeStaticEntry
	MAX-ACCESS  	not-accessible
	STATUS  	current
   	DESCRIPTION 	"A table containing forwarding information about unicast
                     	entries configured into the bridge by management. This
                     	information is used by the transparent bridging function
                     	in determining how to propagate a received frame."
	INDEX   { rcBridgeStaticAddress, rcBridgeStaticPort }
              ::= { rcBridgeStaticTable 1 }
 
RcBridgeStaticEntry ::=
SEQUENCE {
	  rcBridgeStaticAddress  MacAddress,
	  rcBridgeStaticPort     InterfaceIndex,
	  rcBridgeStaticMonitor  TruthValue,
	  rcBridgeStaticPriority INTEGER,
	  rcBridgeStaticStatus   INTEGER,
	  rcBridgeStaticQosLevel INTEGER
	 }

rcBridgeStaticAddress OBJECT-TYPE
        SYNTAX  	MacAddress
        MAX-ACCESS  	read-only
        STATUS  	current
        DESCRIPTION 	"The MAC address of this entry." 
        ::= { rcBridgeStaticEntry 1 }

rcBridgeStaticPort OBJECT-TYPE
        SYNTAX  	InterfaceIndex
        MAX-ACCESS  	read-only
        STATUS  	current
        DESCRIPTION 	"Port on which the MAC address is found."
        ::= { rcBridgeStaticEntry 2 }
 
rcBridgeStaticMonitor OBJECT-TYPE
        SYNTAX  	TruthValue 
        MAX-ACCESS  	read-write
        STATUS  	current
        DESCRIPTION 	"Used to indicate whether monitoring should be
		     	performed on incoming packets that match this
		     	entry."
        ::= { rcBridgeStaticEntry 3 }

rcBridgeStaticPriority OBJECT-TYPE
        SYNTAX  	INTEGER {
           			low(0),
			        high(1)
		        }
        MAX-ACCESS  	read-write
        STATUS  	deprecated
        DESCRIPTION 	"Used to indicate forwarding priority of incoming 
        	     	packets that match this entry." 
        DEFVAL         { low }
        ::= { rcBridgeStaticEntry 4 }

rcBridgeStaticStatus OBJECT-TYPE
       	SYNTAX  	INTEGER {
			    other(1),
			    invalid(2),
			    permanent(3),
			    deleteOnReset(4),
			    deleteOnTimeout(5)
       		        }
        MAX-ACCESS  	read-write
        STATUS  	current
        DESCRIPTION   	"This object indicates the status of this 
                       	entry. The default value is permanent(3)."
        ::= { rcBridgeStaticEntry 5 }

rcBridgeStaticQosLevel OBJECT-TYPE
        SYNTAX  	INTEGER {
                            level0(0),
                            level1(1),
                            level2(2),
                            level3(3),
                            level4(4),
                            level5(5),
                            level6(6),
                            level7(7)
                        }
        MAX-ACCESS  	read-write
        STATUS  	current
        DESCRIPTION   	"Used to indicate the qos level."
        DEFVAL         { level1 }
        ::= { rcBridgeStaticEntry 6 }

rcBridgeStaticTblSize OBJECT-TYPE  
        SYNTAX        	Integer32  
        MAX-ACCESS        	read-only  
        STATUS        	current  
        DESCRIPTION   	"Used to indicate the number of entries in 
                       	the bridge static table."    
        ::= { rcBridge 4 }

-- The filtering (Destination-Address) Database

rcBridgeFilterTable OBJECT-TYPE
	SYNTAX  	SEQUENCE OF RcBridgeFilterEntry
	MAX-ACCESS  	not-accessible
	STATUS  	current
	DESCRIPTION 	"This table is a proprietary replacement to the standard
                     	dot1dStaticTable (Filtering information) in rfc1493."
	::= { rcBridge 5 }
 
rcBridgeFilterEntry OBJECT-TYPE
	SYNTAX  	RcBridgeFilterEntry
	MAX-ACCESS  	not-accessible
	STATUS  	current
	DESCRIPTION 	"A table containing filtering information configured into
                     	the bridge by management specifying a destination address
                     	on a specific port and a set of incoming ports. Frames 
                     	received from one of the incoming ports and containing 
		     	the specific destination addresses are not allowed to be
		     	forwarded."
	INDEX   { rcBridgeFilterAddress, rcBridgeFilterPort }
        ::= { rcBridgeFilterTable 1 }
 
RcBridgeFilterEntry ::=
        SEQUENCE {
	     rcBridgeFilterAddress        MacAddress,
	     rcBridgeFilterPort           InterfaceIndex,
	     rcBridgeFilterNotAllowedFrom OCTET STRING,
	     rcBridgeFilterStatus         INTEGER
        }

rcBridgeFilterAddress OBJECT-TYPE
        SYNTAX  	MacAddress
        MAX-ACCESS  	read-only
        STATUS  	current
        DESCRIPTION 	"The MAC address of this entry.  This address is used
		     	to match the destination address of incoming packets."
        ::= { rcBridgeFilterEntry 1 }
 
rcBridgeFilterPort OBJECT-TYPE
        SYNTAX  	InterfaceIndex
        MAX-ACCESS  	read-only
        STATUS  	current
        DESCRIPTION 	"Port on which this MAC address is found."
        ::= { rcBridgeFilterEntry 2 }
 
rcBridgeFilterNotAllowedFrom OBJECT-TYPE
        SYNTAX  	OCTET STRING (SIZE(88))
        MAX-ACCESS  	read-write
        STATUS  	current
        DESCRIPTION 	"Used to indicate a set of ports.  Traffic arriving
		     	on any of the specified ports is not forwarded to this 
                     	MAC address."
        ::= { rcBridgeFilterEntry 3 }

rcBridgeFilterStatus OBJECT-TYPE
        SYNTAX  	INTEGER {
		               other(1),
       		               invalid(2),
       		               permanent(3),
       		               deleteOnReset(4),
       		               deleteOnTimeout(5)
       	         	}
        MAX-ACCESS  	read-write
        STATUS  	current
        DESCRIPTION 	"This object indicates the status of this 
                     	entry. The default value is permanent(3)."
        ::= { rcBridgeFilterEntry 4 }

rcBridgeFilterTblSize OBJECT-TYPE  
        SYNTAX        	Integer32  
        MAX-ACCESS        	read-only  
        STATUS        	current  
        DESCRIPTION   	"Used to indicate the number of entries in 
                       	the bridge filter table."    
        ::= { rcBridge 6 }

-- The unknown mac discard config table

rcBridgeUnknownMacDiscardTable OBJECT-TYPE
	SYNTAX  	SEQUENCE OF RcBridgeUnknownMacDiscardEntry
	MAX-ACCESS  	not-accessible
	STATUS  	current
	DESCRIPTION 	"This table is used to configure the 'unknown mac discard' feature.
                        This feature applies to layer 2 and layer 3 packets coming from 
                        or going out to a specific physical port."
	::= { rcBridge 7 }
 
rcBridgeUnknownMacDiscardEntry OBJECT-TYPE
	SYNTAX  	RcBridgeUnknownMacDiscardEntry
	MAX-ACCESS  	not-accessible
	STATUS  	current
	DESCRIPTION 	"A table containing information configuring
                        the 'unknown mac discard' feature."
	INDEX   { rcBridgeUnknownMacDiscardIfIndex }
        ::= { rcBridgeUnknownMacDiscardTable 1 }
 
RcBridgeUnknownMacDiscardEntry ::=
        SEQUENCE {
	    rcBridgeUnknownMacDiscardIfIndex                  InterfaceIndex,
	    rcBridgeUnknownMacDiscardAutoLearnEnable          TruthValue,
	    rcBridgeUnknownMacDiscardAutoLearnMode            INTEGER,
	    rcBridgeUnknownMacDiscardAutoLearnTableMode       INTEGER,
	    rcBridgeUnknownMacDiscardLogViolations            INTEGER,
	    rcBridgeUnknownMacDiscardSendTrap                 INTEGER,
	    rcBridgeUnknownMacDiscardDisablePort              INTEGER,
	    rcBridgeUnknownMacDiscardDefaultAutoLearnMonitor  INTEGER,
	    rcBridgeUnknownMacDiscardDefaultAutoLearnPriority INTEGER
        }

rcBridgeUnknownMacDiscardIfIndex OBJECT-TYPE
        SYNTAX  	InterfaceIndex
        MAX-ACCESS  	read-only
        STATUS  	current
        DESCRIPTION 	"Port on which this 'unknown mac discard' configuration applied to."
        ::= { rcBridgeUnknownMacDiscardEntry 1 }
 
rcBridgeUnknownMacDiscardAutoLearnEnable OBJECT-TYPE  
        SYNTAX        	TruthValue  
        MAX-ACCESS        	read-write  
        STATUS        	current  
        DESCRIPTION   	"This variable is used to enable/disable the auto-learn capability 
                         of a specific port. The default value is auto-learn disabled."
        ::= { rcBridgeUnknownMacDiscardEntry 2 }

rcBridgeUnknownMacDiscardAutoLearnMode OBJECT-TYPE  
        SYNTAX        	INTEGER {
                               oneShot(1),
                               continuous(2)
                        }
        MAX-ACCESS        	read-write  
        STATUS        	current  
        DESCRIPTION   	"This variable is used to control the auot-learn mode to either 
                         one-shot or continuous. In one-shot mode, the first n MAC addresses 
                         will be learned. The number n is dependents on the system's 
                         available resource. In continuous mode, MAC address is continuous 
                         learned until the resource limit is reached. After that the 
                         subsequent MAC will be disallowed until one of the original 
                         learned MAC is aged out. The default value is one-shot mode."
        ::= { rcBridgeUnknownMacDiscardEntry 3 }

rcBridgeUnknownMacDiscardAutoLearnTableMode OBJECT-TYPE
        SYNTAX  	INTEGER {
		               unlock(1),
       		               lock(2)
       	         	}
        MAX-ACCESS  	read-write
        STATUS  	current
        DESCRIPTION 	"This MIB variable is used to lock or unlock the auto-learn MAC 
                         table. When the auto-learn table is lock neither new MAC will be 
                         learned nor the original learned MAC will be aged out. User needs 
                         to lock the auto-learn table before MAC addresses can be save to 
                         the NVRAM. The whole auto-learn table will be flushed when the 
                         setting change from lock to unlock mode. The default value is 
                         unlock mode."
        ::= { rcBridgeUnknownMacDiscardEntry 4 }

rcBridgeUnknownMacDiscardLogViolations OBJECT-TYPE
        SYNTAX  	INTEGER {
		               disable(1),
       		               enable(2)
       	         	}
        MAX-ACCESS  	read-write
        STATUS  	current
        DESCRIPTION 	"This variable controls the logging action that the system will 
                         take when a MAC address violation event was detected. The 
                         value 'enable' means a log record will be written to the system 
                         log file when a violation event was detected. The default value 
                         is enable."
        ::= { rcBridgeUnknownMacDiscardEntry 5 }

rcBridgeUnknownMacDiscardSendTrap OBJECT-TYPE
        SYNTAX  	INTEGER {
		               disable(1),
       		               enable(2)
       	         	}
        MAX-ACCESS  	read-write
        STATUS  	current
        DESCRIPTION 	"This variable controls the send trap action that system will take 
                         when a MAC address violation event was detected. The value 'enable' 
                         means a SNMP trap packet will be send to the management station 
                         when a violation event was detected. The default value is disable."
        ::= { rcBridgeUnknownMacDiscardEntry 6 }

rcBridgeUnknownMacDiscardDisablePort OBJECT-TYPE
        SYNTAX  	INTEGER {
		               disable(1),
       		               enable(2)
       	         	}
        MAX-ACCESS  	read-write
        STATUS  	current
        DESCRIPTION 	"This variable controls the 'disable-port' action that system 
                         will take when a MAC address violation event was detected. The 
                         value 'enable' means the specific port will be disabled when the 
                         violation event was detected. It needs user manually to bring 
                         the port back once it was disabled. The default value is disable."
        ::= { rcBridgeUnknownMacDiscardEntry 7 }

rcBridgeUnknownMacDiscardDefaultAutoLearnMonitor OBJECT-TYPE
        SYNTAX  	INTEGER {
			 	none(1),
			 	monitor(2)
			}
        MAX-ACCESS  	read-write
        STATUS  	current
        DESCRIPTION 	"This variable controls the default monitor setting of an auto-learn 
                         MAC address. The value 'monitor' means a copy of packet that send 
                         from or to the auto-learned MAC address will be forwarded to the 
                         designated monitoring port on the system. The default value is none."
        ::= { rcBridgeUnknownMacDiscardEntry 8 }

rcBridgeUnknownMacDiscardDefaultAutoLearnPriority OBJECT-TYPE
        SYNTAX  	INTEGER {
		               low(1),
       		               high(2)
       	         	}
        MAX-ACCESS  	read-write
        STATUS  	current
        DESCRIPTION 	"This variable controls the default priority setting of an 
                         auto-learn MAC address. The value 'low' means packets send from 
                         the MAC address is forwarded at low priority. The value 'high' 
                         means packets send from the MAC address is forwarded at high 
                         priority. The default value is low."
        ::= { rcBridgeUnknownMacDiscardEntry 9 }

-- The Manual Edit table

rcBridgeManualEditTable OBJECT-TYPE
	SYNTAX  	SEQUENCE OF RcBridgeManualEditEntry
	MAX-ACCESS  	not-accessible
	STATUS  	current
	DESCRIPTION 	"This table is used to specify what MAC addresses can be learned 
                         on each port."
	::= { rcBridge 8 }
 
rcBridgeManualEditEntry OBJECT-TYPE
	SYNTAX  	RcBridgeManualEditEntry
	MAX-ACCESS  	not-accessible
	STATUS  	current
	DESCRIPTION 	"A table containing information of
                        MAC addresses that can be learned."
	INDEX   { rcBridgeManualEditAddress }
        ::= { rcBridgeManualEditTable 1 }
 
RcBridgeManualEditEntry ::=
        SEQUENCE {
	    rcBridgeManualEditAddress    MacAddress,
	    rcBridgeManualEditPorts      PortSet,
	    rcBridgeManualEditMonitor    TruthValue,
	    rcBridgeManualEditPriority   INTEGER,
	    rcBridgeManualEditStatus     INTEGER
        }

rcBridgeManualEditAddress OBJECT-TYPE
        SYNTAX  	MacAddress
        MAX-ACCESS  	read-only
        STATUS  	current
        DESCRIPTION 	"This variable contains the source MAC address of an entry."
        ::= { rcBridgeManualEditEntry 1 }
 
rcBridgeManualEditPorts OBJECT-TYPE  
        SYNTAX        	PortSet  
        MAX-ACCESS        	read-write  
        STATUS        	current  
        DESCRIPTION   	"This variable contains the allowed ports on which the MAC 
                         address of this entry can be learned."
        ::= { rcBridgeManualEditEntry 2 }

rcBridgeManualEditMonitor OBJECT-TYPE  
        SYNTAX        	TruthValue
        MAX-ACCESS        	read-write  
        STATUS        	current  
        DESCRIPTION   	"This variable specifies the monitoring setting of the MAC 
                         address. The value 'true' means a copy of packet frame that 
                         send from or to the MAC address is forwarded to the designated 
                         monitoring port on the system. The default value is false."
        ::= { rcBridgeManualEditEntry 3 }

rcBridgeManualEditPriority OBJECT-TYPE
        SYNTAX  	INTEGER {
		               low(1),
       		               high(2)
       	         	}
        MAX-ACCESS  	read-write
        STATUS  	current
        DESCRIPTION 	"This variable specifies the priority setting of the MAC address. 
                         The value 'low' means packet frames send from the MAC address 
                         is forwarded at low priority. The default value is low."
        ::= { rcBridgeManualEditEntry 4 }

rcBridgeManualEditStatus OBJECT-TYPE
        SYNTAX  	INTEGER {
		               other(1),
		               invalid(2),
       		               active(3)
       	         	}
        MAX-ACCESS  	read-write
        STATUS  	current
        DESCRIPTION 	"The variable controls the status of a MAC address in the table. 
                         The value 'active' is used to add the MAC address entry into the 
                         table. The value 'invalid' is used to delete the MAC address from 
                         the table."
        ::= { rcBridgeManualEditEntry 5 }

rcBridgeManualEditTblSize OBJECT-TYPE  
        SYNTAX        	Integer32  
        MAX-ACCESS        	read-only  
        STATUS        	current  
        DESCRIPTION   	"Used to indicate the number of entries in 
                       	the manual edit table."    
        ::= { rcBridge 9 }

-- The Auto Learn table

rcBridgeAutoLearnTable OBJECT-TYPE
	SYNTAX  	SEQUENCE OF RcBridgeAutoLearnEntry
	MAX-ACCESS  	not-accessible
	STATUS  	current
	DESCRIPTION 	"This table contains information of auto-learned MAC address when 
                         the 'unknow MAC discard' table's auto-learn is enabled. User must 
                         explicitly lock and save the table into NVRAM in order to have 
                         this table has the same configuration cross the system reset."
	::= { rcBridge 10 }
 
rcBridgeAutoLearnEntry OBJECT-TYPE
	SYNTAX  	RcBridgeAutoLearnEntry
	MAX-ACCESS  	not-accessible
	STATUS  	current
	DESCRIPTION 	"Entries in this table are created automatically
                        when the user explicitly does a lock operation on
                        the auto-learn-table (i.e., when 'AutoLearnTableMode'
                        is set to lock(2))."
	INDEX   { rcBridgeAutoLearnAddress }
        ::= { rcBridgeAutoLearnTable 1 }
 
RcBridgeAutoLearnEntry ::=
        SEQUENCE {
	    rcBridgeAutoLearnAddress    MacAddress,
	    rcBridgeAutoLearnPort       PortSet,
	    rcBridgeAutoLearnMonitor    TruthValue,
	    rcBridgeAutoLearnPriority   INTEGER,
	    rcBridgeAutoLearnAction     INTEGER
        }

rcBridgeAutoLearnAddress OBJECT-TYPE
        SYNTAX  	MacAddress
        MAX-ACCESS  	read-only
        STATUS  	current
        DESCRIPTION 	"This variable contains the source MAC address of the entries."
        ::= { rcBridgeAutoLearnEntry 1 }
 
rcBridgeAutoLearnPort OBJECT-TYPE  
        SYNTAX        	PortSet  
        MAX-ACCESS        	read-only  
        STATUS        	current  
        DESCRIPTION   	"This variable contains the port where the MAC address was learned."
        ::= { rcBridgeAutoLearnEntry 2 }

rcBridgeAutoLearnMonitor OBJECT-TYPE  
        SYNTAX        	TruthValue
        MAX-ACCESS        	read-only  
        STATUS        	current  
        DESCRIPTION   	"This variable contains the monitor setting of the MAC address. 
                         The value 'true' means a copy of packet frame that send from or 
                         to the MAC address is forwarded to the designated monitoring port 
                         on the system. This value should be synchronized with the setting 
                         of 'unknow MAC discard' table's 'Default AutoLearnMonitor' setting 
                         when the MAC address was learned."
        ::= { rcBridgeAutoLearnEntry 3 }

rcBridgeAutoLearnPriority OBJECT-TYPE
        SYNTAX  	INTEGER {
		               low(1),
       		               high(2)
       	         	}
        MAX-ACCESS  	read-only
        STATUS  	current
        DESCRIPTION 	"This variable contains the priority setting of the MAC address. 
                         The value 'low' means packet frames send from the MAC address is 
                         forwarded at low priority. The value 'high' means packet frames 
                         send from the MAC address is forwarded at high priority. This 
                         value should be synchronized with the setting of 'unknow MAC 
                         discard' table's 'DefaultAutoLearnPriority' setting when the MAC
                         address was learned."
        ::= { rcBridgeAutoLearnEntry 4 }

rcBridgeAutoLearnAction OBJECT-TYPE
        SYNTAX  	INTEGER {
		               none(0),
		               convertToManualEdit(1)
       	         	}
        MAX-ACCESS  	read-write
        STATUS  	current
        DESCRIPTION 	"This variable is for converting an auto-learned MAC address entry 
                         to a manual edit MAC address entry. This variable provides a mechanism
                         for user to move a MAC address entry from auto-learn table to manual 
                         edit table."
        ::= { rcBridgeAutoLearnEntry 5 }


rcBridgeAutoLearnTblSize OBJECT-TYPE  
        SYNTAX        	Integer32  
        MAX-ACCESS        	read-only  
        STATUS        	current  
        DESCRIPTION   	"Used to indicate the number of entries in 
                       	the auto learn table."    
        ::= { rcBridge 11 }


-- The Statis Multicast table

rcBridgeStaticMulticastTable OBJECT-TYPE
	SYNTAX  	SEQUENCE OF RcBridgeStaticMulticastEntry
	MAX-ACCESS  	not-accessible
	STATUS  	current
	DESCRIPTION 	""
	::= { rcBridge 12 }
 
rcBridgeStaticMulticastEntry OBJECT-TYPE
	SYNTAX  	RcBridgeStaticMulticastEntry
	MAX-ACCESS  	not-accessible
	STATUS  	current
	DESCRIPTION 	""
	INDEX   { rcBridgeStaticMulticastAddress }
        ::= { rcBridgeStaticMulticastTable 1 }
 
RcBridgeStaticMulticastEntry ::=
        SEQUENCE {
	    rcBridgeStaticMulticastAddress         MacAddress,
	    rcBridgeStaticMulticastForwardingPorts PortSet,
	    rcBridgeStaticMulticastMltIds          IdList,
	    rcBridgeStaticMulticastRowStatus       RowStatus
        }

rcBridgeStaticMulticastAddress OBJECT-TYPE
        SYNTAX  	MacAddress
        MAX-ACCESS  	read-only
        STATUS  	current
        DESCRIPTION 	"src mac addr."
        ::= { rcBridgeStaticMulticastEntry 1 }
 
rcBridgeStaticMulticastForwardingPorts OBJECT-TYPE  
        SYNTAX        	PortSet  
        MAX-ACCESS        	read-write  
        STATUS        	current  
        DESCRIPTION   	"ports for forward this mac"
        ::= { rcBridgeStaticMulticastEntry 2 }

rcBridgeStaticMulticastMltIds OBJECT-TYPE  
        SYNTAX        	IdList
        MAX-ACCESS        	read-write  
        STATUS        	current  
        DESCRIPTION   	"list of mlts this mac will be forwarded on"
        ::= { rcBridgeStaticMulticastEntry 3 }

rcBridgeStaticMulticastRowStatus OBJECT-TYPE
        SYNTAX  	RowStatus
        MAX-ACCESS  	read-write
        STATUS  	current
        DESCRIPTION 	"row status"
        ::= { rcBridgeStaticMulticastEntry 4 }

rcBridgeStaticMulticastTblSize OBJECT-TYPE  
        SYNTAX        	Integer32  
        MAX-ACCESS        	read-only  
        STATUS        	current  
        DESCRIPTION   	"Used to indicate the number of entries in 
                       	the static multicast table."    
        ::= { rcBridge 13 }


-- rcBoot Group
rcBootFlashSwVersion OBJECT-TYPE
        SYNTAX        DisplayString
        MAX-ACCESS        read-only
        STATUS        obsolete
        DESCRIPTION   "BootFlashSwVersion indicates the software
                      version in the Flash."
        ::= { rcBoot 1 } 
 
rcBootPcmciaSwVersion OBJECT-TYPE
        SYNTAX        DisplayString
        MAX-ACCESS        read-only
        STATUS        obsolete
        DESCRIPTION   "BootPcmciaSwVersion indicate the software
                      version in the Pcmcia card."
        ::= { rcBoot 2 } 
 

rcBootLastBootSource OBJECT-TYPE
        SYNTAX        DisplayString
        MAX-ACCESS        read-only
        STATUS        obsolete
        DESCRIPTION   "Indicates the boot source of the last
                      the system boot."
        ::= { rcBoot 3 } 
 
rcBootPrimary OBJECT-TYPE
        SYNTAX          INTEGER {
                           flash(1),
                           pcmcia(2),
                           net(3),
                           skip(4)
                        }
        MAX-ACCESS        	read-write
        STATUS        	obsolete
        DESCRIPTION   	"BootPrimary is indicator for the
                     	primary source to boot the system."
	DEFVAL 		{ flash }
        ::= { rcBoot 4 } 
 
rcBootSecondary OBJECT-TYPE
        SYNTAX          INTEGER {
                           flash(1),
                           pcmcia(2),
                           net(3),
                           skip(4)
                        }
        MAX-ACCESS        	read-write
        STATUS        	obsolete
        DESCRIPTION   	"BootSecondary indicates the second choice
                        of the boot source."
	DEFVAL 		{ pcmcia }
        ::= { rcBoot 5 } 
 
rcBootTertiary OBJECT-TYPE
        SYNTAX          INTEGER {
                           flash(1),
                           pcmcia(2),
                           net(3),
                           skip(4)
                        }
        MAX-ACCESS        	read-write
        STATUS        	obsolete
        DESCRIPTION   	"BootTertiary indicates the third choice 
                        of boot source."
	DEFVAL 		{ net }
        ::= { rcBoot 6 } 
 

-- rcDevice Group
rcDeviceLastBootSource OBJECT-TYPE
        SYNTAX          DisplayString
        MAX-ACCESS          read-only
        STATUS          current
        DESCRIPTION     "Used to indicate the source of the software
                         image the system was last booted with."
        ::= { rcDevice 1 } 
 
rcDevicePrimarySource OBJECT-TYPE
        SYNTAX          INTEGER {
                           flash(1),
                           pcmcia(2),
                           net(3),
                           skip(4)
                        }
        MAX-ACCESS        	read-write
        STATUS        	current
        DESCRIPTION   	"Used to indicate the primary choice to get
                         a system software image."
        ::= { rcDevice 2 } 
 
rcDevicePrimarySourceFileName OBJECT-TYPE
        SYNTAX          DisplayString (SIZE(0..31))
        MAX-ACCESS          read-write
        STATUS          current
        DESCRIPTION     "Used to indicate a file number, if applicable."
        ::= { rcDevice 3 } 

rcDeviceSecondarySource OBJECT-TYPE
        SYNTAX          INTEGER {
                           flash(1),
                           pcmcia(2),
                           net(3),
                           skip(4)
                        }
        MAX-ACCESS        	read-write
        STATUS        	current
        DESCRIPTION   	"Used to indicate the secondary choice to get
                         a system software image."
        ::= { rcDevice 4 } 
 
rcDeviceSecondarySourceFileName OBJECT-TYPE
        SYNTAX          DisplayString (SIZE(0..31))
        MAX-ACCESS          read-write
        STATUS          current
        DESCRIPTION     "Used to indicate a file name, if applicable."
        ::= { rcDevice 5 } 

rcDeviceTertiarySource OBJECT-TYPE
        SYNTAX          INTEGER {
                           flash(1),
                           pcmcia(2),
                           net(3),
                           skip(4)
                        }
        MAX-ACCESS        	read-write
        STATUS        	current
        DESCRIPTION   	"Used to indicate the tertiary choice to get
                         a system software image."
        ::= { rcDevice 6 } 
 
rcDeviceTertiarySourceFileName OBJECT-TYPE
        SYNTAX          DisplayString (SIZE(0..31))
        MAX-ACCESS          read-write
        STATUS          current
        DESCRIPTION     "Used to indicate a file name, if applicable."
        ::= { rcDevice 7 } 

rcDeviceConfigSource OBJECT-TYPE
        SYNTAX          INTEGER {
                           flash(1),
                           pcmcia(2),
			   nvram(5)
                        }
        MAX-ACCESS        	read-write
        STATUS        	current
        DESCRIPTION   	"Used to indicate the location to get a system 
			configuration file during system boot."
        ::= { rcDevice 8 } 
 
rcDeviceConfigSourceFileName OBJECT-TYPE
        SYNTAX          DisplayString (SIZE(0..31))
        MAX-ACCESS          read-write
        STATUS          current
        DESCRIPTION     "Used to indicate a file name, if applicable."
        ::= { rcDevice 9 } 

rcDeviceFlashBytesUsed OBJECT-TYPE
        SYNTAX        Integer32
        MAX-ACCESS          read-only
        STATUS          current
        DESCRIPTION     "Used to indicate the number of bytes used in the
                         system's configuration flash device."
        ::= { rcDevice 10 } 

rcDeviceFlashBytesFree OBJECT-TYPE
        SYNTAX        Integer32
        MAX-ACCESS          read-only
        STATUS          current
        DESCRIPTION     "Used to indicate the number of bytes available in
                         the system's configuration flash device."
        ::= { rcDevice 11 } 

rcDevicePcmciaBytesUsed OBJECT-TYPE
        SYNTAX        Integer32
        MAX-ACCESS          read-only
        STATUS          current
        DESCRIPTION     "Used to indicate the number of bytes used in the
                         system's PCMCIA device."
        ::= { rcDevice 12 } 

rcDevicePcmciaBytesFree OBJECT-TYPE
        SYNTAX        Integer32
        MAX-ACCESS          read-only
        STATUS          current
        DESCRIPTION     "Used to indicate the number of bytes available in 
                         the system's PCMCIA device."
        ::= { rcDevice 13 } 

rcDeviceAction OBJECT-TYPE
        SYNTAX          INTEGER {
			    none(1),
                            squeezeFlash(2),
                            squeezePcmcia(3),
                            formatFlash(4),
                            formatPcmcia(5),
                            recoverFlash(6), 
                            recoverPcmcia(7) 
                        }
        MAX-ACCESS        	read-write
        STATUS        	current
        DESCRIPTION   	"Used to specify a particular action to perform on
                         one of the system's device."
        ::= { rcDevice 14 } 
 
rcDeviceResult OBJECT-TYPE
        SYNTAX          INTEGER {
                            none(1),
                            inProgress(2),
                            success(3),
                            fail(4)
                        }
        MAX-ACCESS        	read-only
        STATUS        	current
        DESCRIPTION   	"Used to indicate the result of the last action
                         performed on one of the system's device."
        ::= { rcDevice 15 } 
 
rcDeviceFlashNumFiles OBJECT-TYPE
        SYNTAX          INTEGER (0..128)
        MAX-ACCESS          read-only
        STATUS          current
        DESCRIPTION     "Used to indicate the number of files available in
                         the system's configuration flash device."
        ::= { rcDevice 16 }
 
rcDevicePcmciaNumFiles OBJECT-TYPE
        SYNTAX          INTEGER (0..128)
        MAX-ACCESS          read-only
        STATUS          current
        DESCRIPTION     "Used to indicate the number of files available in
                         the system's PCMCIA device."
        ::= { rcDevice 17 }
 

-- The Device Flash Table

rcDeviceFlashTable OBJECT-TYPE
	SYNTAX  	SEQUENCE OF RcDeviceFlashEntry
	MAX-ACCESS  	not-accessible
	STATUS  	current
	DESCRIPTION 	"Flash table."
	::= { rcDevice 25 }
 
rcDeviceFlashEntry OBJECT-TYPE
	SYNTAX  	RcDeviceFlashEntry
	MAX-ACCESS  	not-accessible
	STATUS  	current
	DESCRIPTION 	"An entry in the system's flash table."
	INDEX   { rcDeviceFlashFileNum }
        ::= { rcDeviceFlashTable 1 }
 
RcDeviceFlashEntry ::=
        SEQUENCE {
	     rcDeviceFlashFileNum     INTEGER,
	     rcDeviceFlashFileName    DisplayString,
	     rcDeviceFlashFileVersion DisplayString,
	     rcDeviceFlashFileType    INTEGER,
	     rcDeviceFlashFileMode    INTEGER,
	     rcDeviceFlashFileSize    INTEGER,
	     rcDeviceFlashFileCrc     INTEGER,
	     rcDeviceFlashFileStatus  INTEGER,
	     rcDeviceFlashRowStatus   RowStatus
        }

rcDeviceFlashFileNum OBJECT-TYPE
        SYNTAX  	INTEGER (0..128)
        MAX-ACCESS  	read-only
        STATUS  	current
        DESCRIPTION 	"Used to indicate a particular file in flash."
        ::= { rcDeviceFlashEntry 1 }
 
rcDeviceFlashFileName OBJECT-TYPE
        SYNTAX  	DisplayString
        MAX-ACCESS  	read-only
        STATUS  	current
        DESCRIPTION 	"Used to indicate a flash file's name."
        ::= { rcDeviceFlashEntry 2 }
 
rcDeviceFlashFileVersion OBJECT-TYPE
        SYNTAX  	DisplayString
        MAX-ACCESS  	read-only
        STATUS  	current
        DESCRIPTION 	"Used to indicate the flash file's version."
        ::= { rcDeviceFlashEntry 3 }
 
rcDeviceFlashFileType OBJECT-TYPE
        SYNTAX  	INTEGER {
                           config(1),
                           log(2),
                           trace(3),
                           executable(4)
                        }
        MAX-ACCESS  	read-only
        STATUS  	current
        DESCRIPTION     "Used to indicate the flash file's type."
        ::= { rcDeviceFlashEntry 4 }
 
rcDeviceFlashFileMode OBJECT-TYPE
        SYNTAX  	INTEGER {
                           compressed(1),
                           uncompressed(2)
                        }
        MAX-ACCESS  	read-only
        STATUS  	current
        DESCRIPTION     "Used to indicate the flash file's mode."
        ::= { rcDeviceFlashEntry 5 }
 
rcDeviceFlashFileSize OBJECT-TYPE
        SYNTAX        Integer32
        MAX-ACCESS  	read-only
        STATUS  	current
        DESCRIPTION     "Used to indicate the flash file's size."
        ::= { rcDeviceFlashEntry 6 }
 
rcDeviceFlashFileCrc OBJECT-TYPE
        SYNTAX        Integer32
        MAX-ACCESS  	read-only
        STATUS  	current
        DESCRIPTION     "Used to indicate the flash file's CRC."
        ::= { rcDeviceFlashEntry 7 }
 
rcDeviceFlashFileStatus OBJECT-TYPE
        SYNTAX  	INTEGER {
                           active(1),
                           deleted(2)
                        }
        MAX-ACCESS  	read-only
        STATUS  	current
        DESCRIPTION     "Used to indicate the flash file's status.
                         A file that has been marked for deletion, but  
                         who's space has not been reclaimed yet is marked
                         as 'deleted'."
        ::= { rcDeviceFlashEntry 8 }
 
rcDeviceFlashRowStatus OBJECT-TYPE
        SYNTAX  	RowStatus
        MAX-ACCESS  	read-write
        STATUS  	current
        DESCRIPTION 	"Row status."
        ::= { rcDeviceFlashEntry 9 }


-- The Device Pcmcia Table

rcDevicePcmciaTable OBJECT-TYPE
	SYNTAX  	SEQUENCE OF RcDevicePcmciaEntry
	MAX-ACCESS  	not-accessible
	STATUS  	current
	DESCRIPTION 	"PCMCIA table."
	::= { rcDevice 26 }
 
rcDevicePcmciaEntry OBJECT-TYPE
	SYNTAX  	RcDevicePcmciaEntry
	MAX-ACCESS  	not-accessible
	STATUS  	current
        DESCRIPTION     "An entry in the system's PCMCIA table."
	INDEX   { rcDevicePcmciaFileNum }
        ::= { rcDevicePcmciaTable 1 }
 
RcDevicePcmciaEntry ::=
        SEQUENCE {
	     rcDevicePcmciaFileNum     INTEGER,
	     rcDevicePcmciaFileName    DisplayString,
	     rcDevicePcmciaFileVersion DisplayString,
	     rcDevicePcmciaFileType    INTEGER,
	     rcDevicePcmciaFileMode     INTEGER,
	     rcDevicePcmciaFileSize    INTEGER,
	     rcDevicePcmciaFileCrc     INTEGER,
	     rcDevicePcmciaFileStatus  INTEGER,
	     rcDevicePcmciaRowStatus   RowStatus
        }

rcDevicePcmciaFileNum OBJECT-TYPE
        SYNTAX  	INTEGER (0..128)
        MAX-ACCESS  	read-only
        STATUS  	current
        DESCRIPTION     "Used to indicate a particular file in PCMCIA."
        ::= { rcDevicePcmciaEntry 1 }
 
rcDevicePcmciaFileName OBJECT-TYPE
        SYNTAX  	DisplayString
        MAX-ACCESS  	read-only
        STATUS  	current
        DESCRIPTION     "Used to indicate the PCMCIA file's name."
        ::= { rcDevicePcmciaEntry 2 }
 
rcDevicePcmciaFileVersion OBJECT-TYPE
        SYNTAX  	DisplayString
        MAX-ACCESS  	read-only
        STATUS  	current
        DESCRIPTION     "Used to indicate the PCMCIA file's version."
        ::= { rcDevicePcmciaEntry 3 }
 
rcDevicePcmciaFileType OBJECT-TYPE
        SYNTAX  	INTEGER {
                           config(1),
                           log(2),
                           trace(3),
                           executable(4)
                        }
        MAX-ACCESS  	read-only
        STATUS  	current
        DESCRIPTION     "Used to indicate the PCMCIA file's type."
        ::= { rcDevicePcmciaEntry 4 }
 
rcDevicePcmciaFileMode OBJECT-TYPE
        SYNTAX  	INTEGER {
                           compressed(1),
                           uncompressed(2)
                        }
        MAX-ACCESS  	read-only
        STATUS  	current
        DESCRIPTION     "Used to indicate a particular file in mode."
        ::= { rcDevicePcmciaEntry 5 }
 
rcDevicePcmciaFileSize OBJECT-TYPE
        SYNTAX        Integer32
        MAX-ACCESS  	read-only
        STATUS  	current
        DESCRIPTION     "Used to indicate the PCMCIA file's size."
        ::= { rcDevicePcmciaEntry 6 }
 
rcDevicePcmciaFileCrc OBJECT-TYPE
        SYNTAX        Integer32
        MAX-ACCESS  	read-only
        STATUS  	current
        DESCRIPTION     "Used to indicate the PCMCIA file's CRC."
        ::= { rcDevicePcmciaEntry 7 }
 
rcDevicePcmciaFileStatus OBJECT-TYPE
        SYNTAX  	INTEGER {
                           active(1),
                           deleted(2)
                        }
        MAX-ACCESS  	read-only
        STATUS  	current
        DESCRIPTION     "Used to indicate the PCMCIA file's status.
                         A file that has been marked for deletion, but
                         who's space has not been reclaimed yet is marked
                         as 'deleted'."
        ::= { rcDevicePcmciaEntry 8 }
 
rcDevicePcmciaRowStatus OBJECT-TYPE
        SYNTAX  	RowStatus
        MAX-ACCESS  	read-write
        STATUS  	current
        DESCRIPTION 	"Row status."
        ::= { rcDevicePcmciaEntry 9 }


-- Multi-Link Trunking Table

rcMltNumMlts OBJECT-TYPE
        SYNTAX        Integer32
        MAX-ACCESS        	read-only
        STATUS        	current
        DESCRIPTION   	"The number of MLTs currently defined in the switch."
        ::= { rcMlt 1 }

rcMltPotentialMembers OBJECT-TYPE
        SYNTAX        	PortSet
        MAX-ACCESS        	read-only
        STATUS        	current
        DESCRIPTION   	"The set of ports that are not members of any MLT."
        ::= { rcMlt 2 }

rcMltTable OBJECT-TYPE
        SYNTAX        	SEQUENCE OF RcMltEntry
        MAX-ACCESS        	not-accessible
        STATUS        	current
        DESCRIPTION   	"A list of Multi-Link Trunk entries. The number of 
                      	entries is given by rcMltNumMlts."
        ::= { rcMlt 10 }

rcMltEntry OBJECT-TYPE
        SYNTAX        	RcMltEntry
        MAX-ACCESS        	not-accessible
        STATUS        	current
        DESCRIPTION   	"Entry containing configuration information for a 
                      	particular Multi-Link Trunk."
        INDEX         	{ rcMltId }
        ::= { rcMltTable 1 }

RcMltEntry ::= SEQUENCE {
                rcMltId	                    INTEGER,
                rcMltName                   DisplayString,
                rcMltPortMembers            PortSet,
		rcMltPortType               INTEGER,	
		rcMltNumVlanIds             INTEGER,
		rcMltVlanIds                IdList,
                rcMltRowStatus              RowStatus,
		rcMltEnable                 TruthValue,
		rcMltLoadBalance            TruthValue,
		rcMltDistributionAlgorithm  INTEGER,
		rcMltIfIndex		    InterfaceIndex
        }

rcMltId OBJECT-TYPE
        SYNTAX        	INTEGER (1..32)
        MAX-ACCESS        	read-only
        STATUS        	current
        DESCRIPTION   	"A value that uniquely identifies the Multi-Link 
                      	Trunk associated with this entry."
        ::= { rcMltEntry 1 }

rcMltName OBJECT-TYPE
        SYNTAX        	DisplayString (SIZE (0..20))
        MAX-ACCESS        	read-write
        STATUS        	current
        DESCRIPTION   	"An administratively-assigned name for this MLT."
        ::= { rcMltEntry 2 }

rcMltPortMembers OBJECT-TYPE
        SYNTAX        	PortSet
        MAX-ACCESS        	read-write
        STATUS        	current
        DESCRIPTION   	"The set of ports that are members of this MLT." 
        ::= { rcMltEntry 3 }

rcMltPortType OBJECT-TYPE
        SYNTAX        	INTEGER {
                        	access(1),     -- access port type
                         	trunk(2)       -- trunk port type
                      	}
        MAX-ACCESS        	read-write
        STATUS        	current
        DESCRIPTION   	"The type of MLT port: access(1) or trunk(2)."
	DEFVAL 		{ access }
        ::= { rcMltEntry 4 }
 
rcMltNumVlanIds OBJECT-TYPE
        SYNTAX        Integer32
        MAX-ACCESS        	read-only
        STATUS        	current
        DESCRIPTION   	"Used to indicate the number of VLAN IDs that
                      	are stored in the rcMltVlanIds variable."
        ::= { rcMltEntry 5 }

rcMltVlanIds OBJECT-TYPE
        SYNTAX        	IdList (SIZE (4096))
        MAX-ACCESS        	read-write
        STATUS        	current
        DESCRIPTION   	"An array used to identify which VLANs this MLT 
                      	is associated with.  Each VLAN ID is stored as a 
		      	two octet value. The first octet in the pair holds
                      	bits 15-8 of the VLAN ID, while the second octet
                      	holds bits 7-0 of the VLAN ID."
        ::= { rcMltEntry 6 }

rcMltRowStatus OBJECT-TYPE
        SYNTAX        	RowStatus
        MAX-ACCESS        	read-write
        STATUS        	current
        DESCRIPTION   	"Used to create/delete entries in the rcMltTable."
        ::= { rcMltEntry 7 }

rcMltEnable OBJECT-TYPE
        SYNTAX        	TruthValue
        MAX-ACCESS        	read-write
        STATUS        	current
        DESCRIPTION   	"Enable the entry."
	DEFVAL 		{ true }
        ::= { rcMltEntry 8 }

rcMltLoadBalance OBJECT-TYPE
        SYNTAX        	TruthValue
        MAX-ACCESS        	read-write
        STATUS        	current
        DESCRIPTION   	"Perform load balance?"
	DEFVAL	{ false }
        ::= { rcMltEntry 9 }

rcMltDistributionAlgorithm OBJECT-TYPE
        SYNTAX        	INTEGER {
                        	none(1)
                      	}
        MAX-ACCESS        	read-write
        STATUS        	current
        DESCRIPTION   	"none(1), ...  It will be fill later"
	DEFVAL		{ none }
        ::= { rcMltEntry 10 }

rcMltIfIndex OBJECT-TYPE
        SYNTAX        InterfaceIndex
        MAX-ACCESS        read-only
        STATUS        current
        DESCRIPTION   "Used to indicate the 'logical' ifIndex assigned to
                      this MLT."
        ::= { rcMltEntry 11 }


-- rcWeb related information

rcWebEnableServer OBJECT-TYPE
        SYNTAX        TruthValue
        MAX-ACCESS        read-write
        STATUS        current
        DESCRIPTION   "Control whether the web server should be enabled.
		      Setting this variable to true will make the server
		      operational.  Setting this variable to false will
		      disable server."
        DEFVAL        { false }
        ::= { rcWeb 1 }

rcWebRWAUserName OBJECT-TYPE
        SYNTAX        DisplayString (SIZE (1..20))
        MAX-ACCESS        read-write
        STATUS        current
        DESCRIPTION   "User name for the read-write-all web-server account."
        ::= { rcWeb 2 }

rcWebRWAPassword OBJECT-TYPE
        SYNTAX        DisplayString (SIZE (1..20))
        MAX-ACCESS        read-write
        STATUS        current
        DESCRIPTION   "Password for the read-write-all web-server account."
        ::= { rcWeb 3 }

rcWebRWUserName OBJECT-TYPE
        SYNTAX        DisplayString (SIZE (1..20))
        MAX-ACCESS        read-write
        STATUS        current
        DESCRIPTION   "User name for the read-write web-server account."
        ::= { rcWeb 4 }
 
rcWebRWPassword OBJECT-TYPE 
        SYNTAX        DisplayString (SIZE (1..20)) 
        MAX-ACCESS        read-write 
        STATUS        current 
        DESCRIPTION   "Password for the read-write web-server account." 
        ::= { rcWeb 5 } 

rcWebROUserName OBJECT-TYPE
        SYNTAX        DisplayString (SIZE (1..20))
        MAX-ACCESS        read-write
        STATUS        current
        DESCRIPTION   "User name for the read-only web-server account."
        ::= { rcWeb 6 }
 
rcWebROPassword OBJECT-TYPE 
        SYNTAX        DisplayString (SIZE (1..20))
        MAX-ACCESS        read-write 
        STATUS        current 
        DESCRIPTION   "Password for the read-only web-server account." 
        ::= { rcWeb 7 } 

rcWebLastChange OBJECT-TYPE 
        SYNTAX        TimeTicks 
        MAX-ACCESS        read-only 
        STATUS        current 
        DESCRIPTION   "Last web-browser initiated configuration
                      change since sysUpTime."
        ::= { rcWeb 8 }
 
rcWebNumHits OBJECT-TYPE
        SYNTAX        Integer32
        MAX-ACCESS        read-only
        STATUS        current
        DESCRIPTION   "Number of hits to the web-server"
	::= { rcWeb 9 } 

rcWebNumAccessChecks OBJECT-TYPE
        SYNTAX        Integer32
        MAX-ACCESS        read-only
        STATUS        current
        DESCRIPTION   "Number of access checks performed by the web-server"
        ::= { rcWeb 10 }

rcWebNumAccessBlocks OBJECT-TYPE
        SYNTAX        Integer32
        MAX-ACCESS        read-only
        STATUS        current
        DESCRIPTION   "Number of accesses blocked by the web-server"
        ::= { rcWeb 11 }

rcWebNumRxErrors OBJECT-TYPE 
        SYNTAX        Integer32
        MAX-ACCESS        read-only 
        STATUS        current 
        DESCRIPTION   "Number of receive errors encountered by the web-server" 
        ::= { rcWeb 12 }

rcWebNumTxErrors OBJECT-TYPE 
        SYNTAX        Integer32
        MAX-ACCESS        read-only 
        STATUS        current 
        DESCRIPTION   "Number of transmit errors encountered by the web-server" 
        ::= { rcWeb 13 }

rcWebNumSetRequest OBJECT-TYPE 
        SYNTAX        Integer32
        MAX-ACCESS        read-only 
        STATUS        current 
        DESCRIPTION   "Number of set-request to the web-server" 
        ::= { rcWeb 14 }

rcWebPrimaryHtmlSourceDir OBJECT-TYPE
        SYNTAX        DisplayString (SIZE(0..64))
        MAX-ACCESS        read-write
        STATUS        current
        DESCRIPTION   "primary html source directory"
	DEFVAL	      { "local" }
        ::= { rcWeb 15 }
 
rcWebSecondaryHtmlSourceDir OBJECT-TYPE
        SYNTAX        DisplayString (SIZE(0..64))
        MAX-ACCESS        read-write
        STATUS        current
        DESCRIPTION   "secondary html source directory"
	DEFVAL	      { "pcmcia" }
        ::= { rcWeb 16 }
 
rcWebTertiaryHtmlSourceDir OBJECT-TYPE
        SYNTAX        DisplayString (SIZE(0..64))
        MAX-ACCESS        read-write
        STATUS        current
        DESCRIPTION   "tertiary html source directory"
        ::= { rcWeb 17 }
 
rcWebRWL3UserName OBJECT-TYPE
        SYNTAX        DisplayString (SIZE (1..20))
        MAX-ACCESS        read-write
        STATUS        current
        DESCRIPTION   "user name for the L3 web server account"
        ::= { rcWeb 18 }
 
rcWebRWL3Password OBJECT-TYPE
        SYNTAX        DisplayString (SIZE (1..20))
        MAX-ACCESS        read-write
        STATUS        current
        DESCRIPTION   "password for the L3 web server account"
        ::= { rcWeb 19 }

rcWebRWL2UserName OBJECT-TYPE
        SYNTAX        DisplayString (SIZE (1..20))
        MAX-ACCESS        read-write
        STATUS        current
        DESCRIPTION   "user name for the L2 web server account"
        ::= { rcWeb 20 }
 
rcWebRWL2Password OBJECT-TYPE
        SYNTAX        DisplayString (SIZE (1..20))
        MAX-ACCESS        read-write
        STATUS        current
        DESCRIPTION   "password for the L2 web server account"
        ::= { rcWeb 21 }
 
rcWebDefaultDisplayRows OBJECT-TYPE
        SYNTAX        INTEGER (10..100)
        MAX-ACCESS        read-write
        STATUS        current
        DESCRIPTION   "default display rows in html page."
	DEFVAL	      { 48 }
        ::= { rcWeb 22 }

rcWebLastHostAccessBlocked OBJECT-TYPE
        SYNTAX        IpAddress
        MAX-ACCESS        read-only
        STATUS        current
        DESCRIPTION   "last host access blocked"
        ::= { rcWeb 23 }
 
rcWebHelpTftpSourceDir OBJECT-TYPE
        SYNTAX        DisplayString (SIZE (0..64))
        MAX-ACCESS        read-write
        STATUS        current
        DESCRIPTION   "tftp source directory for help files"
        ::= { rcWeb 24 }
 

-- rcCli related information

rcCliRWAUserName OBJECT-TYPE
        SYNTAX        DisplayString (SIZE (1..20))
        MAX-ACCESS        read-write
        STATUS        current
        DESCRIPTION   "User name for the read-write-all CLI account."
        ::= { rcCli 1 }

rcCliRWAPassword OBJECT-TYPE
        SYNTAX        DisplayString (SIZE (0..20))
        MAX-ACCESS        read-write
        STATUS        current
        DESCRIPTION   "Password for the read-write-all CLI account."
        ::= { rcCli 2 }

rcCliRWUserName OBJECT-TYPE
        SYNTAX        DisplayString (SIZE (1..20))
        MAX-ACCESS        read-write
        STATUS        current
        DESCRIPTION   "User name for the read-write CLI account."
        ::= { rcCli 3 }
 
rcCliRWPassword OBJECT-TYPE 
        SYNTAX        DisplayString (SIZE (0..20)) 
        MAX-ACCESS        read-write 
        STATUS        current 
        DESCRIPTION   "Password for the read-write CLI account." 
        ::= { rcCli 4 } 

rcCliRWL3UserName OBJECT-TYPE
        SYNTAX        DisplayString (SIZE (1..20))
        MAX-ACCESS        read-write
        STATUS        current
        DESCRIPTION   "User name for the read-write layer-3 CLI account."
        ::= { rcCli 5 }

rcCliRWL3Password OBJECT-TYPE
        SYNTAX        DisplayString (SIZE (0..20))
        MAX-ACCESS        read-write
        STATUS        current
        DESCRIPTION   "Password for the read-write layer-3 CLI account."
        ::= { rcCli 6 }

rcCliRWL2UserName OBJECT-TYPE
        SYNTAX        DisplayString (SIZE (1..20))
        MAX-ACCESS        read-write
        STATUS        current
        DESCRIPTION   "User name for the read-write layer-2 CLI account."   
        ::= { rcCli 7 }  
 
rcCliRWL2Password OBJECT-TYPE
        SYNTAX        DisplayString (SIZE (0..20))
        MAX-ACCESS        read-write
        STATUS        current
        DESCRIPTION   "Password for the read-write layer-2 CLI account."
        ::= { rcCli 8 }

rcCliROUserName OBJECT-TYPE
        SYNTAX        DisplayString (SIZE (1..20))
        MAX-ACCESS        read-write
        STATUS        current
        DESCRIPTION   "User name for the read-only CLI account."
        ::= { rcCli 9 }
 
rcCliROPassword OBJECT-TYPE 
        SYNTAX        DisplayString (SIZE (0..20))
        MAX-ACCESS        read-write 
        STATUS        current 
        DESCRIPTION   "Password for the read-only CLI account." 
        ::= { rcCli 10 } 

rcCliMaxTelnetSessions OBJECT-TYPE 
        SYNTAX        INTEGER (0..8)
        MAX-ACCESS        read-write
        STATUS        current
        DESCRIPTION   "Used to indicate the maximum number of telnet
		      sessions the system will support."
	DEFVAL	      { 8 }
	::= { rcCli 11 } 

rcCliMaxRloginSessions OBJECT-TYPE
        SYNTAX        INTEGER (0..8)
        MAX-ACCESS        read-write  
        STATUS        current
        DESCRIPTION   "Used to indicate the maximum number of rlogin
                      sessions the system will support."
	DEFVAL	      { 8 }
        ::= { rcCli 12 }

rcCliTimeout OBJECT-TYPE
        SYNTAX        INTEGER (30..65535)
        MAX-ACCESS        read-write
        STATUS        current
        DESCRIPTION   "Used to indicate the amount of idle time, in
     		      seconds to wait before timing out telnet and 
		      rlogin sessions."
	DEFVAL        { 900 }
        ::= { rcCli 13 }

rcCliNumAccessViolations OBJECT-TYPE
        SYNTAX        Integer32
        MAX-ACCESS        read-only
        STATUS        current
        DESCRIPTION   "Used to indicate the number of CLI access
		      violations detected by the system."
        ::= { rcCli 14 }

rcCliRWL1UserName OBJECT-TYPE
        SYNTAX        DisplayString (SIZE (1..20))
        MAX-ACCESS        read-write
        STATUS        current
        DESCRIPTION   "User name for the read-write layer-1 CLI account."
        ::= { rcCli 15 }
 
rcCliRWL1Password OBJECT-TYPE
        SYNTAX        DisplayString (SIZE (0..20))
        MAX-ACCESS        read-write
        STATUS        current
        DESCRIPTION   "Password for the read-write layer-1 CLI account."
        ::= { rcCli 16 }


-- Error Group
 
rcErrorLevel OBJECT-TYPE
        SYNTAX        Integer32
        MAX-ACCESS        read-only
        STATUS        current
        DESCRIPTION   "Error level indicator for the last error
                      reported in the system.  The meaning of
		      this value are :

			0 = Informative Information
			1 = Warning Condition
			2 = Error Condition
			3 = Manufacturing Information
			4 = Fatal Condition
		      "
        ::= { rcError 1 } 
 
rcErrorCode OBJECT-TYPE
        SYNTAX        Integer32
        MAX-ACCESS        read-only
        STATUS        current
        DESCRIPTION   "Error code indicator for the last error
                      reported in the system.  This is an encoded
		      value that identifies the software module
		      that generated the error message as well as
                      a specific error condition within that module.
		      This value is transparent to the user.  This
		      value is intended to help Accelar support and
		      development staff to isolate system problems."
        ::= { rcError 2 }

rcErrorText OBJECT-TYPE
        SYNTAX        DisplayString
        MAX-ACCESS        read-only
        STATUS        current
        DESCRIPTION   "Error string of the last error reported 
                      in the system."
        ::= { rcError 3 }

rcErrorReturnCode OBJECT-TYPE
        SYNTAX        INTEGER {
			 none(100),
			 resourceNotAvailable(101),
			 operationNotAllowed(102),
			 operationInProgress(103),
			 invalidPortNumber(104),
			 invalidSubnetAddress(105),
			 invalidSubnetMask(106),
			 invalidVlanId(107),
			 invalidVlanName(108),
			 invalidVlanType(109),
			 invalidStgId(110),
			 invalidProtocolId(111),
			 invalidPortMembers(112),
			 invalidStaticMembers(113),
			 invalidNotAllowedMembers(114),
			 destinationNotReachable(115),
			 tableIsFull(116),
			 nondualConnectorGigPort(117),
			 testIdNotPresent(118),
			 invalidTestId(119),
			 invalidStatusChange(120),
			 invalidCpuCard(121),
			 invalidSrcPortChoice(122),
			 dstPortUnspecified(123),
			 srcPortOneUnspecified(124),
			 srcPortTwoUnspecified(125),
			 notSupported(126),
			 userNameIsNonUnique(127),
			 invalidName(128),
                         cannotModifyThisField(130),
                         invalidUserPasswordLength(131),
                         thisUsernameExists(132),
                         invalidIpAddress(133),
                         invalidMacAddress(134),
                         nosuchEntry(135),
			 anotherLoopBackTestAlreadyRunning(136),
			 protocolIdNotRoutable(137),
			 autoNegotiateIsOn(138),
			 noActionSpecified(139),
			 invalidActionSpecified(140),
                         cannotModifyAutoNegotiateIsOn(141),
                         cannotModifyAutoPortIsFiber(142),
                         autoNegotiationNotSupported(143),
                         cannotSetAdminSpeed(144),
                         cannotSetAdminDuplex(145),
                         ospfRtrDeadIntIsnotMultOfHelloInt(146),
                         ospfRtrDeadIntLessThan4TimesHelloInt(147),
                         notUsed1(148),
                         ospfBadAuthValue(149),
                         ospfEnabled(150),
                         ospfAreaNotFound(151),
                         ospfBackboneArea(152),
                         notInTestMode(153),
                         ospfInvalidAreaRangeMask(154),
                         ospfDuplicateEntry(155),
                         ospfRangeNotAllocated(156),
                         ospfAreaRangeNotFound(157),
                         testRunning(158),
			 nvramLimitExceeded(159),
			 flowAlreadyExist(160),
			 flowNotFound(161),
		 	 duplicateIpAddress(163),
		 	 conflictingIpAddress(164),
			 invalidRouteCost(165),
			 invalidNextHop(166),
			 duplicateRoute(167),
			 cannotFindRoute(168),
			 cannotDeleteLocalRoute(169),
			 badDhcpMinSec(170),
			 badDhcpMaxHop(171),
			 badDhcpMode(172),
			 badAgentAddress(173),
			 dhcpNotEnabled(174),
			 dhcpForwardNotFound(175),
			 dhcpDuplicateForward(176),
			 dhcpMaxForward(177),
			 dhcpBadEnable(178),
			 invalidDeviceFileNumber(179),
			 notExecutableDeviceFile(180),
			 deletedDeviceFile(181),
			 pcmciaNotPresent(182),
			 pcmciaWriteProtected(183),
			 discontiguousSubnetMask(184),
			 invalidOspfMetric(185),
			 ospfHostRouteNotFound(186),
			 invalidMltId(187),
			 invalidMltName(188),
			 onlyOnePortInMlt(189),
			 moreThan4PortsInMlt(190),
			 portsInDifferentQuid(191),
			 portAlreadyInAnotherMlt(192),
			 invalidVlan(193),
			 nonExistIpMcastAddriess(194),
			 invalidIpMulticastAddress(195),
			 portIsLocked(196),
			 accessRestriction(197),
                         invalidDeviceFileLength(198),
                         duplicateAccessPolicyId(199),
                         noDesiredAccessPolicyItem(200),
                         ipfFilterNonExist(201),
                         ipfInvalidVlanPriority(202),
                         ipfInvalidDestinationAddress(203),
                         ipfInvalidSourceAddress(204),
                         ipfFilterDuplicate(205),
                         ipfGlobalListDuplicate(206),
                         ipfGlobalListNonExist(207),
                         ipfBaseListDuplicate(208),
                         ipfBaseListNonExist(209),
                         ipfPortDuplicate(210),
                         ipfPortNonExist(211),
                         ipfListNonExist(212),
                         snmpSnoopDisabled(213),
                         invalidHostIpAddress(214),
                         snoopStaticGroupExist(215),
			 ripAnnouncePolicyNotFound(216),
			 duplicateRipAnnouncePolicy(217),
			 ospfAnnouncePolicyNotFound(218),
			 duplicateOspfAnnouncePolicy(219),
			 policyMatchNetEntryNotFound(220),
			 duplicatePolicyNetEntry(221),
			 policyAddrListEntryNotFound(222),
			 duplicatePolicyAddrListEntry(223),
			 policyAddrListIdNotFound(224),
			 policyExactNetListNotFound(225),
			 policyRangeNetListNotFound(226),
			 policyRipGatewayListNotFound(227),
			 policyRipInterfaceListNotFound(228),
			 policyOspfRtrIdListNotFound(229),
			 policyAnnounceInterfaceListNotFound(230),
			 policyAdvertiseNetListNotFound(231),
			 policyInjectNetListNotFound(232),
			 invalidPolicyListIdListSize(233),
			 policyAddrEntryNotFound(234),
			 duplicatePolicyAddrEntry(235),
			 disableThisPortFirst(236),
			 mutinettingNotSupported(237),
			 addingGlobalFilterToNonGlobalList(238),
			 addingNonGlobalFilterToGlobalList(239),
			 setFilteredPortMode(240),
			 setFilteredPortEnableValue(241),
			 invalidModeType(242),
                         duplicateRipAcceptPolicy(243),
                         ripAccepPolicyNotFound(244),
                         duplicateOspfAcceptPolicy(245),
                         ospfAccepPolicyNotFound(246),
                         invalidAccessPolicyName(247),
                         invalidAccessPolicyPolicyEnable(248),
                         invalidAccessPolicyMode(249),
                         invalidAccessPolicyService(250),
                         invalidAccessPolicyPrecedence(251),
                         invalidAccessPolicyNetAddress(252),
                         invalidAccessPolicyTrustedHostAddress(253),
                         invalidAccessPolicyTrustedHostUserName(254),
                         invalidAccessPolicyAccessLevel(255),
                         invalidAccessPolicyLogSetting(256),
                         invalidAccessPolicyPolicyId(257),
			 invalidAreaOptions(258),
			 cannotDeleteAreaIfCountIsNotZero(259),
			 ospfInterfaceNotFound(260),
			 ospfIfAreaIdConflictsWithConfiguredAreaRange(261),
                         applyingDuplicateGlobalFilterToPort(262),
                         differentMltPortTypes(263),
                         addPortToMltFailed(264),
                         removePortFromMltFailed(265),
                         mirrorPortInMlt(266),
                         invalidDhcpAlwaysBroadcast(267),
                         interfaceIsSetToTransmitRipV1(268),
                         ripInterfaceDoesnotExist(269),
                         interfaceIsNotRunningRip(270),
                         cannotCreateVirtLinksThroughStubArea(271),
			 invalidSyslogEnableSetting(272),
			 invalidSyslogHostIpAddr(274),
			 invalidSyslogHostUdpPort(275),
			 invalidSyslogHostFacility(276),
 			 invalidSyslogModuleId(277),
			 invalidSyslogSeverity(278),
			 invalidSyslogMapInfoSeverity(279),
			 invalidSyslogMapWarningSeverity(280),
			 invalidSyslogMapErrorSeverity(281),
			 invalidSyslogMapMfgSeverity(282),
			 invalidSyslogMapFatalSeverity(283),
			 invalidSyslogMapTraceMsgSetting(284),
			 invalidSyslogMapTrapMsgSetting(285),
			 invalidSyslogLogTraceMsgSetting(286),
			 invalidSyslogLogTrapMsgSetting(287),
			 invalidSyslogEntryEnableSetting(288),
			 invalidSyslogMaxHostSetting(289),
			 invalidSyslogHostId(290),
			 duplicateSyslogEntry(291),
			 syslogHostTableIsFull(292),
			 invalidHoldDownTime(294),
  			 incompatibleAruHardware(295),
  			 invalidVrid(296),
  			 duplicateVrrpEntry(297),
  			 noVrrpIpAddressSpecified(298),
  			 invalidVrrpControlValue(299),
			 invalidVrrpPriority(300),
			 invalidVrrpAdvertisementInterval(301),
			 maxNumOfVrrpsEntriesExceeded(302),
			 policyNetListEntryNotFound(303),
			 duplicatePolicyNetListEntry(304),
			 policyNetListIdNotFound(305),
                         filterOnAnEnabledPort(306),
                         listOnAnEnabledPort(307),
                         invalidIpFilterSrcOption(308),
                         invalidIpFilterDstOption(309),
                         invalidOspfAreaImportextOption(310),
                         invalidOspfInterfaceMd5KeyIdLength(311),
                         invalidOspfInterfaceMd5KeyLength(312),
                         invalidIPXNetworkNumber(313),
                         ipxCircuitAlreadyExists(314),
                         ipxCircuitDoesNotExist(315),
                         encapsulationIsNotAllowedOnSameSegment(316),
                         encapsulationDoesNotMatchProtocolBasedVLAN(317),
                         invalidDvmrpIfTblEnableValue(318),
                         invalidDvmrpIfTblMetricValue(319),
                         ipHostPartForSubnetAddrIsNonZero(320),
                         globalMulticastNotEnabled(321),
                         metricFieldIsCreatedButModified(322),
                         invalidIpMRouteInterfaceTblTtlValue(323),
                         invalidUdpPortNumber(324),
                         invalidUdpProtocolNameLength(325),
                         cannotModifyUdpProtocolName(326),
                         udpProtocolEntryDoesnotexists(327),
                         duplicateUdpProtocolEntry(328),
                         cannotDelUdpProtocolEntryFwdEntriesExists(329),
                         udpBroadcastIntfEntryDoesnotExists(330),
                         duplicateUdpBroadcastIntfEntry(331),
                         invalidUdpConfBroacastInterface(332),
                         updConfIntfEntryNotEnabledForUdpBcastForwarding(333),
                         udpPortFwdEntryDoesnotExists(334),
                         duplicateUdpPortFwdEntryDoesnotExists(335),
                         udpPortFwdEntryUdpPortInterfaceDoesnotExists(336),
                         udpPortFwdListEntryDoesnotExists(337),
                         duplicateUdpPortFwdListEntryDoesnotExists(338),
                         udpPortFwdListEntryPortFwdIdDoesnotExists(339),
                         udpPortFwdListEntryinvalidFwdIdListSize(340),
                         cannotDeleteUdpPortFwdListEntryInterfaceUsingThisList(341),
                         invalidIgmpSnoopDestAddress(342),
                         invalidIgmpSnoopHostAddress(343),
                         cannotDeleteDefaultUdpProtocolTblEntry(344),
                         nextHopRouteIsStaticRoute(345),
                         invalidUpdateIntervalValueInDVMRPGlobalTable(346),
                         invalidTriggeredUpdateIntervalValueInDVMRPGlobalTable(347),
                         invalidLeafTimeoutValueInDVMRPGlobalTable(348),
                         invalidNbrTimeoutValueInDVMRPGlobalTable(349),
                         invalidNbrProbeIntervalValueInDVMRPGlobalTable(350),
                         invalidQueryIntervalValueInIgmpInterfaceTable(351),
                         invalidVersionValueInIgmpInterfaceTable(352),
                         invalidQueryMaxResponseTimeValueInIgmpInterfaceTable(353),
                         invalidRobustnessValueInIgmpInterfaceTable(354),
                         invalidLastMembQueryIntvlValueInIgmpInterfaceTable(355),
                         invalidANDMaskInRcIpTosRuleGroup(356),
                         invalidORRule1InRcIpTosRuleGroup(357),
                         invalidORRule2InRcIpTosRuleGroup(358),
                         invalidORRule3InRcIpTosRuleGroup(359),
                         deleteStaticPortNotValid(360),
                         maxEntriesForIgmpAccTbl(361),
                         maxMaskNumberOfHostIgmpAccTbl(362),
                         dvmrpIgmpExclusive(363),
                         theSpecifiedAreaRangeMaskIsInvalid(364),
                         invalidLengthOf2kBootConfigImageSource(365),
                         invalidLengthOf2kBootConfigSource(366),
                         preferenceOfStaticRouteIsInvalid(367),
                         copyFileOutOfSpace(368),
                         copyFileFileNotFound(369),
                         copyFileInvalidDestination(370),
                         copyFileInvalidSource(371),
                         copyFileFail(372),
			 invalidLinkFlapDetectAutoPortDown(373),
			 invalidLinkFlapDetectFrequency(374),
			 invalidLinkFlapDetectInterval(375),
			 invalidLinkFlapDetectSendTrap(376),
			 invalidQosLevel(377),
			 invalidQosWeight(378),
			 invalidQosThreshold(379),
			 invalidTagToQosTableIeee1pValue(380),
		  	 invalidTagToQosTableQosLevel(381),		
			 invalidDsFieldToQosTableDsField(382),
			 invalidDsFieldToQosTableQosLevel(383),
			 invalidQosToTagTableQosLevel(384),
			 invalidQosToTagTableIeee1pValue(385),
			 invalidQosLevelValue(386),	
		 	 invalidQosToDsFieldTableDsFieldValue(387),
			 invalidQosToDsFieldTableQosLevel(388),
			 invalidDiffServEnable(389),
			 invalidDiffServType(390),
			 invalidIeeeOverride(391),
			 invalidVlanQosValue(392),
			 invalidVlanTosValue(393),
			 operationNotAllowedOnAccessPort(394),
			 operationNotAllowedOnTaggingPort(395),
			 invalidFileName(396),
                         invalidDiaglogueDuplicateMirroredPort(397),
                         invalidDiaglogueEnableValue(398),
                         invalidDiaglogueEnableSetting(399),
                         invalidDiaglogueModeSetting(400),
                         invalidDiaglogueEntryId(401),
                         srcMacVlanIsNotYetEnabled(402),
                         srcMacVlanIsNotYetDisabled(403),
                         invalidDiaglogueOperation(404),
                         invalidMacAddressSpecied(405),
                         maxResponseTimeGreaterThanQueryInterval(406),
                         noModifyDsFltrAllowedOnDiffSrvCorePort(407),
                         mltMoreThan4PortsInMgMlt(408),
                         protocolRulesForThePortHasExceeded16(409)

-- the following part is the conflict definition in rel2.2
--
--                       rcSNMPStaticRouteNexthop(345),
--                       dvmrpGlobInvalidUpdateInterval(346),
--                       dvmrpGlobInvalidTriggerUpdateInterval(347),
--                       dvmrpGlobInvalidLeafTimeout(348),
--                       dvmrpGlobInvalidNbrTimeout(349),
--                       dvmrpGlobInvalidNbrProbeInterval(350),
--                       igmpIfInvalidQueryInterval(351),
--                       igmpIfInvalidVersion(352),
--                       igmpIfInvalidQueryMaxResponseTime(353),
--                       igmpIfInvalidRobustness(354),
--                       igmpIfInvalidLastMembQueryIntvl(355),
--                       ipTosRuleInvalidAndMask(356),
--                       ipTosRuleInvalidOrRule1(357),
--                       ipTosRuleInvalidOrRule2(358),
--                       ipTosRuleInvalidOrRule3(359),
--                       igmpDeleteStaticPortNotValid(360),
--                       igmpMaxEntriesAccTblExceeded(361),
--                       igmpMaxHostMaskExceeded(362),
--                       dvrmpOrIgmpAlreadyEnabled(363),
--                       rcSnmpOspfInvalidAreaAggregateLsaType(364),
--                       invalidDiagDuplicateMirroredPort(365),
--                       invalidDiagEnableValue(366),
--                       invalidDiagEnableSetting(367),
--                       invalidDiagModeSetting(368),
--                       invalidDiagEntryId(369),
--                       invalidPreferenceOfStaticRouting(370),
--                       ipTosRuleInvalidTosPriorityEnable(371),
--                       ipTosRuleInvalidTosThreshold(372)
--

		      }
        MAX-ACCESS        read-only
        STATUS        current
 	DESCRIPTION   "This variable is used primarily as an enumeration
		      to list the proprietary return codes that this
		      device can send to a management station in
		      response to a failed SNMP operation."
	DEFVAL	      { none }
        ::= { rcError 4 }

rcErrorSendTrap OBJECT-TYPE
        SYNTAX        TruthValue
        MAX-ACCESS        read-write
        STATUS        current
        DESCRIPTION   "Indicates whether to send trap upon receiving an
                      error in the system."
	DEFVAL	      { true }
        ::= { rcError 5 }


-- TRAPS

rcCardDown NOTIFICATION-TYPE
        OBJECTS      { rcCardIndex, rcCardAdminStatus, rcCardOperStatus }
        STATUS       current
        DESCRIPTION  "A rcCardDown trap signifies that the SNMPv2 entity,
                     acting in an agent role, has detected that the
                     rcCardOperStatus object for one of its cards 
                     is about to transition into the down state."
        ::= { rcTraps 1 }

rcCardUp NOTIFICATION-TYPE
        OBJECTS       { rcCardIndex, rcCardAdminStatus, rcCardOperStatus }
        STATUS        current
        DESCRIPTION   "A rcCardUp trap signifies that the SNMPv2 entity,
                      acting in an agent role, has detected that the
                      rcCardOperStatus object for one of its cards 
                      is about to transition into the up state."
        ::= { rcTraps 2 }

rcErrorNotification NOTIFICATION-TYPE
        OBJECTS       { rcErrorLevel, rcErrorCode, rcErrorText }
        STATUS        current
        DESCRIPTION   "A rcErrorNotification trap signifies that the 
                      SNMPv2 entity, acting in an agent role, has 
                      detected that an error condition has occured."
        ::= { rcTraps 3 }
 
rcStpNewRoot NOTIFICATION-TYPE
        OBJECTS       { rcStgId }
        STATUS        current
        DESCRIPTION   "A rcStpNewRoot trap signifies that the
                      SNMPv2 entity, acting in an agent role, has
                      detected the Spanning Tree Protocol has declared
                      the device to be the new root of the spanning 
       		      tree." 
        ::= { rcTraps 4 }

rcStpTopologyChange NOTIFICATION-TYPE
       OBJECTS        { rcStgId, rcPortIndex }
       STATUS         current   
       DESCRIPTION    "A rcStpTopologyChange trap signifies that the 
                      SNMPv2 entity, acting in an agent role, has 
                      detected the Spanning Tree Protocol has gone due
                      a topology change event."
       ::= { rcTraps 5 }

rcChasPowerSupplyDown NOTIFICATION-TYPE
        OBJECTS       { rcChasPowerSupplyId, rcChasPowerSupplyOperStatus}
        STATUS        current
        DESCRIPTION   "A rcChasPowerSupplyDown trap signifies that the 
                      SNMPv2 entity, acting in an agent role, has 
                      detected that the rcChasPowerSupplyOperStatus 
                      object for one of its power supply unit is 
                      about to transition into the down state."
        ::= { rcTraps 6 }

rcChasFanDown NOTIFICATION-TYPE
        OBJECTS       { rcChasFanId, rcChasFanOperStatus}
        STATUS        current
        DESCRIPTION   "A rcChasFanDown trap signifies that the 
                      SNMPv2 entity, acting in an agent role, has 
                      detected that the rcChasFanOperStatus object 
                      for one of its power supply unit is about to 
                      transition into the down state."
        ::= { rcTraps 7 }

rcLinkOscillation NOTIFICATION-TYPE
        OBJECTS          { rcPortIndex }
        STATUS             current
        DESCRIPTION   "A rcLinkOscillation trap signifies that the
                       SNMPv2 entity, acting in an agent role, has
                       detected an excessive number of link state
                       transitions on the specified port."
        ::= { rcTraps 8 }

rcMacViolation NOTIFICATION-TYPE
        OBJECTS       { rcErrorText, rcPortIndex }
        STATUS        obsolete
        DESCRIPTION   "A rcMacViolation trap signifies that the
                      SNMPv2 entity, acting in an agent role, has
                      received a PDU with an invalid source MAC
                      address."
        ::= { rcTraps 9 }

--rcSonetTrap NOTIFICATION-TYPE
--      OBJECTS       { rcPortIndex, rcPosSonetTrapType, rcPosSonetTrapIndication }
--      STATUS        obsolete
--      DESCRIPTION   "A rcSonetTrap trap signifies that the
--                    SNMPv2 entity, acting in an agent role, has
--                    detected a change of status on a Sonet port."
--      ::= { rcTraps 10 }

rc2kCardDown NOTIFICATION-TYPE
        OBJECTS      { rc2kCardIndex, 
                       rc2kCardFrontAdminStatus, 
                       rc2kCardFrontOperStatus }
        STATUS       current
        DESCRIPTION  "A rcCardDown trap signifies that the SNMPv2 entity,
                     acting in an agent role, has detected that the
                     rcCardOperStatus object for one of its cards
                     is about to transition into the down state."
        ::= { rcTraps 11 }

rc2kCardUp NOTIFICATION-TYPE
        OBJECTS       { rc2kCardIndex, 
                        rc2kCardFrontAdminStatus, 
                        rc2kCardFrontOperStatus }
        STATUS        current
        DESCRIPTION   "A rcCardUp trap signifies that the SNMPv2 entity,
                      acting in an agent role, has detected that the
                      rcCardOperStatus object for one of its cards
                      is about to transition into the up state."
        ::= { rcTraps 12 }

rc2kTemperature NOTIFICATION-TYPE
        OBJECTS       { rc2kChassisTemperature }
        STATUS        current
        DESCRIPTION   "A rc2kTemperature trap signifies that the SNMPv2 
		      entity, acting in an agent role, has detected the
                      chassis is over-heating."
        ::= { rcTraps 13 }

rcChasPowerSupplyUp NOTIFICATION-TYPE
        OBJECTS       { rcChasPowerSupplyId, rcChasPowerSupplyOperStatus}
        STATUS        current
        DESCRIPTION   "A rcChasPowerSupplyUp trap signifies that the
                      SNMPv2 entity, acting in an agent role, has
                      detected that the rcChasPowerSupplyOperStatus
                      object for one of its power supply unit is
                      about to transition into the up state."
        ::= { rcTraps 14 }

-- Syslog Group
 
rcSyslogGlobal      OBJECT IDENTIFIER ::= { rcSyslog 1 }

rcSyslogGlobalEnable OBJECT-TYPE
        SYNTAX        	TruthValue
        MAX-ACCESS        	read-write
        STATUS        	current
        DESCRIPTION   	"Used to enable/disable the SysLog feature.  When
			enabled this feature will send a message to a server 
			on a network that this configured to receive and
			store diagnostic messages from this device.  The
			type of messages sent is user configurable."
	DEFVAL	      	{ true }
        ::= { rcSyslogGlobal 1 }

rcSyslogGlobalMaxHosts OBJECT-TYPE
        SYNTAX        INTEGER (0..10)
        MAX-ACCESS        read-write
        STATUS        current
        DESCRIPTION   "Maximun number of remote hosts considered 'active'
                       and able to receive messages from the Syslog service
                       on the router."
        DEFVAL        { 5 }
        ::= { rcSyslogGlobal 2 }

rcSyslogGlobalOperState OBJECT-TYPE
        SYNTAX        INTEGER {
                         active(1),
                         inactive(2),
                         emptyHostTbl(3),
                         allHostDisabled(4)
                      }
        MAX-ACCESS        read-only
        STATUS        current
        DESCRIPTION   "The operational state of the syslog service
                       on the router."
        DEFVAL        { active }
        ::= { rcSyslogGlobal 3 }

rcSyslogHostTbl OBJECT-TYPE
        SYNTAX        SEQUENCE OF RcSyslogHostEntry
        MAX-ACCESS        not-accessible
        STATUS        current
        DESCRIPTION   "Table of remote host destinations for syslog."
        ::= { rcSyslog 2 }

rcSyslogHostEntry OBJECT-TYPE
        SYNTAX        RcSyslogHostEntry
        MAX-ACCESS        not-accessible
        STATUS        current
        DESCRIPTION   "Entry containing information for a particular
                       entry in rcSyslogHostTable."
        INDEX         { rcSyslogHostId }
        ::= { rcSyslogHostTbl 1 }

RcSyslogHostEntry ::= SEQUENCE {
                rcSyslogHostId                  INTEGER,
                rcSyslogHostIpAddr              IpAddress,
                rcSyslogHostUdpPort             INTEGER,
		rcSyslogHostFacility            INTEGER,	
		rcSyslogHostModuleId            INTEGER,
		rcSyslogHostModuleId2           INTEGER,
		rcSyslogHostSeverity            INTEGER,
		rcSyslogHostMapInfoSeverity     INTEGER,
		rcSyslogHostMapWarningSeverity  INTEGER,
		rcSyslogHostMapErrorSeverity    INTEGER,
		rcSyslogHostMapMfgSeverity      INTEGER,
		rcSyslogHostMapFatalSeverity    INTEGER,
		rcSyslogHostMapTraceMsg         INTEGER,
		rcSyslogHostMapTrapMsg          INTEGER,
		rcSyslogHostLogTraceMsgs        TruthValue,
		rcSyslogHostLogTrapMsgs         TruthValue,
		rcSyslogHostEnable              TruthValue,
                rcSyslogHostRowStatus           RowStatus
        }

rcSyslogHostId OBJECT-TYPE
        SYNTAX        INTEGER (1..10)
        MAX-ACCESS        read-only
        STATUS        current
        DESCRIPTION   "Host Id."
        ::= { rcSyslogHostEntry 1 }

rcSyslogHostIpAddr OBJECT-TYPE
        SYNTAX        IpAddress
        MAX-ACCESS        read-write
        STATUS        current
        DESCRIPTION   "Host Ip Address"
        ::= { rcSyslogHostEntry 2 }

rcSyslogHostUdpPort OBJECT-TYPE
        SYNTAX        INTEGER (514..530)
        MAX-ACCESS        read-write
        STATUS        current
        DESCRIPTION   "Specifies the UDP port to use to send syslog 
                      messages to the host." 
        DEFVAL        { 514 }
        ::= { rcSyslogHostEntry 3 }

rcSyslogHostFacility OBJECT-TYPE
        SYNTAX        INTEGER {
                         local0(128),
                         local1(136),
                         local2(144),
                         local3(152),
                         local4(160),
                         local5(168),
                         local6(176),
                         local7(184)
                      }
        MAX-ACCESS        read-write
        STATUS        current
        DESCRIPTION   "Specifies the UNIX facility used in messages
 		      to the syslog host.  Default is LOCAL7."
        DEFVAL        { local7 }
        ::= { rcSyslogHostEntry 4 }
 
rcSyslogHostModuleId OBJECT-TYPE
        SYNTAX        INTEGER {
                         common         (1),      -- '00000001'H
                         snmp           (2),      -- '00000002'H
                         rmon           (4),      -- '00000004'H
                         portmgr        (8),      -- '00000008'H
                         chasmgr       (16),      -- '00000010'H
                         bridge        (32),      -- '00000020'H
                         ospf          (64),      -- '00000040'H
                         hwif         (128),      -- '00000080'H
                         sim          (256),      -- '00000100'H
                         cpp          (512),      -- '00000200'H
                         netdrv      (1024),      -- '00000400'H
                         vlanmgr     (2048),      -- '00000800'H
                         cli         (4096),      -- '00001000'H
                         main        (8192),      -- '00002000'H
                         p2ip       (16384),      -- '00004000'H
                         rcip       (32768),      -- '00008000'H
                         rompager   (65536),      -- '00010000'H
                         acif      (131072),      -- '00020000'H
                         gbip      (262144),      -- '00040000'H
                         wdt       (524288),      -- '00080000'H
                         tdp      (1048576),      -- '00100000'H
                         mandiag  (2097152),      -- '00200000'H
                         mantest  (4194304),      -- '00400000'H
                         igmp     (8388608),      -- '00800000'H
                         ipfil   (16777216),      -- '01000000'H
                         mlt     (33554432),      -- '02000000'H
                         ippolicy(67108864),      -- '04000000'H
                         ipmc   (134217728),      -- '08000000'H
                         syslog (268435456)       -- '10000000'H
                      }
        MAX-ACCESS        read-write
        STATUS        current
        DESCRIPTION   "Specifies for which modules/tasks syslog messages
		       should be sent.  Default is all modules/tasks."
        ::= { rcSyslogHostEntry 5 }

rcSyslogHostModuleId2 OBJECT-TYPE
        SYNTAX        Integer32
        MAX-ACCESS        read-write
        STATUS        current
        DESCRIPTION   "Specifies for which modules/tasks syslog messages
                       should be sent.  Default is all modules/tasks."
        ::= { rcSyslogHostEntry 6 }

rcSyslogHostSeverity OBJECT-TYPE
        SYNTAX        INTEGER {
                         info(1),
                         warning(2),
                         error(4),
                         mfg(8),
                         fatal(16)
                      }
        MAX-ACCESS        read-write
        STATUS        current
        DESCRIPTION   "Specifies the severity level for which syslog messages
		       should be sent for the modules specifies in 
                       'SyslogHostModule'."
        DEFVAL        { info }
        ::= { rcSyslogHostEntry 7 }

rcSyslogHostMapInfoSeverity OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for Accelar
		       INFO messages.  Default is INFO."
        DEFVAL        { info }
        ::= { rcSyslogHostEntry 8 }

rcSyslogHostMapWarningSeverity OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for Accelar
                       WARNING messages.  Default is WARNING.  Should be
                       <= INFO."
        DEFVAL        { warning }
        ::= { rcSyslogHostEntry 9 }

rcSyslogHostMapErrorSeverity OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for Accelar
                       ERROR messages.  Default is ERROR.  Should be
		       <= WARNING."
        DEFVAL        { error }
        ::= { rcSyslogHostEntry 10 }

rcSyslogHostMapMfgSeverity OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for Accelar
                       Manufactoring messages.  Dafault is ERROR."
        DEFVAL        { error }
        ::= { rcSyslogHostEntry 11 }

rcSyslogHostMapFatalSeverity OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for Accelar
                       FATAL messages.  Default is EMERGENCY.  Should be
		       <= ERROR."
        DEFVAL        { emergency }
        ::= { rcSyslogHostEntry 12 }

rcSyslogHostMapTraceMsg OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the syslog severity to use for syslog
		       trace messages.  Default is DEBUG."
        ::= { rcSyslogHostEntry 13 }

rcSyslogHostMapTrapMsg OBJECT-TYPE
        SYNTAX        INTEGER {
                         emergency(1),
                         alert(2),
                         critical(3),
                         error(4),
                         warning(5),
                         notice(6),
                         info(7),
                         debug(8)
                      }
        MAX-ACCESS        read-write
        STATUS        current
        DESCRIPTION   "Specifies the UNIX severity code to use for syslog
		       messages for SNMP traps sent to the syslog host.
                       Default is INFO."
        ::= { rcSyslogHostEntry 14 }

rcSyslogHostLogTraceMsgs OBJECT-TYPE
        SYNTAX        TruthValue
        MAX-ACCESS        read-write
        STATUS        current
        DESCRIPTION   "Indicate whether to activate the host to log the 
                       syslog trace messages."
        ::= { rcSyslogHostEntry 15 }

rcSyslogHostLogTrapMsgs OBJECT-TYPE
        SYNTAX        TruthValue
        MAX-ACCESS        read-write
        STATUS        current
        DESCRIPTION   "Indicate whether to activate the host to log the
	               syslog messages for SNMP traps."
        ::= { rcSyslogHostEntry 16 }

rcSyslogHostEnable OBJECT-TYPE
        SYNTAX        TruthValue
        MAX-ACCESS        read-write
        STATUS        current
        DESCRIPTION   "Enable/Disable messages to be sent to syslog host."
        DEFVAL        { false }
        ::= { rcSyslogHostEntry 17 }

rcSyslogHostRowStatus OBJECT-TYPE
        SYNTAX        RowStatus
        MAX-ACCESS        read-write
        STATUS        current
        DESCRIPTION   "Used to create/delete entries in the rcSyslogTable."
        ::= { rcSyslogHostEntry 18 }


-- Diag Mirror by port Table

rcDiagMirrorByPortTable OBJECT-TYPE
        SYNTAX        	SEQUENCE OF RcDiagMirrorByPortEntry
        MAX-ACCESS        	not-accessible
        STATUS        	current
        DESCRIPTION   	"This table is used to configure the Mirror By
			Port feature.  This feature allows the device
			to forward a copy of each packet seen on a
			particular port to a different port."
        ::= { rcDiag 1 }

rcDiagMirrorByPortEntry OBJECT-TYPE
        SYNTAX        	RcDiagMirrorByPortEntry
        MAX-ACCESS        	not-accessible
        STATUS        	current
        DESCRIPTION   	"Entry containing mirror by port information."
        INDEX         	{ rcDiagMirrorByPortId }
        ::= { rcDiagMirrorByPortTable 1 }

RcDiagMirrorByPortEntry ::= SEQUENCE {
                rcDiagMirrorByPortId            INTEGER,
                rcDiagMirrorByPortMirroredPort  InterfaceIndex,
                rcDiagMirrorByPortMirroringPort InterfaceIndex,
                rcDiagMirrorByPortMode          INTEGER,
                rcDiagMirrorByPortEnable        TruthValue,
                rcDiagMirrorByPortRowStatus     RowStatus
        }

rcDiagMirrorByPortId OBJECT-TYPE
        SYNTAX        	INTEGER (1..10)
        MAX-ACCESS        	read-only
        STATUS        	current
        DESCRIPTION   	"Entry id."
        ::= { rcDiagMirrorByPortEntry 1 }

rcDiagMirrorByPortMirroredPort OBJECT-TYPE
        SYNTAX        	InterfaceIndex
        MAX-ACCESS        	read-write
        STATUS        	current
        DESCRIPTION   	"Used to configure the 'mirrored' port.  The port
			where packets are copied from."
        ::= { rcDiagMirrorByPortEntry 2 }

rcDiagMirrorByPortMirroringPort OBJECT-TYPE
        SYNTAX        	InterfaceIndex
        MAX-ACCESS        	read-write
        STATUS        	current
        DESCRIPTION   	"Used to configure the 'mirroring' port.  The port
			where packets are copied to."
        ::= { rcDiagMirrorByPortEntry 3 }

rcDiagMirrorByPortMode OBJECT-TYPE
        SYNTAX        	INTEGER {
                         	tx(1),
                         	rx(2),
                         	both(3)
                      	}
        MAX-ACCESS        	read-write
        STATUS        	current
        DESCRIPTION  	"Used to configure the 'mode' of the mirror operation.
			'tx' means packets being transmitted on the 'mirrored'
			port will be copied.  'rx' means packets received on
			the 'mirrored' port will be copied.  'both' means
			all traffic on the 'mirrored' port will be copied."
	DEFVAL	      	{ rx }
        ::= { rcDiagMirrorByPortEntry 4 }

rcDiagMirrorByPortEnable OBJECT-TYPE
        SYNTAX        	TruthValue
        MAX-ACCESS        	read-write
        STATUS        	current
        DESCRIPTION   	"Used to enable/disable this entry."
	DEFVAL	      	{ true }
        ::= { rcDiagMirrorByPortEntry 5 }

rcDiagMirrorByPortRowStatus OBJECT-TYPE
        SYNTAX        	RowStatus
        MAX-ACCESS        	read-write
        STATUS        	current
        DESCRIPTION   	"Row status of this entry."
        ::= { rcDiagMirrorByPortEntry 6 }


-- Diag Port Conv Steering Table

rcDiagPortConvSteeringTable OBJECT-TYPE
        SYNTAX        SEQUENCE OF RcDiagPortConvSteeringEntry
        MAX-ACCESS        not-accessible
        STATUS        current
        DESCRIPTION   "Diag Port Conv Steering Table"
        ::= { rcDiag 2 }

rcDiagPortConvSteeringEntry OBJECT-TYPE
        SYNTAX        RcDiagPortConvSteeringEntry
        MAX-ACCESS        not-accessible
        STATUS        current
        DESCRIPTION   "Entry containing infomation of Diag Port Conv Steering."
        INDEX         { rcDiagPortConvSteeringId }
        ::= { rcDiagPortConvSteeringTable 1 }

RcDiagPortConvSteeringEntry ::= SEQUENCE {
                rcDiagPortConvSteeringId           INTEGER,
                rcDiagPortConvSteeringPortOne      INTEGER,
                rcDiagPortConvSteeringPortTwo      INTEGER,
                rcDiagPortConvSteeringMode         INTEGER,
                rcDiagPortConvSteeringForwardPort  INTEGER,
                rcDiagPortConvSteeringEnable       TruthValue,
                rcDiagPortConvSteeringRowStatus    RowStatus
        }

rcDiagPortConvSteeringId OBJECT-TYPE
        SYNTAX        Integer32
        MAX-ACCESS        read-only
        STATUS        current
        DESCRIPTION   "Entry id."
        ::= { rcDiagPortConvSteeringEntry 1 }

rcDiagPortConvSteeringPortOne OBJECT-TYPE
        SYNTAX        Integer32
        MAX-ACCESS        read-write
        STATUS        current
        DESCRIPTION   "IfIndex for port one"
        ::= { rcDiagPortConvSteeringEntry 2 }

rcDiagPortConvSteeringPortTwo OBJECT-TYPE
        SYNTAX        Integer32
        MAX-ACCESS        read-write
        STATUS        current
        DESCRIPTION   "IfIndex for port two"
        ::= { rcDiagPortConvSteeringEntry 3 }

rcDiagPortConvSteeringMode OBJECT-TYPE
        SYNTAX        INTEGER {
                         oneToTwo(1),
                         twoToOne(2),
                         both(3)
                      }
        MAX-ACCESS        read-write
        STATUS        current
        DESCRIPTION   "Used to specify the traffic flow that should be
		      captured between ports one and two."
        ::= { rcDiagPortConvSteeringEntry 4 }

rcDiagPortConvSteeringForwardPort OBJECT-TYPE
        SYNTAX        Integer32
        MAX-ACCESS        read-write
        STATUS        current
        DESCRIPTION   "IfIndex of the port where captured traffic should
		      be forwarded to."
        ::= { rcDiagPortConvSteeringEntry 5 }

rcDiagPortConvSteeringEnable OBJECT-TYPE
        SYNTAX        TruthValue
        MAX-ACCESS        read-write
        STATUS        current
        DESCRIPTION   "Enable this entry."
	DEFVAL	      { true }
        ::= { rcDiagPortConvSteeringEntry 6 }

rcDiagPortConvSteeringRowStatus OBJECT-TYPE
        SYNTAX        RowStatus
        MAX-ACCESS        read-write
        STATUS        current
        DESCRIPTION   "Used to create/delete entries in the rcDiagMirrorByPortTable."
        ::= { rcDiagPortConvSteeringEntry 7 }


-- Diag Mac Conv Steering Table

rcDiagMacConvSteeringTable OBJECT-TYPE
        SYNTAX        SEQUENCE OF RcDiagMacConvSteeringEntry
        MAX-ACCESS        not-accessible
        STATUS        current
        DESCRIPTION   "Diag Mac Conv Steering Table"
        ::= { rcDiag 3 }

rcDiagMacConvSteeringEntry OBJECT-TYPE
        SYNTAX        RcDiagMacConvSteeringEntry
        MAX-ACCESS        not-accessible
        STATUS        current
        DESCRIPTION   "Entry containing infomation of Diag Mac Conv Steering."
        INDEX         { rcDiagMacConvSteeringId }
        ::= { rcDiagMacConvSteeringTable 1 }

RcDiagMacConvSteeringEntry ::= SEQUENCE {
                rcDiagMacConvSteeringId          INTEGER,
                rcDiagMacConvSteeringSrcMac      MacAddress,
                rcDiagMacConvSteeringDstMac      MacAddress,
                rcDiagMacConvSteeringInPort      INTEGER,
                rcDiagMacConvSteeringForwardPort INTEGER,
                rcDiagMacConvSteeringEnable      TruthValue,
                rcDiagMacConvSteeringRowStatus   RowStatus
        }

rcDiagMacConvSteeringId OBJECT-TYPE
        SYNTAX        Integer32
        MAX-ACCESS        read-only
        STATUS        current
        DESCRIPTION   "Entry id."
        ::= { rcDiagMacConvSteeringEntry 1 }

rcDiagMacConvSteeringSrcMac OBJECT-TYPE
        SYNTAX        MacAddress
        MAX-ACCESS        read-write
        STATUS        current
        DESCRIPTION   "Source MAC address"
        ::= { rcDiagMacConvSteeringEntry 2 }

rcDiagMacConvSteeringDstMac OBJECT-TYPE
        SYNTAX        MacAddress
        MAX-ACCESS        read-write
        STATUS        current
        DESCRIPTION   "Destination MAC address"
        ::= { rcDiagMacConvSteeringEntry 3 }

rcDiagMacConvSteeringInPort OBJECT-TYPE
        SYNTAX        Integer32
        MAX-ACCESS        read-write
        STATUS        current
        DESCRIPTION   "IfIndex of ingress port."
        ::= { rcDiagMacConvSteeringEntry 4 }

rcDiagMacConvSteeringForwardPort OBJECT-TYPE
        SYNTAX        Integer32
        MAX-ACCESS        read-write
        STATUS        current
        DESCRIPTION   "IfIndex of the port where captured traffic should
		      be forwarded to."
        ::= { rcDiagMacConvSteeringEntry 5 }

rcDiagMacConvSteeringEnable OBJECT-TYPE
        SYNTAX        TruthValue
        MAX-ACCESS        read-write
        STATUS        current
        DESCRIPTION   "Enable this entry."
	DEFVAL	      { true }
        ::= { rcDiagMacConvSteeringEntry 6 }

rcDiagMacConvSteeringRowStatus OBJECT-TYPE
        SYNTAX        RowStatus
        MAX-ACCESS        read-write
        STATUS        current
        DESCRIPTION   "Used to create/delete entries in the rcDiagMirrorByPortTable."
        ::= { rcDiagMacConvSteeringEntry 7 }

rcDiagSaveConfig OBJECT-TYPE
        SYNTAX        TruthValue
        MAX-ACCESS        read-write
        STATUS        current
        DESCRIPTION   "Used to configure whether the various mirror feature
                      settings should be saved and restored across system
                      reboot."
        ::= { rcDiag 10 }

rcDiagMirrorByPortTblSize OBJECT-TYPE
        SYNTAX        Integer32
        MAX-ACCESS        	read-only
        STATUS        	current
        DESCRIPTION   	"Used to indicate table size."
        ::= { rcDiag 11 }

rcDiagPortConvSteeringTblSize OBJECT-TYPE
        SYNTAX        Integer32
        MAX-ACCESS        	read-only
        STATUS        	current
        DESCRIPTION   	"Used to indicate table size."
        ::= { rcDiag 12 }

rcDiagMacConvSteeringTblSize OBJECT-TYPE
        SYNTAX        Integer32
        MAX-ACCESS        	read-only
        STATUS        	current
        DESCRIPTION   	"Used to indicate table size."
        ::= { rcDiag 13 }

rcDiagDiagnosticsEnable OBJECT-TYPE
        SYNTAX        TruthValue
        MAX-ACCESS        read-write
        STATUS        current
        DESCRIPTION   "Used to enable/disable the mirroring feature
                      for the entire device.  This setting overrides
                      any setting in the various mirroring tables."
        DEFVAL                { false }
        ::= { rcDiag 14 }

-- RCIPX
-- IPX 
-- IPX Routing Enable

rcIpxRoutingEnable OBJECT-TYPE
   	SYNTAX        TruthValue
  	MAX-ACCESS        read-write
  	STATUS        current
	DESCRIPTION   "Global Ipx Routing control variable"
	DEFVAL { false }
	::= { rcIpx 1 }

-- IPX Address Table

rcIpxAddrTable OBJECT-TYPE
        SYNTAX        SEQUENCE OF RcIpxAddrEntry
        MAX-ACCESS        not-accessible
        STATUS        current
        DESCRIPTION   "The table of addressing information relevant to
                      this entity's IPX addresses.  This table is used
                      for associating IfIndex and IPX network number."
	::= { rcIpx 2 }

rcIpxAddrEntry OBJECT-TYPE
	SYNTAX        RcIpxAddrEntry
	MAX-ACCESS 	      not-accessible
	STATUS 	      current
	DESCRIPTION   "The addressing information for one of this
                      entity's IP addresses."
	INDEX         { rcIpxAddrVlanId, rcIpxAddrNetAddr, rcIpxAddrEncap }
	::= { rcIpxAddrTable 1 }

RcIpxAddrEntry ::=
    	SEQUENCE {
           	rcIpxAddrVlanId      INTEGER,
	        rcIpxAddrNetAddr     OCTET STRING (SIZE(4)),
                rcIpxAddrEncap       INTEGER,
           	rcIpxAddrEntryStatus RowStatus
    	}

rcIpxAddrVlanId OBJECT-TYPE
   	SYNTAX        INTEGER (1..4094)
  	MAX-ACCESS        read-write
  	STATUS        current
	DESCRIPTION   "The index value which uniquely identifies the
                      interface to which this entry is applicable.  The
                      interface identified by a particular value of this
                      index is the same interface as identified by the
                      same value of ifIndex."
	::= { rcIpxAddrEntry 1 }

rcIpxAddrNetAddr       OBJECT-TYPE
        SYNTAX         OCTET STRING (SIZE(4))
        MAX-ACCESS         read-write
        STATUS         current
        DESCRIPTION    "IPX Network address."
        ::= { rcIpxAddrEntry 2 }

rcIpxAddrEncap OBJECT-TYPE
        SYNTAX        INTEGER {
                         none(0),
                         ethernetii(1),
                         snap(2),
                         llc(3),
                         raw(4)
                      }
        MAX-ACCESS        read-write
        STATUS        current
        DESCRIPTION   "Specify IPX encapsulation format.  It is relevent
                       if the VLAN is port based.  But it's always nice to have it."
        DEFVAL { none }
        ::= { rcIpxAddrEntry 3 }

rcIpxAddrEntryStatus OBJECT-TYPE
        SYNTAX        RowStatus
        MAX-ACCESS        read-write
        STATUS        current
        DESCRIPTION   "Used to create/delete entries in the rcIpxAddrEntry."
        ::= { rcIpxAddrEntry 4 }


-- RCIPX

-- ORNA Group

rcOrnaMgmtIpAddr OBJECT-TYPE
        SYNTAX        	IpAddress
        MAX-ACCESS        	read-write
        STATUS        	current
        DESCRIPTION   	"The IP address of the ORNA (High Performance Remote
			Monitor) module.  This is the IP address a network
			management station would use to contact the ORNA
			module."
        ::= { rcOrna 1 }

rcOrnaMgmtNetMask OBJECT-TYPE
        SYNTAX        	IpAddress
        MAX-ACCESS        	read-write
        STATUS        	current
        DESCRIPTION   	"The network mask of the ORNA module."
        ::= { rcOrna 2 }

rcOrnaMgmtGateway OBJECT-TYPE
        SYNTAX        	IpAddress
        MAX-ACCESS        	read-write
        STATUS        	current
        DESCRIPTION   	"The IP address of the gateway the ORNA module
			should use to route internetwork traffic."
        ::= { rcOrna 3 }

rcOrnaMgmtMacAddress OBJECT-TYPE
        SYNTAX        	DisplayString (SIZE(24))
        MAX-ACCESS        	read-only
        STATUS        	current
        DESCRIPTION   	"The MAC address of the ORNA module." 
        ::= { rcOrna 4 }

rcOrnaMonitorMacAddress OBJECT-TYPE
        SYNTAX        	DisplayString (SIZE(24))
        MAX-ACCESS        	read-only
        STATUS        	current
        DESCRIPTION   	"Not used currently"
        ::= { rcOrna 5 }

rcOrnaBootInfo OBJECT-TYPE
        SYNTAX        	DisplayString (SIZE(0..256))
        MAX-ACCESS        	read-only
        STATUS        	current
        DESCRIPTION   	"ORNA's boot information."
        ::= { rcOrna 6 }

rcOrnaInfo OBJECT-TYPE
        SYNTAX        	DisplayString (SIZE(0..256))
        MAX-ACCESS        	read-only
        STATUS        	current
        DESCRIPTION   	"Additional general information"
        ::= { rcOrna 7 }

rcOrnaModel OBJECT-TYPE
        SYNTAX        	DisplayString (SIZE(24))
        MAX-ACCESS        	read-only
        STATUS        	current
        DESCRIPTION   	"ORNA model information"
        ::= { rcOrna 8 }

rcOrnaSubModel OBJECT-TYPE
        SYNTAX        	DisplayString (SIZE(24))
        MAX-ACCESS        	read-only
        STATUS        	current
        DESCRIPTION   	"ORNA sub-model information"
        ::= { rcOrna 9 }

rcOrnaDescription OBJECT-TYPE
        SYNTAX        	DisplayString (SIZE(64))
        MAX-ACCESS        	read-only
        STATUS        	current
        DESCRIPTION   	"ORNA description information"
        ::= { rcOrna 10 }

rcOrnaPartNumber OBJECT-TYPE
        SYNTAX        	DisplayString (SIZE(24))
        MAX-ACCESS        	read-only
        STATUS        	current
        DESCRIPTION   	"ORNA part number"
        ::= { rcOrna 11 }

rcOrnaSerialNumber OBJECT-TYPE
        SYNTAX        	DisplayString (SIZE(24))
        MAX-ACCESS        	read-only
        STATUS        	current
        DESCRIPTION   	"ORNA serial number"
        ::= { rcOrna 12 }

rcOrnaMemorySize OBJECT-TYPE
        SYNTAX        	DisplayString (SIZE(8))
        MAX-ACCESS        	read-only
        STATUS        	current
        DESCRIPTION   	"HRPM memory size in kbytes"
        ::= { rcOrna 13 }

rcOrnaHwVersion OBJECT-TYPE
        SYNTAX        	DisplayString (SIZE(8))
        MAX-ACCESS        	read-only
        STATUS        	current
        DESCRIPTION   	"ORNA hardware version"
        ::= { rcOrna 14 }

rcOrnaRMmVersion OBJECT-TYPE
        SYNTAX        	DisplayString (SIZE(8))
        MAX-ACCESS        	read-only
        STATUS        	current
        DESCRIPTION   	"ORNA RMM ASIC version"
        ::= { rcOrna 15 }

rcOrnaSwVersion OBJECT-TYPE
        SYNTAX        	DisplayString (SIZE(8))
        MAX-ACCESS        	read-only
        STATUS        	current
        DESCRIPTION   	"ORNA software version." 
	::= { rcOrna 16 } 

rcOrnaBootPromVersion OBJECT-TYPE
        SYNTAX        	DisplayString (SIZE(8))
        MAX-ACCESS        	read-only
        STATUS        	current
        DESCRIPTION   	"ORNA Boot PROM version."
        ::= { rcOrna 17 }

rcOrnaOperatingSystem OBJECT-TYPE
        SYNTAX        	DisplayString (SIZE(24))
        MAX-ACCESS        	read-only
        STATUS        	current
        DESCRIPTION   	"ORNA operating system information."
        ::= { rcOrna 18 }

rcOrnaAction OBJECT-TYPE
        SYNTAX        	INTEGER {
                         	none(0),
                         	reset(1)
                      	}
        MAX-ACCESS        	read-write
        STATUS        	current
        DESCRIPTION   	"Action control variable."
        ::= { rcOrna 19 }

rcOrnaResult OBJECT-TYPE
        SYNTAX        	INTEGER {
                         	none(1),
                         	inProgress(2),
                         	success(3),
                         	fail(4)
                      	}
        MAX-ACCESS        	read-only
        STATUS        	current
        DESCRIPTION   	"Result of last action performed."
        ::= { rcOrna 20 }


-- POS PPP IPX Table

rcPosPppIpxTable OBJECT-TYPE
        SYNTAX        SEQUENCE OF RcPosPppIpxEntry
        MAX-ACCESS        not-accessible
        STATUS        current
        DESCRIPTION   ""
	::= { rcPos 1 }

rcPosPppIpxEntry OBJECT-TYPE
	SYNTAX        RcPosPppIpxEntry
	MAX-ACCESS 	      not-accessible
	STATUS 	      current
	DESCRIPTION   ""
	INDEX         { rcPosPppIpxIfIndex }
	::= { rcPosPppIpxTable 1 }

RcPosPppIpxEntry ::=
    	SEQUENCE {
           	rcPosPppIpxIfIndex         InterfaceIndex,
           	rcPosPppIpxAdminStatus     INTEGER,
           	rcPosPppIpxOperStatus      INTEGER,
	        rcPosPppIpxNetAddr         OCTET STRING (SIZE(4)),
                rcPosPppIpxRoutingProtocol INTEGER
    	}

rcPosPppIpxIfIndex OBJECT-TYPE
   	SYNTAX        InterfaceIndex
  	MAX-ACCESS        read-only
  	STATUS        current
	DESCRIPTION   "port number."
	::= { rcPosPppIpxEntry 1 }

rcPosPppIpxAdminStatus OBJECT-TYPE  
        SYNTAX        INTEGER {
                         up(1),
                         down(2),
                         unknown(3)
                      }
        MAX-ACCESS        read-write
        STATUS        current
        DESCRIPTION   ""
        DEFVAL { down }
        ::= { rcPosPppIpxEntry 2 }

rcPosPppIpxOperStatus OBJECT-TYPE  
        SYNTAX        INTEGER {
                         up(1),
                         down(2),
                         unknown(3)
                      }
        MAX-ACCESS        read-only
        STATUS        current
        DESCRIPTION   ""
        ::= { rcPosPppIpxEntry 3 }

rcPosPppIpxNetAddr OBJECT-TYPE
        SYNTAX         OCTET STRING (SIZE(4))
        MAX-ACCESS         read-write
        STATUS         current
        DESCRIPTION    "IPX Network address."
        ::= { rcPosPppIpxEntry 4 }

rcPosPppIpxRoutingProtocol OBJECT-TYPE  
        SYNTAX        INTEGER {
                         none(0),
                         rip(2)
                      }
        MAX-ACCESS        read-write
        STATUS        current
        DESCRIPTION   ""
        DEFVAL { none }
        ::= { rcPosPppIpxEntry 5 }

-- Link Flap Detect Group

rcLinkFlapDetectAutoPortDownEnable OBJECT-TYPE
        SYNTAX        	TruthValue
        MAX-ACCESS        	read-write
        STATUS        	current
        DESCRIPTION   	"Used to enable/disable the Link Flap Detect
			feature.  When enabled this feature will monitor
			the number of times a port goes down during a
			certain interval.  If the number exceeds a given
			bound the port will be forced out-of-service." 
        ::= { rcLinkFlapDetect 1 }

rcLinkFlapDetectSendTrap OBJECT-TYPE
        SYNTAX        	TruthValue
        MAX-ACCESS        	read-write
        STATUS        	current
        DESCRIPTION   	"Used to configure whether a trap should be
			sent if the port is forced out-of-service."	
        ::= { rcLinkFlapDetect 2 }

rcLinkFlapDetectFrequency OBJECT-TYPE
        SYNTAX        	INTEGER (1..9999)
        MAX-ACCESS        	read-write
        STATUS        	current
        DESCRIPTION   	"Used to configure the number of times the port
			can go down." 
        ::= { rcLinkFlapDetect 3 }

rcLinkFlapDetectInterval OBJECT-TYPE
        SYNTAX        	INTEGER (2..600)
        MAX-ACCESS        	read-write
        STATUS        	current
        DESCRIPTION   	"Used to configure the interval (in minutes)."
        ::= { rcLinkFlapDetect 4 }


-- Radius Group
-- Radius Global Infomation

rcRadiusGlobal   OBJECT IDENTIFIER       ::= { rcRadius 1 }

rcRadiusGlobalEnable OBJECT-TYPE
        SYNTAX        TruthValue
        MAX-ACCESS        read-write
        STATUS        current
        DESCRIPTION   "Enable/disable this feature."
	DEFVAL 	      { false }
        ::= { rcRadiusGlobal 1 }

rcRadiusGlobalMaxNumberServer OBJECT-TYPE
        SYNTAX        INTEGER (1..10)
        MAX-ACCESS        read-write
        STATUS        current
        DESCRIPTION   "Maximum number of RADIUS servers."
	DEFVAL 	      { 10 }
        ::= { rcRadiusGlobal 2 }

rcRadiusGlobalServerTableSize OBJECT-TYPE
        SYNTAX        Integer32
        MAX-ACCESS          read-only
        STATUS          current
        DESCRIPTION     "Used to indicate the number of entries in the
                        rcRadiusServerTable."
        ::= { rcRadiusGlobal 3 }

-- Radius Server Table Infomation

rcRadiusServerTable OBJECT-TYPE
        SYNTAX        SEQUENCE OF RcRadiusServerEntry
        MAX-ACCESS        not-accessible
        STATUS        current
        DESCRIPTION   "The RADIUS table (0 to 10 entries).  This
                      table lists the information of the RADIUS server."
        ::= { rcRadius 2 }

rcRadiusServerEntry OBJECT-TYPE
        SYNTAX        RcRadiusServerEntry
        MAX-ACCESS        not-accessible
        STATUS        current
        DESCRIPTION   "A RADIUS server table entry."
        INDEX         { rcRadiusServerPriority, rcRadiusServerAddress}
        ::= { rcRadiusServerTable 1 }

RcRadiusServerEntry ::=
        SEQUENCE {
                rcRadiusServerPriority INTEGER,
                rcRadiusServerAddress IpAddress,
                rcRadiusServerTimeOut INTEGER,
                rcRadiusServerEnable TruthValue,
                rcRadiusServerMaxRetries INTEGER,
                rcRadiusServerUdpPort INTEGER,
                rcRadiusServerSecretKey DisplayString,
                rcRadiusServerAccessRequests Counter32,
                rcRadiusServerAccessAccepts Counter32,
                rcRadiusServerAccessRejects Counter32,
                rcRadiusServerBadResponses Counter32,
                rcRadiusServerPendingRequests Counter32,
                rcRadiusServerClientRetries Counter32,
                rcRadiusServerRowStatus RowStatus
        }

rcRadiusServerPriority OBJECT-TYPE
        SYNTAX        INTEGER (1..10)
        MAX-ACCESS        read-write
        STATUS        current
        DESCRIPTION   "Server priority, used to control which server to choose
                       first to send authentication."
	DEFVAL 	      { 10 }
        ::= { rcRadiusServerEntry 1 }

rcRadiusServerAddress OBJECT-TYPE
        SYNTAX        IpAddress
        MAX-ACCESS        read-write
        STATUS        current
        DESCRIPTION   "Server IP address of the RADIUS authentication server
                       referred to in this table entry."
        ::= { rcRadiusServerEntry 2 }

rcRadiusServerTimeOut OBJECT-TYPE
        SYNTAX        INTEGER (1..10)
        MAX-ACCESS        read-write
        STATUS        current
        DESCRIPTION   "The time interval in seconds before the client 
                       retransmit the packet."
	DEFVAL 	      { 3 }
        ::= { rcRadiusServerEntry 3 }

rcRadiusServerEnable  OBJECT-TYPE
        SYNTAX        TruthValue 
        MAX-ACCESS        read-write
        STATUS        current
        DESCRIPTION   "Enable or disable this server."
	DEFVAL 	      { true }
        ::= { rcRadiusServerEntry 4 }

rcRadiusServerMaxRetries OBJECT-TYPE
        SYNTAX        INTEGER (1..6)
        MAX-ACCESS        read-write
        STATUS        current
        DESCRIPTION   "Maximum number of retransmissions."
	DEFVAL 	      { 3 }
        ::= { rcRadiusServerEntry 5 }

rcRadiusServerUdpPort OBJECT-TYPE
        SYNTAX        INTEGER (1..65536)
        MAX-ACCESS        read-write
        STATUS        current
        DESCRIPTION   "The UDP port the client is using to send requests
                       to this server."
	DEFVAL 	      { 1812 }
        ::= { rcRadiusServerEntry 6 }

rcRadiusServerSecretKey OBJECT-TYPE
        SYNTAX        DisplayString (SIZE (0..20)) 
        MAX-ACCESS        read-write
        STATUS        current
        DESCRIPTION   "The identifier of the RADIUS authentication client."
        ::= { rcRadiusServerEntry 7 }

rcRadiusServerAccessRequests OBJECT-TYPE
        SYNTAX          Counter32
        MAX-ACCESS          read-only
        STATUS          current
        DESCRIPTION     "The number of RADIUS access-response packets sent to 
                         this server. This does not include retransmissions."
        ::= { rcRadiusServerEntry 8 }

rcRadiusServerAccessAccepts OBJECT-TYPE
        SYNTAX          Counter32
        MAX-ACCESS          read-only
        STATUS          current
        DESCRIPTION     "The number of RADIUS access-accept packets (valid or 
                         invalid) received from this server."
        ::= { rcRadiusServerEntry 9 }

rcRadiusServerAccessRejects OBJECT-TYPE
        SYNTAX          Counter32
        MAX-ACCESS          read-only
        STATUS          current
        DESCRIPTION     "The number of RADIUS access-reject packets (valid or 
                         invalid) received from this server."
        ::= { rcRadiusServerEntry 10 }

rcRadiusServerBadResponses OBJECT-TYPE
        SYNTAX          Counter32
        MAX-ACCESS          read-only
        STATUS          current
        DESCRIPTION     "The number of RADIUS invalid access-response packets 
                         received from this server."
        ::= { rcRadiusServerEntry 11 }

rcRadiusServerPendingRequests OBJECT-TYPE
        SYNTAX          Counter32
        MAX-ACCESS          read-only
        STATUS          current
        DESCRIPTION     "The number of RADIUS access-request packets destined 
                         for this server that have not yet timed out or 
                         received a response. This variable is incremented 
                         when an access-request is sent and decremented due 
                         to receipt of an access-accept, access-reject, a 
                         timeout or retransmission."
        ::= { rcRadiusServerEntry 12 }

rcRadiusServerClientRetries OBJECT-TYPE
        SYNTAX          Counter32
        MAX-ACCESS          read-only
        STATUS          current
        DESCRIPTION     "The number of authentication retransmission to 
                         this server."
        ::= { rcRadiusServerEntry 13 }

rcRadiusServerRowStatus OBJECT-TYPE
        SYNTAX        RowStatus
        MAX-ACCESS        read-write
        STATUS        current
        DESCRIPTION   "Used to create/delete entries."
        ::= { rcRadiusServerEntry 14 }


-- rc2k Group

rc2kChassis     OBJECT IDENTIFIER ::= { rc2k 1 }

rc2kChassisPortOperStatus  OBJECT-TYPE
        SYNTAX          OCTET STRING (SIZE(256))
        MAX-ACCESS          read-only
        STATUS          current
        DESCRIPTION     "A bit array that contains the oper-status
                        of the ports in the device.  2 bits are used
                        for each port.  The high order 2 bits of the
                        first octet represent port #0, the next two
                        bits are used for port #1, etc.  The status
                        is encoded with the following scheme :

                        value   meaning
                        -----   -------
                          0     no-link (admin=up, oper=down)
                          1     up	(admin=up, oper=up)
                          2     down	(admin=down, oper=down)
                          3     testing	(admin=test, oper=test)
                        "
        ::= { rc2kChassis 1 }

rc2kChassisTemperature OBJECT-TYPE
        SYNTAX          Gauge32
        MAX-ACCESS          read-only
        STATUS          current
        DESCRIPTION     "Used to indicate the core operating temperature
                        of the chassis.  This value represents the degree
			in celsius of the air inside the chassis."
        ::= { rc2kChassis 2 }

rc2kChassisAmbientLowerTemperature OBJECT-TYPE
        SYNTAX          Gauge32
        MAX-ACCESS          read-only
        STATUS          obsolete
        DESCRIPTION     "Used to indicate the temperature of the air
                        entering the fan at the lower half of the chassis."
        ::= { rc2kChassis 3 }

rc2kChassisAmbientUpperTemperature OBJECT-TYPE 
        SYNTAX          Gauge32 
        MAX-ACCESS          read-only 
        STATUS          obsolete 
        DESCRIPTION     "Used to indicate the temperature of the air
                        entering the fan at the upper half of the chassis." 
        ::= { rc2kChassis 4 }

rc2kChassisBaseMacAddr OBJECT-TYPE 
        SYNTAX          MacAddress 
        MAX-ACCESS          read-only 
        STATUS          current 
        DESCRIPTION     "base mac addr"
        ::= { rc2kChassis 5 }

-- 2k CPU Ethernet Port table

rc2kCpuEthernetPortTable OBJECT-TYPE
        SYNTAX        SEQUENCE OF Rc2kCpuEthernetPortEntry
        MAX-ACCESS        not-accessible
        STATUS        current
        DESCRIPTION   "2k CPU Ethernet Port table"
        ::= { rc2k 2 }

rc2kCpuEthernetPortEntry OBJECT-TYPE
        SYNTAX        Rc2kCpuEthernetPortEntry
        MAX-ACCESS        not-accessible
        STATUS        current
        DESCRIPTION   "Entry containing infomation of 2k CPU Ethernet Port"
        INDEX         { rc2kCpuEthernetPortIfIndex }
        ::= { rc2kCpuEthernetPortTable 1 }

Rc2kCpuEthernetPortEntry ::= SEQUENCE {
                rc2kCpuEthernetPortIfIndex       InterfaceIndex,
		rc2kCpuEthernetPortDescr	 DisplayString,
                rc2kCpuEthernetPortAdminStatus   INTEGER,
                rc2kCpuEthernetPortOperStatus    INTEGER,
                rc2kCpuEthernetPortAddr          IpAddress,
                rc2kCpuEthernetPortMask          IpAddress,
                rc2kCpuEthernetPortGateway       IpAddress,
                rc2kCpuEthernetPortNetwork       IpAddress,
                rc2kCpuEthernetPortAutoNegotiate TruthValue,
                rc2kCpuEthernetPortAdminDuplex   INTEGER,
                rc2kCpuEthernetPortOperDuplex    INTEGER,
                rc2kCpuEthernetPortAdminSpeed    INTEGER,
                rc2kCpuEthernetPortOperSpeed     INTEGER,
                rc2kCpuEthernetPortEnableBootp   TruthValue,
                rc2kCpuEthernetPortMgmtMacAddr   MacAddress
        }

rc2kCpuEthernetPortIfIndex OBJECT-TYPE
        SYNTAX        InterfaceIndex
        MAX-ACCESS        read-only
        STATUS        current
        DESCRIPTION   "IfIndex of the port."
        ::= { rc2kCpuEthernetPortEntry 1 }

rc2kCpuEthernetPortDescr OBJECT-TYPE 
        SYNTAX        DisplayString (SIZE (0..128)) 
        MAX-ACCESS        read-only 
        STATUS        current 
        DESCRIPTION   "Port description" 
        ::= { rc2kCpuEthernetPortEntry 2 } 

rc2kCpuEthernetPortAdminStatus OBJECT-TYPE
        SYNTAX        	INTEGER {
                            up(1),
                            down(2),
                            unknown(3)
                      	}
        MAX-ACCESS        	read-write
        STATUS        	current
        DESCRIPTION  	"Used to configure the admininstrative status
			of the port."
        ::= { rc2kCpuEthernetPortEntry 3 }

rc2kCpuEthernetPortOperStatus OBJECT-TYPE
        SYNTAX        	INTEGER {
                            up(1),
                            down(2),
                            unknown(3)
                      	}
        MAX-ACCESS        	read-only
        STATUS        	current
        DESCRIPTION   	"Used to indicate the administrative status
			of the port."
        ::= { rc2kCpuEthernetPortEntry 4 }

rc2kCpuEthernetPortAddr OBJECT-TYPE
        SYNTAX        	IpAddress
        MAX-ACCESS        	read-write
        STATUS        	current
        DESCRIPTION   	"Used to configure the port's IP address"
        ::= { rc2kCpuEthernetPortEntry 5 }

rc2kCpuEthernetPortMask OBJECT-TYPE
        SYNTAX        	IpAddress
        MAX-ACCESS        	read-write
        STATUS        	current
        DESCRIPTION   	"Used to configure the port's net mask"
        ::= { rc2kCpuEthernetPortEntry 6 }

rc2kCpuEthernetPortGateway OBJECT-TYPE
        SYNTAX        	IpAddress
        MAX-ACCESS        	read-write
        STATUS        	current
        DESCRIPTION   	"Used to configure the the IP address of the
			gateway that should be used to forward IP
			traffic."  
        ::= { rc2kCpuEthernetPortEntry 7 }

rc2kCpuEthernetPortNetwork OBJECT-TYPE
        SYNTAX        	IpAddress
        MAX-ACCESS        	read-write
        STATUS        	current
        DESCRIPTION   	"Used to configure the network that can be
			used to remotely manage this device."
        ::= { rc2kCpuEthernetPortEntry 8 }

rc2kCpuEthernetPortAutoNegotiate OBJECT-TYPE
        SYNTAX        	TruthValue
        MAX-ACCESS        	read-write
        STATUS        	current
        DESCRIPTION   	"Used to configure auto-negotiation on this
			port."
	DEFVAL	      	{ true }
        ::= { rc2kCpuEthernetPortEntry 9 }

rc2kCpuEthernetPortAdminDuplex OBJECT-TYPE
        SYNTAX        	INTEGER {
                            half(1),
                            full(2)
                      	}
        MAX-ACCESS        	read-write
        STATUS        	current
        DESCRIPTION   	"Used to configure the administrative duplex
			setting for this port."
        ::= { rc2kCpuEthernetPortEntry 10 }

rc2kCpuEthernetPortOperDuplex OBJECT-TYPE
        SYNTAX        	INTEGER {
                            half(1),
                            full(2)
                      	}
        MAX-ACCESS        	read-only
        STATUS        	current
        DESCRIPTION   	"Used to indicate the operational duplex
			setting for this port."
        ::= { rc2kCpuEthernetPortEntry 11 }

rc2kCpuEthernetPortAdminSpeed OBJECT-TYPE
        SYNTAX        	INTEGER {
                            none(0),
                            mbps10(1),      -- 10Mb/s
                            mbps100(2)      -- 100Mb/s
                      	}
        MAX-ACCESS        	read-write
        STATUS        	current
        DESCRIPTION   	"Used to configure the administrative speed
			setting for this port."
        ::= { rc2kCpuEthernetPortEntry 12 }

rc2kCpuEthernetPortOperSpeed OBJECT-TYPE
        SYNTAX        	INTEGER {
                            none(0),
                            mbps10(1),      -- 10Mb/s
                            mbps100(2)      -- 100Mb/s
                      	}
        MAX-ACCESS        	read-only
        STATUS        	current
        DESCRIPTION   	"Used to indicate the operational duplex
			setting for this port."
        ::= { rc2kCpuEthernetPortEntry 13 }

rc2kCpuEthernetPortEnableBootp OBJECT-TYPE
        SYNTAX        	TruthValue
        MAX-ACCESS        	read-write
        STATUS        	current
        DESCRIPTION   	"Used to enable/disable the Bootp feature
			on this port."
	DEFVAL	      	{ false }
        ::= { rc2kCpuEthernetPortEntry 14 }

rc2kCpuEthernetPortMgmtMacAddr OBJECT-TYPE
        SYNTAX          MacAddress 
        MAX-ACCESS          read-only 
        STATUS          current 
        DESCRIPTION     "Used to indicate the mac addr for this port."
        ::= { rc2kCpuEthernetPortEntry 15 }


-- 2k CPU Serial Port table

rc2kCpuSerialPortTable OBJECT-TYPE
        SYNTAX        SEQUENCE OF Rc2kCpuSerialPortEntry
        MAX-ACCESS        not-accessible
        STATUS        current
        DESCRIPTION   "2k CPU Serial Port table"
        ::= { rc2k 3 }

rc2kCpuSerialPortEntry OBJECT-TYPE
        SYNTAX        Rc2kCpuSerialPortEntry
        MAX-ACCESS        not-accessible
        STATUS        current
        DESCRIPTION   "Entry containing infomation of 2k CPU Serial Port"
        INDEX         { rc2kCpuSerialPortIfIndex }
        ::= { rc2kCpuSerialPortTable 1 }

Rc2kCpuSerialPortEntry ::= SEQUENCE {
                rc2kCpuSerialPortIfIndex          InterfaceIndex,
		rc2kCpuSerialPortDescr		  DisplayString,
                rc2kCpuSerialPortMode             INTEGER,
                rc2kCpuSerialPortAdminStatus      INTEGER,
                rc2kCpuSerialPortOperStatus       INTEGER,
                rc2kCpuSerialPortBaudRate         INTEGER,
                rc2kCpuSerialPortDataBits         INTEGER,
                rc2kCpuSerialPortMyAddr           IpAddress,
                rc2kCpuSerialPortPeerAddr         IpAddress,
                rc2kCpuSerialPortSlipMtu          INTEGER,
                rc2kCpuSerialPortSlipTxRxCompress TruthValue,
                rc2kCpuSerialPortSlipRxCompress   TruthValue,
                rc2kCpuSerialPortPppConfigFile    DisplayString
        }

rc2kCpuSerialPortIfIndex OBJECT-TYPE
        SYNTAX        	InterfaceIndex
        MAX-ACCESS        	read-only
        STATUS        	current
        DESCRIPTION   	"IfIndex for this port."
        ::= { rc2kCpuSerialPortEntry 1 }

rc2kCpuSerialPortDescr OBJECT-TYPE
        SYNTAX        	DisplayString (SIZE (0..128))
        MAX-ACCESS        	read-only
        STATUS        	current
        DESCRIPTION   	"Port description."
        ::= { rc2kCpuSerialPortEntry 2 }

rc2kCpuSerialPortMode OBJECT-TYPE
        SYNTAX        	INTEGER {
                            cli(1),
                            slip(2),
                            ppp(3)
                     	 }
        MAX-ACCESS        	read-write
        STATUS       	 current
        DESCRIPTION   	"Used to configure the mode this port should
			operate in."
        ::= { rc2kCpuSerialPortEntry 3 }

rc2kCpuSerialPortAdminStatus OBJECT-TYPE
        SYNTAX        	INTEGER {
                            up(1),
                            down(2),
                            unknown(3)
                      	}
        MAX-ACCESS        	read-write
        STATUS        	current
        DESCRIPTION     "Used to configure the administrative status
                        setting for this port."
        ::= { rc2kCpuSerialPortEntry 4 }

rc2kCpuSerialPortOperStatus OBJECT-TYPE
        SYNTAX        	INTEGER {
                            up(1),
                            down(2),
                            unknown(3)
                      	}
        MAX-ACCESS        	read-only
        STATUS        	current
        DESCRIPTION     "Used to indicate the operational status
                        setting for this port."
        ::= { rc2kCpuSerialPortEntry 5 }

rc2kCpuSerialPortBaudRate OBJECT-TYPE
        SYNTAX        	INTEGER {
                            baud2400(2400),
                            baud4800(4800),
                            baud9600(9600),
                            baud19200(19200),
                            baud38400(38400),
                            baud57600(57600),
                            baud115200(115200)
                      	}
        MAX-ACCESS        	read-write
        STATUS        	current
        DESCRIPTION   	"Used to configure the baud rate of this port."
        ::= { rc2kCpuSerialPortEntry 6 }

rc2kCpuSerialPortDataBits OBJECT-TYPE
        SYNTAX        	INTEGER {
                            seven(1),
                            eight(2)
                      	}
        MAX-ACCESS        	read-write
        STATUS        	current
        DESCRIPTION   	"Used to configure the number of data bits, per
			byte of data, this port should send/receive."
        ::= { rc2kCpuSerialPortEntry 7 }

rc2kCpuSerialPortMyAddr OBJECT-TYPE
        SYNTAX        	IpAddress
        MAX-ACCESS        	read-write
        STATUS        	current
        DESCRIPTION   	"Used to configure this port's IP address.
			Used for both 'slip' and 'ppp' modes."
        ::= { rc2kCpuSerialPortEntry 8 }

rc2kCpuSerialPortPeerAddr OBJECT-TYPE
        SYNTAX        	IpAddress
        MAX-ACCESS        	read-write
        STATUS        	current
        DESCRIPTION   	"Used to configure the peer's IP address.
			Used for both 'slip' and 'ppp' modes."
        ::= { rc2kCpuSerialPortEntry 9 }

rc2kCpuSerialPortSlipMtu OBJECT-TYPE
        SYNTAX        	INTEGER (0..224)
        MAX-ACCESS        	read-write
        STATUS        	current
        DESCRIPTION   	"Used to configure the MTU for this port.
			Used for slip only."
        ::= { rc2kCpuSerialPortEntry 10 }

rc2kCpuSerialPortSlipTxRxCompress OBJECT-TYPE
        SYNTAX        	TruthValue
        MAX-ACCESS        	read-write
        STATUS        	current
        DESCRIPTION   	"Used to enable/disable compression of TCP/IP
			packet headers on this port.  Used for slip only."
	DEFVAL	      	{ true }
        ::= { rc2kCpuSerialPortEntry 11 }

rc2kCpuSerialPortSlipRxCompress OBJECT-TYPE
        SYNTAX        	TruthValue
        MAX-ACCESS        	read-write
        STATUS        	current
        DESCRIPTION   	"Used to enable/disable compression for receiving
			packets on this port.  Used for slip only."	
	DEFVAL	      	{ true }
        ::= { rc2kCpuSerialPortEntry 12 }

rc2kCpuSerialPortPppConfigFile OBJECT-TYPE
        SYNTAX        	DisplayString (SIZE(256))
        MAX-ACCESS        	read-write
        STATUS        	current
        DESCRIPTION   	"Used to configure the configuration file to use
			for PPP."
        ::= { rc2kCpuSerialPortEntry 13 }


-- 2k Device Group

rc2kDevice     OBJECT IDENTIFIER ::= { rc2k 4 }

rc2kDeviceGlobalTable OBJECT-TYPE
        SYNTAX        SEQUENCE OF Rc2kDeviceGlobalEntry
        MAX-ACCESS        not-accessible
        STATUS        current
        DESCRIPTION   "2k CPU Ethernet Port table"
        ::= { rc2kDevice 1 }

rc2kDeviceGlobalEntry OBJECT-TYPE
        SYNTAX        Rc2kDeviceGlobalEntry
        MAX-ACCESS        not-accessible
        STATUS        current
        DESCRIPTION   "Entry containing infomation of 2k CPU Ethernet Port"
        INDEX         { rc2kDeviceGlobalSlot }
        ::= { rc2kDeviceGlobalTable 1 }

Rc2kDeviceGlobalEntry ::= SEQUENCE {
		rc2kDeviceGlobalSlot		INTEGER,
		rc2kDeviceGlobalFlashBytesUsed 	INTEGER,
		rc2kDeviceGlobalFlashBytesFree 	INTEGER,
		rc2kDeviceGlobalFlashNumFiles 	INTEGER,
		rc2kDeviceGlobalPcmciaBytesUsed	INTEGER,
		rc2kDeviceGlobalPcmciaBytesFree	INTEGER,
		rc2kDeviceGlobalPcmciaNumFiles 	INTEGER,
		rc2kDeviceGlobalAction 		INTEGER,
		rc2kDeviceGlobalResult 		INTEGER
	}

rc2kDeviceGlobalSlot OBJECT-TYPE
        SYNTAX        INTEGER (5..6)
        MAX-ACCESS        read-only
        STATUS        current
        DESCRIPTION   "slot number"
        ::= { rc2kDeviceGlobalEntry 1 }

rc2kDeviceGlobalFlashBytesUsed OBJECT-TYPE
        SYNTAX        Integer32
        MAX-ACCESS        read-only
        STATUS        current
        DESCRIPTION   "bytes used"
        ::= { rc2kDeviceGlobalEntry 2 }

rc2kDeviceGlobalFlashBytesFree OBJECT-TYPE
        SYNTAX        Integer32
        MAX-ACCESS        read-only
        STATUS        current
        DESCRIPTION   "bytes free"
        ::= { rc2kDeviceGlobalEntry 3 }

rc2kDeviceGlobalFlashNumFiles OBJECT-TYPE
        SYNTAX        Integer32
        MAX-ACCESS        read-only
        STATUS        current
        DESCRIPTION   "# files in flash"
        ::= { rc2kDeviceGlobalEntry 4 }

rc2kDeviceGlobalPcmciaBytesUsed OBJECT-TYPE
        SYNTAX        Integer32
        MAX-ACCESS        read-only
        STATUS        current
        DESCRIPTION   "bytes used"
        ::= { rc2kDeviceGlobalEntry 5 }

rc2kDeviceGlobalPcmciaBytesFree OBJECT-TYPE
        SYNTAX        Integer32
        MAX-ACCESS        read-only
        STATUS        current
        DESCRIPTION   "bytes free"
        ::= { rc2kDeviceGlobalEntry 6 }

rc2kDeviceGlobalPcmciaNumFiles OBJECT-TYPE
        SYNTAX        Integer32
        MAX-ACCESS        read-only
        STATUS        current
        DESCRIPTION   "# files in pcmcia"
        ::= { rc2kDeviceGlobalEntry 7 }
 
rc2kDeviceGlobalAction OBJECT-TYPE
        SYNTAX        INTEGER {
                            none(1),
                            resetPcmcia(2)
                      }
        MAX-ACCESS        read-write
        STATUS        current
        DESCRIPTION   "none(1), resetPcmcia(2), .."
        ::= { rc2kDeviceGlobalEntry 8 }

rc2kDeviceGlobalResult OBJECT-TYPE
        SYNTAX        INTEGER {
                            none(1),
                            inProgress(2),
                            success(3),
                            fail(4)
                      }
        MAX-ACCESS        read-only
        STATUS        current
        DESCRIPTION   "Used to indicate the result of the last action
                      performed on one of the system's device."
        ::= { rc2kDeviceGlobalEntry 9 }

-- 2k Device Separator1 
 
rc2kDeviceSeparator1 OBJECT-TYPE
        SYNTAX          Integer32
        MAX-ACCESS        	read-only
        STATUS        	current
        DESCRIPTION   	"This leaf is used to provide a separation between
			tables.  No meaningful information is stored in this
			variable." 
        ::= { rc2kDevice 2 }

 
-- 2k Device Flash File table

rc2kDeviceFlashFileTable OBJECT-TYPE
        SYNTAX        SEQUENCE OF Rc2kDeviceFlashFileEntry
        MAX-ACCESS        not-accessible
        STATUS        current
        DESCRIPTION   "2k Flash table"
        ::= { rc2kDevice 3 }

rc2kDeviceFlashFileEntry OBJECT-TYPE
        SYNTAX        Rc2kDeviceFlashFileEntry
        MAX-ACCESS        not-accessible
        STATUS        current
        DESCRIPTION   "Entry containing infomation of 2k CPU Serial Port"
        INDEX         { rc2kDeviceFlashFileSlot, rc2kDeviceFlashFileName }
        ::= { rc2kDeviceFlashFileTable 1 }

Rc2kDeviceFlashFileEntry ::= SEQUENCE {
                rc2kDeviceFlashFileSlot	INTEGER,
                rc2kDeviceFlashFileName DisplayString,
                rc2kDeviceFlashFileDate DisplayString,
                rc2kDeviceFlashFileSize INTEGER
        }

rc2kDeviceFlashFileSlot OBJECT-TYPE
        SYNTAX        INTEGER (5..6) 
        MAX-ACCESS        read-only
        STATUS        current
        DESCRIPTION   "slot number"
        ::= { rc2kDeviceFlashFileEntry 1 }

rc2kDeviceFlashFileName OBJECT-TYPE
        SYNTAX        DisplayString (SIZE(0..64))
        MAX-ACCESS        read-only
        STATUS        current
        DESCRIPTION   "name of file"
        ::= { rc2kDeviceFlashFileEntry 2 }

rc2kDeviceFlashFileDate OBJECT-TYPE
        SYNTAX        DisplayString (SIZE(0..32))
        MAX-ACCESS        read-only
        STATUS        current
        DESCRIPTION   "date"
        ::= { rc2kDeviceFlashFileEntry 3 }

rc2kDeviceFlashFileSize OBJECT-TYPE
        SYNTAX        Integer32
        MAX-ACCESS        read-only
        STATUS        current
        DESCRIPTION   "size in bytes"
        ::= { rc2kDeviceFlashFileEntry 4 }

-- 2k Device Pcmcia present

rc2kDevicePcmciaPresent OBJECT-TYPE
        SYNTAX        TruthValue
        MAX-ACCESS        read-only
        STATUS        current
        DESCRIPTION   "pcmcia is a slower device. This leaf is used to
                       stop the access into pcmcia file table when it
                       got the end of flash file table."
        ::= { rc2kDevice 4 }

-- 2k Device Pcmcia File table

rc2kDevicePcmciaFileTable OBJECT-TYPE
        SYNTAX        SEQUENCE OF Rc2kDevicePcmciaFileEntry
        MAX-ACCESS        not-accessible
        STATUS        current
        DESCRIPTION   "2k PCMCIA table"
        ::= { rc2kDevice 5 }

rc2kDevicePcmciaFileEntry OBJECT-TYPE
        SYNTAX        Rc2kDevicePcmciaFileEntry
        MAX-ACCESS        not-accessible
        STATUS        current
        DESCRIPTION   "Entry containing infomation of 2k CPU Serial Port"
        INDEX         { rc2kDevicePcmciaFileSlot, rc2kDevicePcmciaFileName }
        ::= { rc2kDevicePcmciaFileTable 1 }

Rc2kDevicePcmciaFileEntry ::= SEQUENCE {
                rc2kDevicePcmciaFileSlot INTEGER,
                rc2kDevicePcmciaFileName DisplayString,
                rc2kDevicePcmciaFileDate DisplayString,
                rc2kDevicePcmciaFileSize INTEGER
        }

rc2kDevicePcmciaFileSlot OBJECT-TYPE
        SYNTAX        INTEGER (5..6)
        MAX-ACCESS        read-only
        STATUS        current
        DESCRIPTION   "slot number"
        ::= { rc2kDevicePcmciaFileEntry 1 }

rc2kDevicePcmciaFileName OBJECT-TYPE
        SYNTAX        DisplayString (SIZE(0..64))
        MAX-ACCESS        read-only
        STATUS        current
        DESCRIPTION   "name of file"
        ::= { rc2kDevicePcmciaFileEntry 2 }

rc2kDevicePcmciaFileDate OBJECT-TYPE
        SYNTAX        DisplayString (SIZE(0..32))
        MAX-ACCESS        read-only
        STATUS        current
        DESCRIPTION   "date"
        ::= { rc2kDevicePcmciaFileEntry 3 }

rc2kDevicePcmciaFileSize OBJECT-TYPE
        SYNTAX        Integer32
        MAX-ACCESS        read-only
        STATUS        current
        DESCRIPTION   "size in bytes"
        ::= { rc2kDevicePcmciaFileEntry 4 }

-- 2k Device Separator2

rc2kDeviceSeparator2 OBJECT-TYPE 
        SYNTAX        Integer32
        MAX-ACCESS          read-only 
        STATUS          current 
        DESCRIPTION     "This leaf is used to provide a separation between 
                        tables.  No meaningful information is stored in this
                        variable."
        ::= { rc2kDevice 6 } 


-- 2k Boot Config Table

rc2kBootConfigTable OBJECT-TYPE
        SYNTAX        SEQUENCE OF Rc2kBootConfigEntry
        MAX-ACCESS        not-accessible
        STATUS        current
        DESCRIPTION   "2k Boot Configuration table"
        ::= { rc2k 5 }

rc2kBootConfigEntry OBJECT-TYPE
        SYNTAX        Rc2kBootConfigEntry
        MAX-ACCESS        not-accessible
        STATUS        current
        DESCRIPTION   "Entry containing boot configuration information."
        INDEX         { rc2kBootConfigSlot }
        ::= { rc2kBootConfigTable 1 }

Rc2kBootConfigEntry ::= SEQUENCE {
		rc2kBootConfigSlot 			INTEGER,
		rc2kBootConfigLastBootConfigSource	DisplayString,
		rc2kBootConfigLastRuntimeImageSource	DisplayString,
		rc2kBootConfigLastRuntimeConfigSource	DisplayString,
		rc2kBootConfigPrimaryImageSource	DisplayString,
		rc2kBootConfigPrimaryConfigSource	DisplayString,
		rc2kBootConfigSecondaryImageSource	DisplayString,
		rc2kBootConfigSecondaryConfigSource	DisplayString,
		rc2kBootConfigTertiaryImageSource	DisplayString,
		rc2kBootConfigTertiaryConfigSource	DisplayString,
		rc2kBootConfigEnableAutoBoot		TruthValue,
		rc2kBootConfigEnableFactoryDefaults	TruthValue,
		rc2kBootConfigEnableDebugMode		TruthValue,
		rc2kBootConfigEnableHwWatchDogTimer	TruthValue,
		rc2kBootConfigEnableRebootOnError	TruthValue,
		rc2kBootConfigEnableTelnetServer	TruthValue,
		rc2kBootConfigEnableRloginServer	TruthValue,
		rc2kBootConfigEnableFtpServer		TruthValue,
		rc2kBootConfigEnableTftpServer		TruthValue,
		rc2kBootConfigSwVersion			DisplayString,
                rc2kBootConfigMulticastConfigProfile    INTEGER
        }

rc2kBootConfigSlot OBJECT-TYPE
        SYNTAX        INTEGER (5..6)
        MAX-ACCESS        read-only
        STATUS        current
        DESCRIPTION   "slot number"
        ::= { rc2kBootConfigEntry 1 }

rc2kBootConfigLastBootConfigSource OBJECT-TYPE
        SYNTAX        DisplayString (SIZE(0..64))
        MAX-ACCESS        read-only
        STATUS        current
        DESCRIPTION   "boot config source"
        ::= { rc2kBootConfigEntry 2 }

rc2kBootConfigLastRuntimeImageSource OBJECT-TYPE
        SYNTAX        DisplayString (SIZE(0..64))
        MAX-ACCESS        read-only
        STATUS        current
        DESCRIPTION   "runtime image source"
        ::= { rc2kBootConfigEntry 3 }

rc2kBootConfigLastRuntimeConfigSource OBJECT-TYPE
        SYNTAX        DisplayString (SIZE(0..64))
        MAX-ACCESS        read-only
        STATUS        current
        DESCRIPTION   "runtime config source"
        ::= { rc2kBootConfigEntry 4 }

rc2kBootConfigPrimaryImageSource OBJECT-TYPE
        SYNTAX        DisplayString (SIZE(0..64))
        MAX-ACCESS        read-write
        STATUS        current
        DESCRIPTION   "image source"
        ::= { rc2kBootConfigEntry 5 }

rc2kBootConfigPrimaryConfigSource OBJECT-TYPE
        SYNTAX        DisplayString (SIZE(0..64))
        MAX-ACCESS        read-write
        STATUS        current
        DESCRIPTION   "config source"
        ::= { rc2kBootConfigEntry 6 }

rc2kBootConfigSecondaryImageSource OBJECT-TYPE
        SYNTAX        DisplayString (SIZE(0..64))
        MAX-ACCESS        read-write
        STATUS        current
        DESCRIPTION   "image source"
        ::= { rc2kBootConfigEntry 7 }

rc2kBootConfigSecondaryConfigSource OBJECT-TYPE
        SYNTAX        DisplayString (SIZE(0..64))
        MAX-ACCESS        read-write
        STATUS        current
        DESCRIPTION   "config source"
        ::= { rc2kBootConfigEntry 8 }
 
rc2kBootConfigTertiaryImageSource OBJECT-TYPE
        SYNTAX        DisplayString (SIZE(0..64))
        MAX-ACCESS        read-write
        STATUS        current
        DESCRIPTION   "image source"
        ::= { rc2kBootConfigEntry 9 }
 
rc2kBootConfigTertiaryConfigSource OBJECT-TYPE
        SYNTAX        DisplayString (SIZE(0..64))
        MAX-ACCESS        read-write
        STATUS        current
        DESCRIPTION   "config source"
        ::= { rc2kBootConfigEntry 10 }
 
rc2kBootConfigEnableAutoBoot OBJECT-TYPE
        SYNTAX        TruthValue
        MAX-ACCESS        read-write
        STATUS        current
        DESCRIPTION   "auto boot mode"
        ::= { rc2kBootConfigEntry 11 }

rc2kBootConfigEnableFactoryDefaults OBJECT-TYPE
        SYNTAX        TruthValue
        MAX-ACCESS        read-write
        STATUS        current
        DESCRIPTION   "use factory default"
        ::= { rc2kBootConfigEntry 12 }

rc2kBootConfigEnableDebugMode OBJECT-TYPE
        SYNTAX        TruthValue
        MAX-ACCESS        read-write
        STATUS        current
        DESCRIPTION   "debug mode"
        ::= { rc2kBootConfigEntry 13 }

rc2kBootConfigEnableHwWatchDogTimer OBJECT-TYPE
        SYNTAX        TruthValue
        MAX-ACCESS        read-write
        STATUS        current
        DESCRIPTION   "hw watch dog timer"
        ::= { rc2kBootConfigEntry 14 }

rc2kBootConfigEnableRebootOnError OBJECT-TYPE
        SYNTAX        TruthValue
        MAX-ACCESS        read-write
        STATUS        current
        DESCRIPTION   "reboot on error"
        ::= { rc2kBootConfigEntry 15 }

rc2kBootConfigEnableTelnetServer OBJECT-TYPE
        SYNTAX        TruthValue
        MAX-ACCESS        read-write
        STATUS        current
        DESCRIPTION   "telnet server"
        ::= { rc2kBootConfigEntry 16 }

rc2kBootConfigEnableRloginServer OBJECT-TYPE
        SYNTAX        TruthValue
        MAX-ACCESS        read-write
        STATUS        current
        DESCRIPTION   "rlogin server"
        ::= { rc2kBootConfigEntry 17 }

rc2kBootConfigEnableFtpServer OBJECT-TYPE
        SYNTAX        TruthValue
        MAX-ACCESS        read-write
        STATUS        current
        DESCRIPTION   "ftp server"
        ::= { rc2kBootConfigEntry 18 }

rc2kBootConfigEnableTftpServer OBJECT-TYPE
        SYNTAX        TruthValue
        MAX-ACCESS        read-write
        STATUS        current
        DESCRIPTION   "tftp server"
        ::= { rc2kBootConfigEntry 19 }

rc2kBootConfigSwVersion OBJECT-TYPE
        SYNTAX        DisplayString
        MAX-ACCESS        read-only
        STATUS        current
        DESCRIPTION   "current sw version"
        ::= { rc2kBootConfigEntry 20 }
 
rc2kBootConfigMulticastConfigProfile OBJECT-TYPE
        SYNTAX        INTEGER (1..6)
        MAX-ACCESS        read-only
        STATUS        current
        DESCRIPTION   "multicast config"
        DEFVAL        { 1 }
        ::= { rc2kBootConfigEntry 21 }


-- 2k Card table

rc2kCardTable OBJECT-TYPE
        SYNTAX        SEQUENCE OF Rc2kCardEntry
        MAX-ACCESS        not-accessible
        STATUS        current
        DESCRIPTION   "2k Card table"
        ::= { rc2k 6 }

rc2kCardEntry OBJECT-TYPE
        SYNTAX        Rc2kCardEntry
        MAX-ACCESS        not-accessible
        STATUS        current
        DESCRIPTION   "Entry containing information of 2k Card"
        INDEX         { rc2kCardIndex }
        ::= { rc2kCardTable 1 }

Rc2kCardEntry ::= SEQUENCE {
                rc2kCardIndex            INTEGER,
                rc2kCardFrontType        INTEGER,
                rc2kCardFrontDescription DisplayString,
                rc2kCardFrontAdminStatus INTEGER,
                rc2kCardFrontOperStatus  INTEGER,
                rc2kCardFrontSerialNum   DisplayString,
                rc2kCardFrontHwVersion   DisplayString,
                rc2kCardFrontPartNumber  DisplayString,
                rc2kCardFrontDateCode    DisplayString,
                rc2kCardFrontDeviations  DisplayString,
                rc2kCardFrontMacAddr     MacAddress,    --excluded
                rc2kCardBackType         INTEGER,
                rc2kCardBackDescription  DisplayString,
                rc2kCardBackSerialNum    DisplayString,
                rc2kCardBackHwVersion    DisplayString,
                rc2kCardBackPartNumber   DisplayString,
                rc2kCardBackDateCode     DisplayString,
                rc2kCardBackDeviations   DisplayString,
		rc2kCardPCMCIAType	 INTEGER,
		rc2kCardPCMCIADescr	 DisplayString,
		rc2kCardASICDescr	 DisplayString,
		rc2kCardFrontMasterIO	 TruthValue
        }

rc2kCardIndex OBJECT-TYPE
        SYNTAX        INTEGER (1..10)
        MAX-ACCESS        read-only
        STATUS        current
        DESCRIPTION   "slot number."
        ::= { rc2kCardEntry 1 }

rc2kCardFrontType OBJECT-TYPE
        SYNTAX        INTEGER {
        other(1),                        -- no card installed
        rc2kCPU(537788672),              -- 0010 0000 0000 1110 0000 0001 0000 0000
        rc2k48x100BaseTX(539033904),     -- 0010 0000 0010 0001 0000 0001 0011 0000
        rc2k24x100BaseTX(539033880),     -- 0010 0000 0010 0001 0000 0001 0001 1000
        rc2k8x1000BaseTX(539099400),     -- 0010 0000 0010 0010 0000 0001 0000 1000  
        rc2k24x100BaseFX(540082456),     -- 0010 0000 0011 0001 0000 0001 0001 1000
        rc2k16x1000BaseSXBB(540147984),  -- 0010 0000 0011 0010 0000 0001 0001 0000 
        rc2k2xOC12(541393154),           -- 0010 0000 0100 0101 0000 0001 0000 0010
        rc2k8xATM(542441736),            -- 0010 0000 0101 0101 0000 0001 0000 1000
        rc2k4xATM(542966020),            -- 0010 0000 0101 1101 0000 0001 0000 0100
        rc2kRMON(545128704),             -- 0010 0000 0111 1110 0000 0001 0000 0000
        rc2k8x1000BaseSXBB(540147976),   -- 0010 0000 0011 0010 0000 0001 0000 1000
        rc2k8x1000BaseLXBB(540156168),   -- 0010 0000 0011 0010 0010 0001 0000 1000
        rc2k8x1000BaseXDBB(540164360),   -- 0010 0000 0011 0010 0100 0001 0000 1000
        rc2k8x1000BaseIC(540168456),     -- 0010 0000 0011 0010 0101 0001 0000 1000 
        rc2k8x1000BaseSXRBB(540180744),  -- 0010 0000 0011 0010 1000 0001 0000 1000
        rc2k8x1000BaseLXRBB(540188936),  -- 0010 0000 0011 0010 1010 0001 0000 1000
        rc2k8xOC3(541327624),            -- 0010 0000 0100 0100 0000 0001 0000 1000
        rc2kMg48x100BaseTX(807469360),   -- 0011 0000 0010 0001 0000 0001 0011 0000
        rc2kMg32x100BaseTX(807473440),   -- 0011 0000 0010 0001 0001 0001 0010 0000
        rc2kMg16x100BaseTX(808522000),   -- 0011 0000 0011 0001 0001 0001 0001 0000
        rc2kMg8x1000BaseTX(808583432),   -- 0011 0000 0011 0010 0000 0001 0000 1000
        rc2kMg8x1000BaseIC(808603912)    -- 0011 0000 0011 0010 0101 0001 0000 1000
                      }
        MAX-ACCESS        read-only
        STATUS        current
        DESCRIPTION     "Used to indicate card types in the Accelar
                        8000 product families.

			For Accelar 8000 devices, all cards use
		      	an encoded value according to the following rule:

        +------+-------+-------+-------+------------+------+------+------+
bits  : |31-28 |     27-20     | 19-16 | 15 | 14-12 | 11-8 |     7-0     |
        +------+-------+-------+-------+----+-------+------+------+------+
field : |  a   |       c       |   d   |  e |    f  |  g   |      h      |
        +------+-------+-------+-------+----+-------+------+------+------+

     a : Family type/Product line
            0x0 = 0000 = Reserved
            0x1 = 0001 = Monoploy non specific (e.g backplane, psu, fans)
            0x2 = 0010 = Boardwalk
            0x3 = 0011 = Marvin Gardens
            0x4 = 0100 = Pacific
            0x5 = 0101 = ParkPlace

     c : Interface / device type:
            0x00 = 00000000 = CPU
            0x01 = 00000001 = Switch fabric
            0x02 = 00000010 = Copper Ethernet
            0x03 = 00000011 = Fiber Ethernet
            0x04 = 00000100 = Sonet (Packets)
            0x05 = 00000101 = ATM
            0x06 = 00000110 = Token Ring
            0x07 = 00000111 = RMON
            0x08 = 00001000 = BFM (Frame or cells indicated by field 'a' above)
            0x09 = 00001001 = PSU
            0x0a = 00001010 = Fan Tray
            0x0b = 00001011 = Chassis/Backplane

     d : Maximum speed (highest negotiable speed)
            0x0 = 0000 = 10 Mbit  
            0x1 = 0001 = 100 Mbit  
            0x2 = 0010 = 1 Gbit
            0x3 = 0011 = 10 Gbit
            0x4 = 0100 = OC-3
            0x5 = 0101 = OC-12
            0x6 = 0110 = OC-48
            0x7 = 0111 = OC-92
            0x8 = 1000 = OC-192
            0x9 = 1001 = 4 Mbit (TR)
            0xa = 1010 = 16 Mbit (TR)
            0xb = 1011 = E3 
            0xc = 1100 = DS1
            0xd = 1101 = DS3
            0xe = 1110 = none (no PHY interfaces on board)
            0xf = 1111 = Max speed indicated implicitly in field (c) (for expansion)
   
     e : 0=non-redundant, 
         1=redundant

     f : Card specific info. 
             For Gigabit used as follows:
		 000=short-haul (SX)
		 010=long-haul (LX)
		 100=extra-distance (DX)
                 101=GBIC
	     For ATM/Sonet used as follows
                 000 = multi mode
                 001 = single mode
                 010 = single or multimode
		 011 = not applicable (e.g., copper has no mode)
             For Marvin Gardens, indicates number of MDA slots
                 000 = none
                 001 = one option slots
                 010 = two option slots
                 011 = three option slots
            For Power Supplies:
                 000 = AC PSU
                 001 = DC PSU

     g : Chassis type
         0x0 = 0000 = work-group (single card switches, etc)
         0x1 = 0001 = back-bone (chassis based products)
         0x2 = 0010 = MDA (option modules)

     h : Number of ports (binary representation obmited)
         (for ACIM/BFM cards, this is number of octapids/blackbirds/dea)
               0x00 =  no ports (cpus, switch fabrics)
               0x01 =  1-port, 
               0x02 =  2-port, 
               0x04 =  4-port,
               0x06 =  6-port,
               0x08 =  8-port,
               0x0c = 12-port,
               0x10 = 16-port,
               0x18 = 24-port,
               0x22 = 36-port,
               0x30 = 48-port,
               0x40 = 64-port.

		"
        ::= { rc2kCardEntry 2 }

rc2kCardFrontDescription OBJECT-TYPE
        SYNTAX        DisplayString (SIZE (0..20))
        MAX-ACCESS        read-only
        STATUS        current
        DESCRIPTION   "description"
        ::= { rc2kCardEntry 3 }

rc2kCardFrontAdminStatus OBJECT-TYPE
        SYNTAX       INTEGER {
                         up(1),
                         down(2),
                         testing(3)
                      }
        MAX-ACCESS        read-write
        STATUS        current
        DESCRIPTION   "Used to indicate the administrative status of this
                       card"
        ::= { rc2kCardEntry 4 }

rc2kCardFrontOperStatus OBJECT-TYPE
        SYNTAX        INTEGER {
                         up(1),
                         down(2),
                         testing(3),
                         unknown(4),
                         dormant(5)
                      }
        MAX-ACCESS        read-only
        STATUS        current
        DESCRIPTION   "Used to indicate the operational status of this card."
        ::= { rc2kCardEntry 5 }

rc2kCardFrontSerialNum OBJECT-TYPE
        SYNTAX        DisplayString (SIZE (0..20))
        MAX-ACCESS        read-only
        STATUS        current
        DESCRIPTION   "serial number of card"
        ::= { rc2kCardEntry 6 }

rc2kCardFrontHwVersion OBJECT-TYPE
        SYNTAX        DisplayString (SIZE (0..20))
        MAX-ACCESS        read-only
        STATUS        current
        DESCRIPTION   "hardware version"
        ::= { rc2kCardEntry 7 }

rc2kCardFrontPartNumber OBJECT-TYPE
        SYNTAX        DisplayString (SIZE (0..20))
        MAX-ACCESS        read-only
        STATUS        current
        DESCRIPTION   "part number"
        ::= { rc2kCardEntry 8 }

rc2kCardFrontDateCode OBJECT-TYPE
        SYNTAX        DisplayString (SIZE (0..20))
        MAX-ACCESS        read-only
        STATUS        current
        DESCRIPTION   "date code"
        ::= { rc2kCardEntry 9 }

rc2kCardFrontDeviations OBJECT-TYPE
        SYNTAX        DisplayString (SIZE (0..20))
        MAX-ACCESS        read-only
        STATUS        current
        DESCRIPTION   "deviations"
        ::= { rc2kCardEntry 10 }

rc2kCardFrontMacAddr OBJECT-TYPE
        SYNTAX        MacAddress
        MAX-ACCESS        read-only
        STATUS        obsolete
        DESCRIPTION   "base mac address"
        ::= { rc2kCardEntry 11 }

rc2kCardBackType OBJECT-TYPE
        SYNTAX        INTEGER {
        other(1),                  -- no card installed
        rc2kBackplane(536969472),  -- 0010 0000 0000 0001 1000 0001 0000 0000
	rc2kSFM(538837248),        -- 0010 0000 0001 1111 0000 0001 0000 0000
	rc2kBFM0(546177280),       -- 0010 0000 1000 1111 0000 0001 0000 0000
	rc2kBFM2(546177282),       -- 0010 0000 1000 1111 0000 0001 0000 0010
	rc2kBFM3(546177283),       -- 0010 0000 1000 1111 0000 0001 0000 0011
	rc2kBFM6(546177286),       -- 0010 0000 1000 1111 0000 0001 0000 0100
	rc2kBFM8(546177288),       -- 0010 0000 1000 1111 0000 0001 0000 1000
	rc2kMGSFM(807272704)       -- 0011 0000 0001 1110 0000 0001 0000 0000
			}
        MAX-ACCESS        read-only
        STATUS        current
        DESCRIPTION   "Refer to rc2kCardFrontType for the encoding scheme"
        ::= { rc2kCardEntry 12 }

rc2kCardBackDescription OBJECT-TYPE
        SYNTAX        DisplayString (SIZE (0..20))
        MAX-ACCESS        read-only
        STATUS        current
        DESCRIPTION   "description"
        ::= { rc2kCardEntry 13 }

rc2kCardBackSerialNum OBJECT-TYPE
        SYNTAX        DisplayString (SIZE (0..20))
        MAX-ACCESS        read-only
        STATUS        current
        DESCRIPTION   "serial number of card"
        ::= { rc2kCardEntry 14 }

rc2kCardBackHwVersion OBJECT-TYPE
        SYNTAX        DisplayString (SIZE (0..20))
        MAX-ACCESS        read-only
        STATUS        current
        DESCRIPTION   "hardware version"
        ::= { rc2kCardEntry 15 }

rc2kCardBackPartNumber OBJECT-TYPE
        SYNTAX        DisplayString (SIZE (0..20))
        MAX-ACCESS        read-only
        STATUS        current
        DESCRIPTION   "part number"
        ::= { rc2kCardEntry 16 }

rc2kCardBackDateCode OBJECT-TYPE
        SYNTAX        DisplayString (SIZE (0..20))
        MAX-ACCESS        read-only
        STATUS        current
        DESCRIPTION   "date code"
        ::= { rc2kCardEntry 17 }

rc2kCardBackDeviations OBJECT-TYPE
        SYNTAX        DisplayString (SIZE (0..20))
        MAX-ACCESS        read-only
        STATUS        current
        DESCRIPTION   "deviations"
        ::= { rc2kCardEntry 18 }

rc2kCardPCMCIAType OBJECT-TYPE
        SYNTAX        INTEGER {
                         none(1),
			 modemCard(2),
                         ethernetCard(3),
                         ataDisk(4)
                      }  
        MAX-ACCESS        read-only
        STATUS        current
        DESCRIPTION   "Used to indicate the type of PCMCIA card currently
                      installed in this CPU card, if any.

                      For non-CPU cards, this variable has no meaning and
                      will always be set to none(1)."
        DEFVAL        { none }
        ::= { rc2kCardEntry 19 }

rc2kCardPCMCIADescr OBJECT-TYPE
        SYNTAX        DisplayString (SIZE (0..128))
        MAX-ACCESS        read-only
        STATUS        current
        DESCRIPTION   "PCMCIA descriptor"
        ::= { rc2kCardEntry 20 }

rc2kCardASICDescr OBJECT-TYPE
        SYNTAX        	DisplayString (SIZE (0..128))
        MAX-ACCESS        	read-only
        STATUS        	current
        DESCRIPTION   	"ASIC descriptor"
        ::= { rc2kCardEntry 21 }

rc2kCardFrontMasterIO OBJECT-TYPE
        SYNTAX        	TruthValue
        MAX-ACCESS        	read-only
        STATUS        	current
        DESCRIPTION   	"Used to indicate whether an IO card in a 8100 device
		       	is operating in the 'master' mode.

			This variable is not meaningful for non-IO cards and
			non-8100 devices."
	DEFVAL	      { false }
        ::= { rc2kCardEntry 22 }

-- 2k copy file

rc2kCopyFile     OBJECT IDENTIFIER ::= { rc2k 7 }

rc2kCopyFileSource OBJECT-TYPE
        SYNTAX        DisplayString (SIZE(0..64))
        MAX-ACCESS        read-write
        STATUS        current
        DESCRIPTION   "source file"
        ::= { rc2kCopyFile 1 }

rc2kCopyFileDestination OBJECT-TYPE
        SYNTAX        DisplayString (SIZE(0..64))
        MAX-ACCESS        read-write
        STATUS        current
        DESCRIPTION   "dest file"
        ::= { rc2kCopyFile 2 }

rc2kCopyFileAction OBJECT-TYPE
        SYNTAX        INTEGER {
                            none(1),
                            start(2)
                      }
        MAX-ACCESS        read-write
        STATUS        current
        DESCRIPTION   "start or cancell"
        ::= { rc2kCopyFile 3 }

rc2kCopyFileResult OBJECT-TYPE
        SYNTAX        INTEGER {
                            none(1),
                            inProgress(2),
                            success(3),
                            fail(4),
                            invalidSource(5),
                            invalidDestination(6),
                            outOfMemory(7),
                            outOfSpace(8),
                            fileNotFound(9)
                      }
        MAX-ACCESS        read-only
        STATUS        current
        DESCRIPTION   "result"
        ::= { rc2kCopyFile 4 }

-- 2k Qos

rc2kQos     OBJECT IDENTIFIER ::= { rc2k 8 }

rc2kQosQosTable OBJECT-TYPE
        SYNTAX        	SEQUENCE OF Rc2kQosQosEntry
        MAX-ACCESS        	not-accessible
        STATUS        	current
        DESCRIPTION   	"This table is used to define the Quality Of
			Service(QOS) profiles for the system.  The system 
			can support eight different QOS levels.  Each QOS
			level can be individually configured." 
        ::= { rc2kQos 1 }

rc2kQosQosEntry OBJECT-TYPE
        SYNTAX        	Rc2kQosQosEntry
        MAX-ACCESS        	not-accessible
        STATUS        	current
        DESCRIPTION   	"QOS profile entry."
        INDEX         	{ rc2kQosQosRow }
        ::= { rc2kQosQosTable 1 }

Rc2kQosQosEntry ::= SEQUENCE {
                rc2kQosQosRow INTEGER,
                rc2kQosQosLevel INTEGER,
                rc2kQosQosName DisplayString,
                rc2kQosQosAdminWeight INTEGER,
                rc2kQosQosOperWeight INTEGER,
                rc2kQosOctapidMode INTEGER,
                rc2kQosQosAdminThreshold INTEGER,
                rc2kQosQosOperThreshold INTEGER
        }

rc2kQosQosRow OBJECT-TYPE
        SYNTAX        INTEGER (1..8)
        MAX-ACCESS        read-only
        STATUS        current
        DESCRIPTION   "Used to uniquely identify a row in this table."
        ::= { rc2kQosQosEntry 1 }

rc2kQosQosLevel OBJECT-TYPE
        SYNTAX        INTEGER (0..7)
        MAX-ACCESS        read-only
        STATUS        current
        DESCRIPTION   "QOS level"
        ::= { rc2kQosQosEntry 2 }

rc2kQosQosName OBJECT-TYPE
        SYNTAX        	DisplayString (SIZE (0..20))
        MAX-ACCESS        	read-write
        STATUS        	current
        DESCRIPTION   	"Qos level name"
        ::= { rc2kQosQosEntry 3 }

rc2kQosQosAdminWeight OBJECT-TYPE
        SYNTAX        Integer32
        MAX-ACCESS        read-write
        STATUS        current
        DESCRIPTION   "Administrative transmit opportunity percentage"
        ::= { rc2kQosQosEntry 4 }

rc2kQosQosOperWeight OBJECT-TYPE
        SYNTAX        Integer32
        MAX-ACCESS        read-only
        STATUS        current
        DESCRIPTION   "Operational transmit opportunity percentage"
        ::= { rc2kQosQosEntry 5 }

rc2kQosOctapidMode OBJECT-TYPE
        SYNTAX        INTEGER {
                          modeSingle(1),
                          mode100(2)
                      }
        MAX-ACCESS        read-write
        STATUS        current
        DESCRIPTION   "Octapid mode"
        ::= { rc2kQosQosEntry 6 }

rc2kQosQosAdminThreshold OBJECT-TYPE
        SYNTAX        INTEGER {
                          none(0),
                          oneEight(1),
                          oneQuarter(2),
                          threeEight(3),
                          halfSdram(4),
                          fiveEight(5),
                          threeQuarter(6),
                          sevenEights(7),
                          allSdram(8),
                          notpresent(9)
                      }
        MAX-ACCESS        read-write
        STATUS        current
        DESCRIPTION   "Administrative queue threshold"
        ::= { rc2kQosQosEntry 7 }

rc2kQosQosOperThreshold OBJECT-TYPE
        SYNTAX        INTEGER {
                          none(0),
                          oneEight(1),
                          oneQuarter(2),
                          threeEight(3),
                          halfSdram(4),
                          fiveEight(5),
                          threeQuarter(6),
                          sevenEights(7),
                          allSdram(8),
                          notpresent(9)
                      }
        MAX-ACCESS        read-only
        STATUS        current
        DESCRIPTION   "Operational queue threshold"
        ::= { rc2kQosQosEntry 8 }


-- 2k Qos Ingress Tag To Qos Table

rc2kQosIngressTagToQosTable OBJECT-TYPE
        SYNTAX        	SEQUENCE OF Rc2kQosIngressTagToQosEntry
        MAX-ACCESS        	not-accessible
        STATUS        	current
        DESCRIPTION   	"This table is used to specify the 802.1P
			to QOS (802.1P->QOS) mapping on packet 
			ingress."
        ::= { rc2kQos 2 }

rc2kQosIngressTagToQosEntry OBJECT-TYPE
        SYNTAX        	Rc2kQosIngressTagToQosEntry
        MAX-ACCESS        	not-accessible
        STATUS        	current
        DESCRIPTION   	"Entry containing infomation of 8021P->Qos mapping"
        INDEX         	{ rc2kQosIngressTagToQosRow }
        ::= { rc2kQosIngressTagToQosTable 1 }

Rc2kQosIngressTagToQosEntry ::= SEQUENCE {
                rc2kQosIngressTagToQosRow INTEGER,
                rc2kQosIngressTagToQosInIeee8021P INTEGER,
                rc2kQosIngressTagToQosQosLevel INTEGER
        }

rc2kQosIngressTagToQosRow OBJECT-TYPE
        SYNTAX        INTEGER (1..8)
        MAX-ACCESS        read-only
        STATUS        current
        DESCRIPTION   "Used to uniquely identify a row in this table."
        ::= { rc2kQosIngressTagToQosEntry 1 }

rc2kQosIngressTagToQosInIeee8021P OBJECT-TYPE
        SYNTAX        INTEGER (0..7)
        MAX-ACCESS        read-only
        STATUS        current
        DESCRIPTION   "802.1P"
        ::= { rc2kQosIngressTagToQosEntry 2 }

rc2kQosIngressTagToQosQosLevel OBJECT-TYPE
        SYNTAX        INTEGER (0..7)
        MAX-ACCESS        read-write
        STATUS        current
        DESCRIPTION   "Qos level"
        ::= { rc2kQosIngressTagToQosEntry 3 }

-- 2k Ingress DsField To Qos Table

rc2kQosIngressDsFieldToQosTable OBJECT-TYPE
        SYNTAX        	SEQUENCE OF Rc2kQosIngressDsFieldToQosEntry
        MAX-ACCESS        	not-accessible
        STATUS        	current
	DESCRIPTION	"This table is used to specify the DSCP
			field to QOS (DsField->QOS) mapping on
			packet ingress."
        ::= { rc2kQos 3 }

rc2kQosIngressDsFieldToQosEntry OBJECT-TYPE
        SYNTAX        Rc2kQosIngressDsFieldToQosEntry
        MAX-ACCESS        not-accessible
        STATUS        current
        DESCRIPTION   "Entry containing infomation of DsField->Qos mapping"
        INDEX         { rc2kQosIngressDsFieldToQosRow }
        ::= { rc2kQosIngressDsFieldToQosTable 1 }

Rc2kQosIngressDsFieldToQosEntry ::= SEQUENCE {
                rc2kQosIngressDsFieldToQosRow INTEGER,
                rc2kQosIngressDsFieldToQosInDsField INTEGER,
                rc2kQosIngressDsFieldToQosQosLevel INTEGER
        }

rc2kQosIngressDsFieldToQosRow OBJECT-TYPE
        SYNTAX        INTEGER (1..64)
        MAX-ACCESS        read-only
        STATUS        current
        DESCRIPTION   "Used to uniquely identify a row in this table."
        ::= { rc2kQosIngressDsFieldToQosEntry 1 }

rc2kQosIngressDsFieldToQosInDsField OBJECT-TYPE
        SYNTAX        INTEGER (0..63)
        MAX-ACCESS        read-only
        STATUS        current
        DESCRIPTION   "diffserv dscp"
        ::= { rc2kQosIngressDsFieldToQosEntry 2 }

rc2kQosIngressDsFieldToQosQosLevel OBJECT-TYPE
        SYNTAX        INTEGER (0..7)
        MAX-ACCESS        read-write
        STATUS        current
        DESCRIPTION   "qos level"
        ::= { rc2kQosIngressDsFieldToQosEntry 3 }

-- 2k Egress Qos To Tag Table

rc2kQosEgressQosToTagTable OBJECT-TYPE
        SYNTAX        	SEQUENCE OF Rc2kQosEgressQosToTagEntry
        MAX-ACCESS        	not-accessible
        STATUS        	current
        DESCRIPTION  	"This table is used to specify the QOS to
			802.1P (QOS->802.1P) mapping on packet
			egress."
        ::= { rc2kQos 4 }

rc2kQosEgressQosToTagEntry OBJECT-TYPE
        SYNTAX        Rc2kQosEgressQosToTagEntry
        MAX-ACCESS        not-accessible
        STATUS        current
        DESCRIPTION   "Entry containing infomation of Qos->Qos mapping"
        INDEX         { rc2kQosEgressQosToTagRow }
        ::= { rc2kQosEgressQosToTagTable 1 }

Rc2kQosEgressQosToTagEntry ::= SEQUENCE {
                rc2kQosEgressQosToTagRow INTEGER,
                rc2kQosEgressQosToTagQosLevel INTEGER,
                rc2kQosEgressQosToTagOutIeee8021P INTEGER
        }

rc2kQosEgressQosToTagRow OBJECT-TYPE
        SYNTAX        INTEGER (1..8)
        MAX-ACCESS        read-only
        STATUS        current
        DESCRIPTION   "Used to uniquely identify a row in this table."
        ::= { rc2kQosEgressQosToTagEntry 1 }

rc2kQosEgressQosToTagQosLevel OBJECT-TYPE
        SYNTAX        INTEGER (0..7)
        MAX-ACCESS        read-only
        STATUS        current
        DESCRIPTION   "qos level"
        ::= { rc2kQosEgressQosToTagEntry 2 }

rc2kQosEgressQosToTagOutIeee8021P OBJECT-TYPE
        SYNTAX        INTEGER (0..7)
        MAX-ACCESS        read-write
        STATUS        current
        DESCRIPTION   "802.1P"
        ::= { rc2kQosEgressQosToTagEntry 3 }

-- 2k Egress Qos To DsField Table

rc2kQosEgressQosToDsFieldTable OBJECT-TYPE
        SYNTAX        	SEQUENCE OF Rc2kQosEgressQosToDsFieldEntry
        MAX-ACCESS        	not-accessible
        STATUS        	current
        DESCRIPTION   	"This table is used to specify the QOS to
			DSCP field (QOS->DsField) mapping on packet
			egress."
        ::= { rc2kQos 5 }

rc2kQosEgressQosToDsFieldEntry OBJECT-TYPE
        SYNTAX        Rc2kQosEgressQosToDsFieldEntry
        MAX-ACCESS        not-accessible
        STATUS        current
        DESCRIPTION   "Entry containing infomation of Qos->Qos mapping"
        INDEX         { rc2kQosEgressQosToDsFieldRow }
        ::= { rc2kQosEgressQosToDsFieldTable 1 }

Rc2kQosEgressQosToDsFieldEntry ::= SEQUENCE {
                rc2kQosEgressQosToDsFieldRow INTEGER,
                rc2kQosEgressQosToDsFieldQosLevel INTEGER,
                rc2kQosEgressQosToDsFieldOutDsField INTEGER
        }

rc2kQosEgressQosToDsFieldRow OBJECT-TYPE
        SYNTAX        INTEGER (1..8)
        MAX-ACCESS        read-only
        STATUS        current
        DESCRIPTION   "Used to uniquely identify a row in this table."
        ::= { rc2kQosEgressQosToDsFieldEntry 1 }

rc2kQosEgressQosToDsFieldQosLevel OBJECT-TYPE
        SYNTAX        INTEGER (0..7)
        MAX-ACCESS        read-only
        STATUS        current
        DESCRIPTION   "qos level"
        ::= { rc2kQosEgressQosToDsFieldEntry 2 }

rc2kQosEgressQosToDsFieldOutDsField OBJECT-TYPE
        SYNTAX        INTEGER (0..63)
        MAX-ACCESS        read-write
        STATUS        current
        DESCRIPTION   "diffserv dscp"
        ::= { rc2kQosEgressQosToDsFieldEntry 3 }

-- 2k Traffic Profile Table

rc2kQosTrafficProfileTable OBJECT-TYPE
        SYNTAX        	SEQUENCE OF Rc2kQosTrafficProfileEntry
        MAX-ACCESS        	not-accessible
        STATUS        	current
        DESCRIPTION   	"This table is used to specify traffic profiles 
			for the system.  These traffic profiles are
			used for policying purposes to guarantee streams
			of traffic do not egress the system above a
			certain rate.  These traffic profiles are applied
			in the 'rcIpFilterTable'."
        ::= { rc2kQos 6 }

rc2kQosTrafficProfileEntry OBJECT-TYPE
        SYNTAX        Rc2kQosTrafficProfileEntry
        MAX-ACCESS        not-accessible
        STATUS        current
        DESCRIPTION   "Entry containing infomation of Qos->Qos mapping"
        INDEX         { rc2kQosTrafficProfileId }
        ::= { rc2kQosTrafficProfileTable 1 }

Rc2kQosTrafficProfileEntry ::= SEQUENCE {
                rc2kQosTrafficProfileId INTEGER,
                rc2kQosTrafficProfileName DisplayString,
                rc2kQosTrafficProfileEnable TruthValue,
                rc2kQosTrafficProfileTranslateDsFieldEnable TruthValue,
                rc2kQosTrafficProfileInProfileDsField INTEGER,
                rc2kQosTrafficProfileOutProfileDsField INTEGER,
                rc2kQosTrafficProfileDiscardEnable TruthValue,
                rc2kQosTrafficProfileAverageRate INTEGER,
                rc2kQosTrafficProfilePeakRate INTEGER,
                rc2kQosTrafficProfileRowStatus RowStatus
        }

rc2kQosTrafficProfileId OBJECT-TYPE
        SYNTAX        	INTEGER (1..64)
        MAX-ACCESS        	read-only
        STATUS        	current
        DESCRIPTION   	"Profile id"
        ::= { rc2kQosTrafficProfileEntry 1 }

rc2kQosTrafficProfileName OBJECT-TYPE
        SYNTAX        	DisplayString (SIZE (0..32))
        MAX-ACCESS        	read-write
        STATUS        	current
        DESCRIPTION   	"Profile name"
        ::= { rc2kQosTrafficProfileEntry 2 }

rc2kQosTrafficProfileEnable OBJECT-TYPE
        SYNTAX        	TruthValue
        MAX-ACCESS        	read-write
        STATUS        	current
        DESCRIPTION   	"Enable this entry"
	DEFVAL		{ true }
        ::= { rc2kQosTrafficProfileEntry 3 }

rc2kQosTrafficProfileTranslateDsFieldEnable OBJECT-TYPE
        SYNTAX        	TruthValue
        MAX-ACCESS        	read-write
        STATUS        	current
        DESCRIPTION    	"Used to specify whether translation of the DSCP
			field should be performed.  If enabled, the value 
			in the DSCP field for packets that fall within 
			the traffic profile will get translated to
			'rc2kQosTrafficProfileInProfileDsField'.  Packets
			that fall outside the traffic profile will get
			translated to 'rc2kQosTrafficProfileOutProfileDsField'.
			If disabled, no translation is performed." 
	DEFVAL		{ false }
        ::= { rc2kQosTrafficProfileEntry 4 }

rc2kQosTrafficProfileInProfileDsField OBJECT-TYPE
        SYNTAX        	INTEGER (0..64)
        MAX-ACCESS        	read-write
        STATUS        	current
        DESCRIPTION   	"Used to specify the DSCP field value for 'good' 
			packets.  A '0' value means leave the DSCP field
			unchanged."
        ::= { rc2kQosTrafficProfileEntry 5 }

rc2kQosTrafficProfileOutProfileDsField OBJECT-TYPE
        SYNTAX        	INTEGER (0..64)
        MAX-ACCESS        	read-write
        STATUS        	current
        DESCRIPTION   	"Used to specify the DSCP field value for 'violation' 
			packets.  A '0' value means leave the DSCP field
			unchanged."
        ::= { rc2kQosTrafficProfileEntry 6 }

rc2kQosTrafficProfileDiscardEnable OBJECT-TYPE
        SYNTAX        	TruthValue
        MAX-ACCESS        	read-write
        STATUS        	current
        DESCRIPTION   	"Used to specify whether packets that fall outside
			the traffic profile should be discarded."
	DEFVAL		{ true }
        ::= { rc2kQosTrafficProfileEntry 7 }

rc2kQosTrafficProfileAverageRate OBJECT-TYPE
        SYNTAX          Integer32
        MAX-ACCESS        	read-write
        STATUS        	current
        DESCRIPTION   	"Average rate in packets per second."
        ::= { rc2kQosTrafficProfileEntry 8 }

rc2kQosTrafficProfilePeakRate OBJECT-TYPE
        SYNTAX          Integer32
        MAX-ACCESS        	read-write
        STATUS        	current
        DESCRIPTION   	"Peak rate in packets per second."
        ::= { rc2kQosTrafficProfileEntry 9 }

rc2kQosTrafficProfileRowStatus OBJECT-TYPE
        SYNTAX        	RowStatus
        MAX-ACCESS        	read-write
        STATUS        	current
        DESCRIPTION   	"Used to create/delete entries."
        ::= { rc2kQosTrafficProfileEntry 10 }


-- rc2kAtm Group

rc2kAtm		OBJECT IDENTIFIER ::= { rc2k 9 }

rc2kAtmGlobal	OBJECT IDENTIFIER ::= { rc2kAtm 1 }


-- Atm Port Table

rc2kAtmPortTable OBJECT-TYPE
        SYNTAX        SEQUENCE OF Rc2kAtmPortEntry
        MAX-ACCESS        not-accessible
        STATUS        current
        DESCRIPTION   "ATM port table"
        ::= { rc2kAtm 2 }

rc2kAtmPortEntry OBJECT-TYPE
        SYNTAX        Rc2kAtmPortEntry
        MAX-ACCESS        not-accessible
        STATUS        current
        DESCRIPTION   "Entry containing infomation of ATM port"
        INDEX         { rc2kAtmPortIfIndex }
        ::= { rc2kAtmPortTable 1 }

Rc2kAtmPortEntry ::= SEQUENCE {
                rc2kAtmPortIfIndex InterfaceIndex,
                rc2kAtmPortIlmiEnable TruthValue,
                rc2kAtmPortSignalingEnable TruthValue,
                rc2kAtmPortUniVersion INTEGER,
                rc2kAtmPortNumVpiBits INTEGER,
                rc2kAtmPortNumVciBits INTEGER,
                rc2kAtmPortAddrPrefix AtmAddr,
                rc2kAtmPortMediaType INTEGER,
                rc2kAtmPortScrambleEnable TruthValue,
                rc2kAtmPortMediaType INTEGER,
                rc2kAtmPortFramingMode INTEGER,
                rc2kAtmPortClockSource INTEGER,
                rc2kAtmPortVpi INTEGER,
                rc2kAtmPortLoopBackMode INTEGER

        }

rc2kAtmPortIfIndex OBJECT-TYPE
        SYNTAX        InterfaceIndex
        MAX-ACCESS        read-only
        STATUS        current
        DESCRIPTION   "port number"
        ::= { rc2kAtmPortEntry 1 }

rc2kAtmPortIlmiEnable OBJECT-TYPE
        SYNTAX        TruthValue
        MAX-ACCESS        read-write
        STATUS        current
        DESCRIPTION   "enable ilmi"
        ::= { rc2kAtmPortEntry 2 }

rc2kAtmPortSignalingEnable OBJECT-TYPE
        SYNTAX        TruthValue
        MAX-ACCESS        read-write
        STATUS        current
        DESCRIPTION   "enable signaling"
        ::= { rc2kAtmPortEntry 3 }

rc2kAtmPortUniVersion OBJECT-TYPE
        SYNTAX        INTEGER {
                          uni30(1),
                          uni31(2),   
                          uni40(3)
                      }
        MAX-ACCESS        read-write
        STATUS        current
        DESCRIPTION   "uni version"
        ::= { rc2kAtmPortEntry 4 }

rc2kAtmPortNumVpiBits OBJECT-TYPE
        SYNTAX        INTEGER (1..8)
        MAX-ACCESS        read-write
        STATUS        current
        DESCRIPTION   "# of vpi bits"
        ::= { rc2kAtmPortEntry 5 }
 
rc2kAtmPortNumVciBits OBJECT-TYPE
        SYNTAX        INTEGER (1..16)
        MAX-ACCESS        read-write
        STATUS        current
        DESCRIPTION   "# of vci bits"
        ::= { rc2kAtmPortEntry 6 }

rc2kAtmPortAddrPrefix OBJECT-TYPE
        SYNTAX        AtmAddr
        MAX-ACCESS        read-write
        STATUS        current
        DESCRIPTION   "atm addr prefix"
        ::= { rc2kAtmPortEntry 7 }
 
rc2kAtmPortMediaType OBJECT-TYPE
        SYNTAX        INTEGER {
                          smf(1),	-- single mode fiber
                          mmf(2),	-- mixed mode fiber
                          copper(3)	-- copper
                      }
        MAX-ACCESS        read-only
        STATUS        current
        DESCRIPTION   "media type"
        ::= { rc2kAtmPortEntry 8 }
 
rc2kAtmPortScrambleEnable OBJECT-TYPE
        SYNTAX        TruthValue
        MAX-ACCESS        read-write
        STATUS        current
        DESCRIPTION   "enable scramble"
        ::= { rc2kAtmPortEntry 9 }
 
rc2kAtmPortFramingMode OBJECT-TYPE
        SYNTAX        INTEGER {
                          sonet(1),
                          sdh(2),
                          g751(3),
                          g832(4),
                          cbit(5),
                          cbitnofallback(6),
                          clearchannel(7)
                      }
        MAX-ACCESS        read-write
        STATUS        current
        DESCRIPTION   "port mode"
        ::= { rc2kAtmPortEntry 10 }
 
rc2kAtmPortClockSource OBJECT-TYPE
        SYNTAX        INTEGER {
                          loopTimed(1),
                          freeRunning(2)
                      }
        MAX-ACCESS        read-write
        STATUS        current
        DESCRIPTION   "clock source"
        ::= { rc2kAtmPortEntry 11 }
 
rc2kAtmPortVpi OBJECT-TYPE
        SYNTAX        INTEGER (1..256)
        MAX-ACCESS        read-write
        STATUS        current
        DESCRIPTION   "non-zero VC signaling"
        ::= { rc2kAtmPortEntry 12 }
 
rc2kAtmPortLoopBackMode OBJECT-TYPE
        SYNTAX        INTEGER { 
                          internal(1),
                          remote(2)
                      }
        MAX-ACCESS        read-write
        STATUS        current
        DESCRIPTION   "loop back mode"
        ::= { rc2kAtmPortEntry 13 }
 


-- Atm Pvc Table

rc2kAtmPvcTable OBJECT-TYPE
        SYNTAX        SEQUENCE OF Rc2kAtmPvcEntry
        MAX-ACCESS        not-accessible
        STATUS        current
        DESCRIPTION   "ATM Pvc table"
        ::= { rc2kAtm 3 }

rc2kAtmPvcEntry OBJECT-TYPE
        SYNTAX        Rc2kAtmPvcEntry
        MAX-ACCESS        not-accessible
        STATUS        current
        DESCRIPTION   "Entry containing infomation of ATM Pvc"
        INDEX         { rc2kAtmPvcIfIndex, rc2kAtmPvcVpi, rc2kAtmPvcVci }
        ::= { rc2kAtmPvcTable 1 }

Rc2kAtmPvcEntry ::= SEQUENCE {
                rc2kAtmPvcIfIndex InterfaceIndex,
                rc2kAtmPvcVpi INTEGER,
                rc2kAtmPvcVci INTEGER,
                rc2kAtmPvcPvcId INTEGER,
                rc2kAtmPvcName DisplayString,
                rc2kAtmPvcEnable TruthValue,
                rc2kAtmPvcEncapsulation INTEGER,
                rc2kAtmPvcServiceType INTEGER,
                rc2kAtmPvcPeakCellRate INTEGER,
                rc2kAtmPvcSustainedCellRate INTEGER,
                rc2kAtmPvcMaxBurstSize INTEGER,
                rc2kAtmPvcRowStatus RowStatus,
                rc2kAtmPvcMaxMtuSize INTEGER

        }

rc2kAtmPvcIfIndex OBJECT-TYPE
        SYNTAX        InterfaceIndex
        MAX-ACCESS        read-only
        STATUS        current
        DESCRIPTION   "port number"
        ::= { rc2kAtmPvcEntry 1 }

rc2kAtmPvcVpi OBJECT-TYPE
        SYNTAX        INTEGER (1..256)
        MAX-ACCESS        read-write
        STATUS        current
        DESCRIPTION   "vpi of this pvc"
        ::= { rc2kAtmPvcEntry 2 }

rc2kAtmPvcVci OBJECT-TYPE
        SYNTAX        INTEGER (1..64000)
        MAX-ACCESS        read-write
        STATUS        current
        DESCRIPTION   "vci of this pvc"
        ::= { rc2kAtmPvcEntry 3 }

rc2kAtmPvcPvcId OBJECT-TYPE
        SYNTAX        Integer32
        MAX-ACCESS        read-only
        STATUS        current
        DESCRIPTION   "internal pvc id"
        ::= { rc2kAtmPvcEntry 4 }

rc2kAtmPvcName OBJECT-TYPE
        SYNTAX        DisplayString
        MAX-ACCESS        read-write
        STATUS        current
        DESCRIPTION   "name of pvc"
        ::= { rc2kAtmPvcEntry 5 }
 
rc2kAtmPvcEnable OBJECT-TYPE
        SYNTAX        TruthValue
        MAX-ACCESS        read-write
        STATUS        current
        DESCRIPTION   "enable this entry"
        ::= { rc2kAtmPvcEntry 6 }

rc2kAtmPvcEncapsulation OBJECT-TYPE
        SYNTAX        INTEGER {
                          null(1),
                          llcSnap(2)
                      }
        MAX-ACCESS        read-write
        STATUS        current
        DESCRIPTION   "encapsulation"
        ::= { rc2kAtmPvcEntry 7 }
 
rc2kAtmPvcServiceType OBJECT-TYPE
        SYNTAX        INTEGER {
                          ubr(1),
                          vbr(2),
                          cbr(3)
                      }
        MAX-ACCESS        read-write
        STATUS        current
        DESCRIPTION   "service type"
        ::= { rc2kAtmPvcEntry 8 }
 
rc2kAtmPvcPeakCellRate OBJECT-TYPE
        SYNTAX        Integer32
        MAX-ACCESS        read-write
        STATUS        current
        DESCRIPTION   "peak cell rate"
        ::= { rc2kAtmPvcEntry 9 }
 
rc2kAtmPvcSustainedCellRate OBJECT-TYPE
        SYNTAX        Integer32
        MAX-ACCESS        read-write
        STATUS        current
        DESCRIPTION   "sustained cell rate"
        ::= { rc2kAtmPvcEntry 10 }

rc2kAtmPvcMaxBurstSize OBJECT-TYPE
        SYNTAX        Integer32
        MAX-ACCESS        read-write
        STATUS        current
        DESCRIPTION   "max burst size"
        ::= { rc2kAtmPvcEntry 11 }
 
rc2kAtmPvcRowStatus OBJECT-TYPE
        SYNTAX        RowStatus
        MAX-ACCESS        read-write
        STATUS        current
        DESCRIPTION   "row status"
        ::= { rc2kAtmPvcEntry 12 }

rc2kAtmPvcMaxMtuSize OBJECT-TYPE
        SYNTAX        Integer32
        MAX-ACCESS        read-write
        STATUS        current
        DESCRIPTION   "maximum MTU size"
        ::= { rc2kAtmPvcEntry 13 }

 
-- Atm LecElan Table

rc2kAtmLecElanTable OBJECT-TYPE
        SYNTAX        SEQUENCE OF Rc2kAtmLecElanEntry
        MAX-ACCESS        not-accessible
        STATUS        current
        DESCRIPTION   "ATM LecElan table"
        ::= { rc2kAtm 4 }

rc2kAtmLecElanEntry OBJECT-TYPE
        SYNTAX        Rc2kAtmLecElanEntry
        MAX-ACCESS        not-accessible
        STATUS        current
        DESCRIPTION   "Entry containing infomation of ATM LecElan"
        INDEX         { rc2kAtmLecElanIfIndex, rc2kAtmLecElanElanId }
        ::= { rc2kAtmLecElanTable 1 }

Rc2kAtmLecElanEntry ::= SEQUENCE {
                rc2kAtmLecElanIfIndex InterfaceIndex,
                rc2kAtmLecElanElanId INTEGER,
                rc2kAtmLecElanElanToJoin DisplayString,
                rc2kAtmLecElanName DisplayString,
                rc2kAtmLecElanEnable TruthValue,
                rc2kAtmLecElanVlanId INTEGER,
                rc2kAtmLecElanConfigMode INTEGER,
                rc2kAtmLecElanConfigLecs AtmAddr,
                rc2kAtmLecElanConfigLes AtmAddr,
                rc2kAtmLecElanActiveLecs AtmAddr,
                rc2kAtmLecElanActiveLes AtmAddr,
                rc2kAtmLecElanRowStatus RowStatus,
                rc2kAtmLecElanMaxMtuSize INTEGER

        }

rc2kAtmLecElanIfIndex OBJECT-TYPE
        SYNTAX        InterfaceIndex
        MAX-ACCESS        read-only
        STATUS        current
        DESCRIPTION   "port number"
        ::= { rc2kAtmLecElanEntry 1 }

rc2kAtmLecElanElanId OBJECT-TYPE
        SYNTAX        INTEGER (1..64000)
        MAX-ACCESS        read-only
        STATUS        current
        DESCRIPTION   "elan id"
        ::= { rc2kAtmLecElanEntry 2 }

rc2kAtmLecElanElanToJoin OBJECT-TYPE
        SYNTAX        DisplayString
        MAX-ACCESS        read-write
        STATUS        current
        DESCRIPTION   "name of elan to join"
        ::= { rc2kAtmLecElanEntry 3 }

rc2kAtmLecElanName OBJECT-TYPE
        SYNTAX        DisplayString
        MAX-ACCESS        read-write
        STATUS        current
        DESCRIPTION   "name of lec"
        ::= { rc2kAtmLecElanEntry 4 }

rc2kAtmLecElanEnable OBJECT-TYPE
        SYNTAX        TruthValue
        MAX-ACCESS        read-write
        STATUS        current
        DESCRIPTION   "enable this entry"
        ::= { rc2kAtmLecElanEntry 5 }

rc2kAtmLecElanVlanId OBJECT-TYPE
        SYNTAX        Integer32
        MAX-ACCESS        read-write
        STATUS        current
        DESCRIPTION   "vlan tag for this lec"
        ::= { rc2kAtmLecElanEntry 6 }
 
rc2kAtmLecElanConfigMode OBJECT-TYPE
        SYNTAX        INTEGER {
                          manual(1),
                          atm(2),
                          ilmi(3)
                      }
        MAX-ACCESS        read-write
        STATUS        current
        DESCRIPTION   "peak cell rate"
        ::= { rc2kAtmLecElanEntry 7 }
 
rc2kAtmLecElanConfigLecs OBJECT-TYPE
        SYNTAX        AtmAddr
        MAX-ACCESS        read-write
        STATUS        current
        DESCRIPTION   "addr of lecs"
        ::= { rc2kAtmLecElanEntry 8 }

rc2kAtmLecElanConfigLes OBJECT-TYPE
        SYNTAX        AtmAddr
        MAX-ACCESS        read-write
        STATUS        current
        DESCRIPTION   "addr of les"
        ::= { rc2kAtmLecElanEntry 9 }
 
rc2kAtmLecElanActiveLecs OBJECT-TYPE
        SYNTAX        AtmAddr
        MAX-ACCESS        read-only
        STATUS        current
        DESCRIPTION   "addr of lecs"
        ::= { rc2kAtmLecElanEntry 10 }
 
rc2kAtmLecElanActiveLes OBJECT-TYPE
        SYNTAX        AtmAddr
        MAX-ACCESS        read-only
        STATUS        current
        DESCRIPTION   "addr of les"
        ::= { rc2kAtmLecElanEntry 11 }
 
rc2kAtmLecElanRowStatus OBJECT-TYPE
        SYNTAX        RowStatus
        MAX-ACCESS        read-write
        STATUS        current
        DESCRIPTION   "row status"
        ::= { rc2kAtmLecElanEntry 12 }
 
rc2kAtmLecElanMaxMtuSize OBJECT-TYPE
        SYNTAX        Integer32
        MAX-ACCESS        read-write
        STATUS        current
        DESCRIPTION   "maximum MTU size"
        ::= { rc2kAtmLecElanEntry 13 }
 

-- Atm 1483Elan Table

rc2kAtm1483ElanTable OBJECT-TYPE
        SYNTAX        SEQUENCE OF Rc2kAtm1483ElanEntry
        MAX-ACCESS        not-accessible
        STATUS        current
        DESCRIPTION   "ATM 1483Elan table"
        ::= { rc2kAtm 5 }

rc2kAtm1483ElanEntry OBJECT-TYPE
        SYNTAX        Rc2kAtm1483ElanEntry
        MAX-ACCESS        not-accessible
        STATUS        current
        DESCRIPTION   "Entry containing infomation of ATM 1483Elan"
        INDEX         { rc2kAtm1483ElanIfIndex, rc2kAtm1483ElanElanId }
        ::= { rc2kAtm1483ElanTable 1 }

Rc2kAtm1483ElanEntry ::= SEQUENCE {
                rc2kAtm1483ElanIfIndex InterfaceIndex,
                rc2kAtm1483ElanElanId INTEGER,
                rc2kAtm1483ElanEnable TruthValue,
                rc2kAtm1483ElanPerformTagging TruthValue,
                rc2kAtm1483ElanNumPvcIds INTEGER,
                rc2kAtm1483ElanPvcIds IdList,
                rc2kAtm1483ElanNumVlanIds INTEGER,
                rc2kAtm1483ElanVlanIds IdList,
                rc2kAtm1483ElanRowStatus RowStatus,
                rc2kAtm1483ElanConnectType INTEGER,
                rc2kAtm1483ElanVlanMacAddress MacAddress,
                rc2kAtm1483ElanDummyMacAddress MacAddress,
                rc2kAtm1483ElanLocalIpAddress IpAddress,
                rc2kAtm1483ElanRemoteIpAddress IpAddress,
                rc2kAtm1483ElanArpSendEnable TruthValue,
                rc2kAtm1483ElanInArpSendInterval INTEGER,
                rc2kAtm1483ElanIpxVlanEncapMethod INTEGER,
                rc2kAtm1483ElanIpxNetworkNum INTEGER

        }

rc2kAtm1483ElanIfIndex OBJECT-TYPE
        SYNTAX        InterfaceIndex
        MAX-ACCESS        read-only
        STATUS        current
        DESCRIPTION   "port number"
        ::= { rc2kAtm1483ElanEntry 1 }

rc2kAtm1483ElanElanId OBJECT-TYPE
        SYNTAX        INTEGER (1..64000)
        MAX-ACCESS        read-only
        STATUS        current
        DESCRIPTION   "elan id"
        ::= { rc2kAtm1483ElanEntry 2 }

rc2kAtm1483ElanEnable OBJECT-TYPE
        SYNTAX        TruthValue
        MAX-ACCESS        read-write
        STATUS        current
        DESCRIPTION   "enable this entry"
        ::= { rc2kAtm1483ElanEntry 3 }

rc2kAtm1483ElanPerformTagging OBJECT-TYPE
        SYNTAX        TruthValue
        MAX-ACCESS        read-write
        STATUS        current
        DESCRIPTION   "perform tagging"
        ::= { rc2kAtm1483ElanEntry 4 }

rc2kAtm1483ElanNumPvcIds OBJECT-TYPE
        SYNTAX        Integer32
        MAX-ACCESS        read-only
        STATUS        current
        DESCRIPTION   "# pvcs in list"
        ::= { rc2kAtm1483ElanEntry 5 }
 
rc2kAtm1483ElanPvcIds OBJECT-TYPE
        SYNTAX        IdList
        MAX-ACCESS        read-write
        STATUS        current
        DESCRIPTION   "list of pvcs. 32 bits/pvc.
                       refer to rc2kAtmPvcEntryPvcId"
        ::= { rc2kAtm1483ElanEntry 6 }
 
rc2kAtm1483ElanNumVlanIds OBJECT-TYPE
        SYNTAX        Integer32
        MAX-ACCESS        read-only
        STATUS        current
        DESCRIPTION   "# of vlans in list"
        ::= { rc2kAtm1483ElanEntry 7 }
 
rc2kAtm1483ElanVlanIds OBJECT-TYPE
        SYNTAX        IdList
        MAX-ACCESS        read-write
        STATUS        current
        DESCRIPTION   "list of vlans. 16 bits/vlan
                       refer to rcVlanId"
        ::= { rc2kAtm1483ElanEntry 8 }
 
rc2kAtm1483ElanRowStatus OBJECT-TYPE
        SYNTAX        RowStatus
        MAX-ACCESS        read-write
        STATUS        current
        DESCRIPTION   "row status"
        ::= { rc2kAtm1483ElanEntry 9 }
 
rc2kAtm1483ElanConnectType OBJECT-TYPE
        SYNTAX        INTEGER {
                          other(0),
                          ip(1),
                          ipx(2)
                      }
        MAX-ACCESS        read-only
        STATUS        current
        DESCRIPTION   "connection type"
        ::= { rc2kAtm1483ElanEntry 10 }
 
rc2kAtm1483ElanVlanMacAddress OBJECT-TYPE
        SYNTAX        MacAddress
        MAX-ACCESS        read-only
        STATUS        current
        DESCRIPTION   "mac for vlan"
        ::= { rc2kAtm1483ElanEntry 11 }
 
rc2kAtm1483ElanDummyMacAddress OBJECT-TYPE
        SYNTAX        MacAddress
        MAX-ACCESS        read-only
        STATUS        current
        DESCRIPTION   "dummy mac for the other router"
        ::= { rc2kAtm1483ElanEntry 12 }
 
rc2kAtm1483ElanLocalIpAddress OBJECT-TYPE
        SYNTAX        IpAddress
        MAX-ACCESS        read-only
        STATUS        current
        DESCRIPTION   "local ip, if ConnectType is ip(2)"
        ::= { rc2kAtm1483ElanEntry 13 }
 
rc2kAtm1483ElanRemoteIpAddress OBJECT-TYPE
        SYNTAX        IpAddress
        MAX-ACCESS        read-write
        STATUS        current
        DESCRIPTION   "remote ip, if ConnectType is ip(2)"
        ::= { rc2kAtm1483ElanEntry 14 }
 
rc2kAtm1483ElanArpSendEnable OBJECT-TYPE
        SYNTAX        TruthValue
        MAX-ACCESS        read-write
        STATUS        current
        DESCRIPTION   "enable arp sending on the port"
        ::= { rc2kAtm1483ElanEntry 15 }
 
rc2kAtm1483ElanInArpSendInterval OBJECT-TYPE
        SYNTAX        INTEGER (1..60)
        MAX-ACCESS        read-write
        STATUS        current
        DESCRIPTION   "interval of arp sending on the port"
        ::= { rc2kAtm1483ElanEntry 16 }

rc2kAtm1483ElanIpxVlanEncapMethod OBJECT-TYPE
        SYNTAX        INTEGER {
                          other(0),
                          llc(1),
                          snap(2),
                          ether-ii(3),
                          raw(4)
                      }
        MAX-ACCESS        read-write
        STATUS        current
        DESCRIPTION   "vlan encapsulayion method"
        ::= { rc2kAtm1483ElanEntry 17 }
 
rc2kAtm1483ElanIpxNetworkNum OBJECT-TYPE
        SYNTAX        Integer32
        MAX-ACCESS        read-write
        STATUS        current
        DESCRIPTION   "network number, if ConnectType is ipx(3)"
        ::= { rc2kAtm1483ElanEntry 18 }


-- Atm PvcStat Table

rc2kAtmPvcStatTable OBJECT-TYPE
        SYNTAX        SEQUENCE OF Rc2kAtmPvcStatEntry
        MAX-ACCESS        not-accessible
        STATUS        current
        DESCRIPTION   "ATM PvcStat table"
        ::= { rc2kAtm 6 }

rc2kAtmPvcStatEntry OBJECT-TYPE
        SYNTAX        Rc2kAtmPvcStatEntry
        MAX-ACCESS        not-accessible
        STATUS        current
        DESCRIPTION   "Entry containing infomation of ATM PvcStat"
        INDEX         { rc2kAtmPvcStatIfIndex, rc2kAtmPvcStatVpi, rc2kAtmPvcStatVci }
        ::= { rc2kAtmPvcStatTable 1 }

Rc2kAtmPvcStatEntry ::= SEQUENCE {
                rc2kAtmPvcStatIfIndex InterfaceIndex,
                rc2kAtmPvcStatVpi INTEGER,
                rc2kAtmPvcStatVci INTEGER,
                rc2kAtmPvcStatInCell Counter64,
                rc2kAtmPvcStatOutCell Counter64,
                rc2kAtmPvcStatInMultiCell Counter64,
                rc2kAtmPvcStatOutMultiCell Counter64

        }

rc2kAtmPvcStatIfIndex OBJECT-TYPE
        SYNTAX        InterfaceIndex
        MAX-ACCESS        read-only
        STATUS        current
        DESCRIPTION   "port number"
        ::= { rc2kAtmPvcStatEntry 1 }

rc2kAtmPvcStatVpi OBJECT-TYPE
        SYNTAX        INTEGER (1..256)
        MAX-ACCESS        read-only
        STATUS        current
        DESCRIPTION   "vpi of this pvc"
        ::= { rc2kAtmPvcStatEntry 2 }

rc2kAtmPvcStatVci OBJECT-TYPE
        SYNTAX        INTEGER (1..64000)
        MAX-ACCESS        read-only
        STATUS        current
        DESCRIPTION   "vci of this pvc"
        ::= { rc2kAtmPvcStatEntry 3 }

rc2kAtmPvcStatInCell OBJECT-TYPE
        SYNTAX        Counter64
        MAX-ACCESS        read-only
        STATUS        current
        DESCRIPTION   "# in cells"
        ::= { rc2kAtmPvcStatEntry 4 }

rc2kAtmPvcStatOutCell OBJECT-TYPE
        SYNTAX        Counter64
        MAX-ACCESS        read-only
        STATUS        current
        DESCRIPTION   "# out cells"
        ::= { rc2kAtmPvcStatEntry 5 }

rc2kAtmPvcStatInMultiCell OBJECT-TYPE
        SYNTAX        Counter64
        MAX-ACCESS        read-only
        STATUS        current
        DESCRIPTION   "# in multicast cells"
        ::= { rc2kAtmPvcStatEntry 6 }
 
rc2kAtmPvcStatOutMultiCell OBJECT-TYPE
        SYNTAX        Counter64
        MAX-ACCESS        read-only
        STATUS        current
        DESCRIPTION   "# out multicast cells"
        ::= { rc2kAtmPvcStatEntry 7 }
 
-- Atm Svc Table

rc2kAtmSvcTable OBJECT-TYPE
        SYNTAX        SEQUENCE OF Rc2kAtmSvcEntry
        MAX-ACCESS        not-accessible
        STATUS        current
        DESCRIPTION   "ATM Svc table"
        ::= { rc2kAtm 7 }

rc2kAtmSvcEntry OBJECT-TYPE
        SYNTAX        Rc2kAtmSvcEntry
        MAX-ACCESS        not-accessible
        STATUS        current
        DESCRIPTION   "Entry containing infomation of ATM Svc"
        INDEX         { rc2kAtmSvcIfIndex, rc2kAtmSvcVpi, rc2kAtmSvcVci }
        ::= { rc2kAtmSvcTable 1 }

Rc2kAtmSvcEntry ::= SEQUENCE {
                rc2kAtmSvcIfIndex InterfaceIndex,
                rc2kAtmSvcVpi INTEGER,
                rc2kAtmSvcVci INTEGER,
                rc2kAtmSvcServiceType INTEGER,
                rc2kAtmSvcPeakCellRate INTEGER,
                rc2kAtmSvcSustainedCellRate INTEGER,
                rc2kAtmSvcMaxBurstSize INTEGER

        }

rc2kAtmSvcIfIndex OBJECT-TYPE
        SYNTAX        InterfaceIndex
        MAX-ACCESS        read-only
        STATUS        current
        DESCRIPTION   "port number"
        ::= { rc2kAtmSvcEntry 1 }

rc2kAtmSvcVpi OBJECT-TYPE
        SYNTAX        INTEGER (1..256)
        MAX-ACCESS        read-only
        STATUS        current
        DESCRIPTION   "vpi of this pvc"
        ::= { rc2kAtmSvcEntry 2 }

rc2kAtmSvcVci OBJECT-TYPE
        SYNTAX        INTEGER (1..64000)
        MAX-ACCESS        read-only
        STATUS        current
        DESCRIPTION   "vci of this pvc"
        ::= { rc2kAtmSvcEntry 3 }

rc2kAtmSvcServiceType OBJECT-TYPE
        SYNTAX        INTEGER {
                          ubr(1),
                          vbr(2),
                          cbr(3)
                      }
        MAX-ACCESS        read-only
        STATUS        current
        DESCRIPTION   "service type"
        ::= { rc2kAtmSvcEntry 4 }

rc2kAtmSvcPeakCellRate OBJECT-TYPE
        SYNTAX        Integer32
        MAX-ACCESS        read-only
        STATUS        current
        DESCRIPTION   "peak cell rate"
        ::= { rc2kAtmSvcEntry 5 }

rc2kAtmSvcSustainedCellRate OBJECT-TYPE
        SYNTAX        Integer32
        MAX-ACCESS        read-only
        STATUS        current
        DESCRIPTION   "sustained cell rate"
        ::= { rc2kAtmSvcEntry 6 }
 
rc2kAtmSvcMaxBurstSize OBJECT-TYPE
        SYNTAX        Integer32
        MAX-ACCESS        read-only
        STATUS        current
        DESCRIPTION   "max burst size"
        ::= { rc2kAtmSvcEntry 7 }
 
-- 2k Mda

rc2kMdaCardTable OBJECT-TYPE
        SYNTAX        SEQUENCE OF Rc2kMdaCardEntry
        MAX-ACCESS        not-accessible
        STATUS        current
        DESCRIPTION   "Mda card table"
        ::= { rc2k 10 }

rc2kMdaCardEntry OBJECT-TYPE
        SYNTAX        Rc2kMdaCardEntry
        MAX-ACCESS        not-accessible
        STATUS        current
        DESCRIPTION   "Entry containing infomation of Mda card"
        INDEX         { rc2kMdaCardSlotNum, rc2kMdaCardMdaNum }
        ::= { rc2kMdaCardTable 1 }

Rc2kMdaCardEntry ::= SEQUENCE {
                rc2kMdaCardSlotNum INTEGER,
                rc2kMdaCardMdaNum INTEGER,
                rc2kMdaCardType INTEGER,
                rc2kMdaCardDescription DisplayString,
                rc2kMdaCardAdminStatus INTEGER,
                rc2kMdaCardOperStatus INTEGER,
                rc2kMdaCardSerialNum DisplayString,
                rc2kMdaCardHwVersion DisplayString,
                rc2kMdaCardPartNumber DisplayString,
                rc2kMdaCardDateCode DisplayString,
                rc2kMdaCardDeviations DisplayString,
                rc2kMdaCardMacAddr MacAddress,
                rc2kMdaCardNumPorts INTEGER,
                rc2kMdaCardFirstIfIndex InterfaceIndex,
                rc2kMdaCardLastIfIndex InterfaceIndex
        }

rc2kMdaCardSlotNum OBJECT-TYPE
        SYNTAX        INTEGER (1..10)
        MAX-ACCESS        read-only
        STATUS        current
        DESCRIPTION   "Slot number"
        ::= { rc2kMdaCardEntry 1 }

rc2kMdaCardMdaNum OBJECT-TYPE
        SYNTAX        	INTEGER (1..4)
        MAX-ACCESS        	read-only
        STATUS        	current
        DESCRIPTION   	"MDA number within slot.  MDAs are numbered
			from left to right."
        ::= { rc2kMdaCardEntry 2 }

rc2kMdaCardType OBJECT-TYPE
        SYNTAX        	INTEGER 
			{
        other(1),                        -- no card installed
	rc2k4x100BaseTX(807469572),	 -- 0011 0000 0010 0001 0000 0010 0000 0100
	rc2k2x100BaseFX(808518146),	 -- 0011 0000 0011 0001 0000 0010 0000 0010 
	rc2k4x100BaseFX(808518148),	 -- 0011 0000 0011 0001 0000 0010 0000 0100
	rc2k1x1000BaseSXBB(808583681),	 -- 0011 0000 0011 0010 0000 0010 0000 0001	
	rc2k1x1000BaseSXRBB(808616449),	 -- 0011 0000 0011 0010 1000 0010 0000 0001 
	rc2k1x1000BaseLXBB(808591873),	 -- 0011 0000 0011 0010 0010 0010 0000 0001
	rc2k1x1000BaseLXRBB(808624641),  -- 0011 0000 0011 0010 1010 0010 0000 0001
        rc2k4xOc3cBaseSM(542380548),	 -- 0010 0000 0101 0100 0001 0010 0000 0100
        rc2k4xOc3cBaseMM(542376452),	 -- 0010 0000 0101 0100 0000 0010 0000 0100
        rc2k4xOc3cBaseCOPPER(542388740), -- 0010 0000 0101 0100 0011 0010 0000 0100
        rc2k1x0c12cBaseSM(542446081),	 -- 0010 0000 0101 0101 0001 0010 0000 0001
        rc2k1x0c12cBaseMM(542441985),	 -- 0010 0000 0101 0101 0000 0010 0000 0001
        rc2k2xDs3(542970370),		 -- 0010 0000 0101 1101 0001 0010 0000 0010
        rc2k2xE3(542839298) 		 -- 0010 0000 0101 1011 0001 0010 0000 0010
			}
        MAX-ACCESS        	read-only
        STATUS        	current
        DESCRIPTION   	"Refer to rc2kCardFrontType for the encoding scheme"
        ::= { rc2kMdaCardEntry 3 }

rc2kMdaCardDescription OBJECT-TYPE
        SYNTAX        DisplayString
        MAX-ACCESS        read-only
        STATUS        current
        DESCRIPTION   "description of mda card"
        ::= { rc2kMdaCardEntry 4 }
 
rc2kMdaCardAdminStatus OBJECT-TYPE
        SYNTAX        INTEGER {
                            up(0),
                            down(1),
                            testing(2),
                            unknown(3)
                      }
        MAX-ACCESS        read-write
        STATUS        current
        DESCRIPTION   "administration status of mda card"
        ::= { rc2kMdaCardEntry 5 }

rc2kMdaCardOperStatus OBJECT-TYPE
        SYNTAX        INTEGER {
                            up(0),
                            down(1),
                            testing(2),
                            unknown(3)
                      }
        MAX-ACCESS        read-only
        STATUS        current
        DESCRIPTION   "operation status of mda card."
        ::= { rc2kMdaCardEntry 6 }

rc2kMdaCardSerialNum OBJECT-TYPE
        SYNTAX        DisplayString
        MAX-ACCESS        read-only
        STATUS        current
        DESCRIPTION   "serial number of mad card"
        ::= { rc2kMdaCardEntry 7 }
 
rc2kMdaCardHwVersion OBJECT-TYPE
        SYNTAX        DisplayString
        MAX-ACCESS        read-only
        STATUS        current
        DESCRIPTION   "hardware version of mda card"
        ::= { rc2kMdaCardEntry 8 }
 
rc2kMdaCardPartNumber OBJECT-TYPE
        SYNTAX        DisplayString
        MAX-ACCESS        read-only
        STATUS        current
        DESCRIPTION   "part number of mda card"
        ::= { rc2kMdaCardEntry 9 }
 
rc2kMdaCardDateCode OBJECT-TYPE
        SYNTAX        DisplayString
        MAX-ACCESS        read-only
        STATUS        current
        DESCRIPTION   "date code of mda card"
        ::= { rc2kMdaCardEntry 10 }
 
rc2kMdaCardDeviations OBJECT-TYPE
        SYNTAX        DisplayString
        MAX-ACCESS        read-only
        STATUS        current
        DESCRIPTION   "hardware deviation infomation of mda card"
        ::= { rc2kMdaCardEntry 11 }
 
rc2kMdaCardMacAddr OBJECT-TYPE
        SYNTAX        MacAddress
        MAX-ACCESS        read-only
        STATUS        current
        DESCRIPTION   "base mac address of mda card"
        ::= { rc2kMdaCardEntry 12 }

rc2kMdaCardNumPorts OBJECT-TYPE
        SYNTAX        Integer32
        MAX-ACCESS        read-only
        STATUS        current
        DESCRIPTION   "number of ports on mda card"
        ::= { rc2kMdaCardEntry 13 }

rc2kMdaCardFirstIfIndex OBJECT-TYPE
        SYNTAX        InterfaceIndex
        MAX-ACCESS        read-only
        STATUS        current
        DESCRIPTION   "first ifindex number on mda card"
        ::= { rc2kMdaCardEntry 14 }

rc2kMdaCardLastIfIndex OBJECT-TYPE
        SYNTAX        InterfaceIndex
        MAX-ACCESS        read-only
        STATUS        current
        DESCRIPTION   "last ifindex number on mda card"
        ::= { rc2kMdaCardEntry 15 }

-- SSH Group
-- SSH Global Information. All requires RWA access.

rcSshGlobal   OBJECT IDENTIFIER        ::= { rcSsh 1 }

rcSshGlobalVersion OBJECT-TYPE
     SYNTAX       INTEGER {
                         v2only(1),
                         both(2)
                      }
     MAX-ACCESS       read-write
     STATUS       current
     DESCRIPTION  "SSH version"
     DEFVAL       { v2only }
     ::= { rcSshGlobal 1 }

rcSshGlobalPort OBJECT-TYPE
     SYNTAX       INTEGER (1..65535)
     MAX-ACCESS       read-write
     STATUS       current
     DESCRIPTION  "SSH connection port."
     DEFVAL       { 22 }
     ::= { rcSshGlobal 2 }

rcSshGlobalMaxSession OBJECT-TYPE
     SYNTAX       INTEGER (0..8)
     MAX-ACCESS       read-write
     STATUS       current
     DESCRIPTION  "Number of session allowed."
     DEFVAL       { 4 }
     ::= { rcSshGlobal 3 }

rcSshGlobalTimeout OBJECT-TYPE
     SYNTAX       INTEGER (1..120)
     MAX-ACCESS       read-write
     STATUS       current
     DESCRIPTION  "SSH connection timeout in seconds."
     DEFVAL       { 60 }
     ::= { rcSshGlobal 4 }

rcSshGlobalRsaKeySize OBJECT-TYPE
     SYNTAX       INTEGER (512..1024)
     MAX-ACCESS       read-write
     STATUS       current
     DESCRIPTION  "SSH Rsa key size."
     DEFVAL       { 1024 }
     ::= { rcSshGlobal 5 }

rcSshGlobalDsaKeySize OBJECT-TYPE
     SYNTAX       INTEGER (512..1024)
     MAX-ACCESS       read-write
     STATUS       current
     DESCRIPTION  "SSH Dsa key size."
     DEFVAL       { 1024 }
     ::= { rcSshGlobal 6 }

rcSshGlobalRsaAuth OBJECT-TYPE
     SYNTAX       TruthValue
     MAX-ACCESS       read-write
     STATUS       current
     DESCRIPTION  "Enable/disable SSH RSA authentication"
     DEFVAL       { true }
     ::= { rcSshGlobal 7 }

rcSshGlobalDsaAuth OBJECT-TYPE
     SYNTAX       TruthValue
     MAX-ACCESS       read-write
     STATUS       current
     DESCRIPTION  "Enable/disable SSH DSA authentication"
     DEFVAL       { true }
     ::= { rcSshGlobal 8 }

rcSshGlobalPassAuth OBJECT-TYPE
     SYNTAX       TruthValue
     MAX-ACCESS       read-write
     STATUS       current
     DESCRIPTION  "Enable/disable SSH RSA authentication"
     DEFVAL       { true }
     ::= { rcSshGlobal 9 }

rcSshGlobalKeyAction OBJECT-TYPE
     SYNTAX       INTEGER  {
                         generateDsa(1),
                         generateRsa(2),
                         deleteDsa(3),
                         deleteRsa(4)
                      }
     MAX-ACCESS       read-write
     STATUS       current
     DESCRIPTION  "SSH key action."
     ::= { rcSshGlobal 10 }

rcSshGlobalEnable OBJECT-TYPE
     SYNTAX       INTEGER {
                         false(0),
                         true(1),
                         secure(2)
                      }
     MAX-ACCESS       read-write
     STATUS       current
     DESCRIPTION  "Enable/disable, or securely enable SSH. Securely enable
                   turns off other daemon flag, and it takes ffect afte reboot"
     DEFVAL       { false }
     ::= { rcSshGlobal 11 }

END
