-- *****************************************************************
-- Meru Networks Enterprise Specific MIB
--
-- Copyright (c) 2005 by Meru Networks
-- All rights reserved
--
-- *****************************************************************

MERU-CONFIG-VLAN-MIB  DEFINITIONS ::= BEGIN

IMPORTS
    NOTIFICATION-TYPE, 
    OBJECT-TYPE, 
    MODULE-IDENTITY, 
    OBJECT-IDENTITY,
    enterprises, 
    Counter32, 
    Counter64, 
    Gauge32, 
    TimeTicks, 
    IpAddress, 
    Integer32
        FROM SNMPv2-SMI
    Ipv6Address
        FROM IPV6-TC
    TEXTUAL-CONVENTION, 
    TimeInterval, 
    TimeStamp,
    DateAndTime, 
    TruthValue, 
    DisplayString, 
    MacAddress, 
    RowStatus
        FROM SNMPv2-TC
    mwConfiguration
        FROM MERU-SMI
    MwlOnOffSwitch,
    MwlProfileOwner
        FROM MERU-TC;

  mwConfigVlan  MODULE-IDENTITY
    LAST-UPDATED "200506050000Z"
    ORGANIZATION "Meru Networks"
    CONTACT-INFO "support@merunetworks.com"
    DESCRIPTION
        "This MIB defines all the managed objects used to manage the Meru WLAN 
         VLAN Configuration infrastructure"
    ::= { mwConfiguration 5 } 
  
    
  
  mwVlanTable  OBJECT-TYPE
    SYNTAX SEQUENCE OF MwVlanEntry
    MAX-ACCESS not-accessible
    STATUS     current
    DESCRIPTION
         "This object describes VLAN Configuration "
    ::= { mwConfigVlan 1 }

  mwVlanEntry  OBJECT-TYPE
    SYNTAX MwVlanEntry
    MAX-ACCESS not-accessible
    STATUS     current
    DESCRIPTION
         "This object describes VLAN Configuration "
    INDEX {  mwVlanTableIndex  }
    ::= { mwVlanTable 1 }

  MwVlanEntry  ::=  SEQUENCE { 
       mwVlanTableIndex                                            Integer32, 
       mwVlanTag                                                   Unsigned32,
       mwVlanName                                                  DisplayString(SIZE (1..32)),
       mwVlanNetMask                                               IpAddress,
       mwVlanIpAddress                                             IpAddress,
       mwVlanInterfaceIndex                                        Unsigned32,
       mwVlanDefaultGateway                                        IpAddress,
       mwVlanDHCPServerIpAddress                                   IpAddress,
       mwVlanDhcpRelayPassThroughFlag                              MwlOnOffSwitch,
       mwVlanOverrideDefaultDHCPServer                             MwlOnOffSwitch,
       mwVlanOwner                                                 MwlProfileOwner,
       mwVlanRowStatus                                             RowStatus 
  }
   
   
  mwVlanTableIndex  OBJECT-TYPE
    SYNTAX Integer32 
    MAX-ACCESS not-accessible 
    STATUS     current
    DESCRIPTION
         "The index value of the  table "
    ::= { mwVlanEntry 1 }

  mwVlanTag  OBJECT-TYPE
    SYNTAX Unsigned32
    MAX-ACCESS read-create
    STATUS     current
    DESCRIPTION
         "This object describes Tag"
    ::= { mwVlanEntry    2 }

  mwVlanName  OBJECT-TYPE
    SYNTAX DisplayString(SIZE (1..32))
    MAX-ACCESS read-create
    STATUS     current
    DESCRIPTION
         "This object describes VLAN Name"
    ::= { mwVlanEntry    3 }

  mwVlanNetMask  OBJECT-TYPE
    SYNTAX IpAddress
    MAX-ACCESS read-create
    STATUS     current
    DESCRIPTION
         "This object describes Netmask"
    ::= { mwVlanEntry    4 }

  mwVlanIpAddress  OBJECT-TYPE
    SYNTAX IpAddress
    MAX-ACCESS read-create
    STATUS     current
    DESCRIPTION
         "This object describes IP Address"
    ::= { mwVlanEntry    5 }

  mwVlanInterfaceIndex  OBJECT-TYPE
    SYNTAX Unsigned32
    MAX-ACCESS read-create
    STATUS     current
    DESCRIPTION
         "This object describes Fast Ethernet Interface Index"
    ::= { mwVlanEntry    6 }

  mwVlanDefaultGateway  OBJECT-TYPE
    SYNTAX IpAddress
    MAX-ACCESS read-create
    STATUS     current
    DESCRIPTION
         "This object describes IP Address of the Default Gateway"
    ::= { mwVlanEntry    7 }

  mwVlanDHCPServerIpAddress  OBJECT-TYPE
    SYNTAX IpAddress
    MAX-ACCESS read-create
    STATUS     current
    DESCRIPTION
         "This object describes DHCP Server IP Address"
    ::= { mwVlanEntry    8 }

  mwVlanDhcpRelayPassThroughFlag  OBJECT-TYPE
    SYNTAX MwlOnOffSwitch
    MAX-ACCESS read-create
    STATUS     current
    DESCRIPTION
         "This object describes DHCP Relay Pass-Through"
    ::= { mwVlanEntry    9 }

  mwVlanOverrideDefaultDHCPServer  OBJECT-TYPE
    SYNTAX MwlOnOffSwitch
    MAX-ACCESS read-create
    STATUS     current
    DESCRIPTION
         "This object describes Override Default DHCP Server Flag"
    ::= { mwVlanEntry   10 }

  mwVlanOwner  OBJECT-TYPE
    SYNTAX MwlProfileOwner
    MAX-ACCESS read-only
    STATUS     current
    DESCRIPTION
         "This object describes Owner"
    ::= { mwVlanEntry   11 }

  mwVlanRowStatus  OBJECT-TYPE
    SYNTAX RowStatus
    MAX-ACCESS read-create
    STATUS     current
    DESCRIPTION
         "This object is used to create and delete rows in the table"
    ::= { mwVlanEntry 14 }

  
END
