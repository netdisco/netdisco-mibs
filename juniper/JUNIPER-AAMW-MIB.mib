-- *******************************************************************
-- Juniper AAMW objects MIB.
--
-- Copyright (c) 2020, Juniper Networks, Inc.
-- All rights reserved.
--
-- The contents of this document are subject to change without notice.
-- *******************************************************************

    JUNIPER-AAMW-MIB DEFINITIONS ::= BEGIN

    IMPORTS
        Integer32,
        NOTIFICATION-TYPE,
        MODULE-IDENTITY, OBJECT-TYPE   FROM SNMPv2-SMI
        DisplayString                  FROM SNMPv2-TC
        jnxJsAAMW                      FROM JUNIPER-JS-SMI;

    jnxJsAAMWMib    MODULE-IDENTITY
        LAST-UPDATED "202009020000Z"
        ORGANIZATION  "Juniper Networks, Inc."
        CONTACT-INFO
            "Juniper Technical Assistance Center
             Juniper Networks, Inc.
             1133 Innovation Way
             Sunnyvale, CA 94089

             E-mail: support@juniper.net
             HTTP://www.juniper.net"
        DESCRIPTION
            "This module defines the objects pertaining to Advanced Anti-Malware"
        REVISION      "202009020000Z"
        DESCRIPTION   "Creation Date"
        ::= { jnxJsAAMW 1 }


    jnxJsAAMWNotifications OBJECT IDENTIFIER ::= { jnxJsAAMWMib 0 }
    jnxJsAAMWObjects       OBJECT IDENTIFIER ::= { jnxJsAAMWMib 1 }


    -- ***************************************************************
    --  Next Branch node.
    -- ***************************************************************

    jnxJsAAMWTrapVars           OBJECT IDENTIFIER ::= { jnxJsAAMWObjects 1 }

    -- ********************************************************************
    -- Objects used for the traps
    -- ********************************************************************
    jnxJsAAMWChannelType   OBJECT-TYPE
        SYNTAX      DisplayString
        MAX-ACCESS  accessible-for-notify
        STATUS      current
        DESCRIPTION
            "The Channel Type of Advanced Anti-Malware to-cloud connection."
        ::= { jnxJsAAMWTrapVars 1 }


    --
    -- AAMW Channel is UP
    --
    jnxJsAAMWChannelUp NOTIFICATION-TYPE
        OBJECTS         { jnxJsAAMWChannelType }
        STATUS          current
        DESCRIPTION
            "An Advanced Anti-Malware Channel Up trap signifies that
             AAMW to-cloud connection is up."
        ::= { jnxJsAAMWNotifications 1 }


    --
    -- AAMW Channel is Down
    --
    jnxJsAAMWChannelDown NOTIFICATION-TYPE
        OBJECTS         { jnxJsAAMWChannelType }
        STATUS          current
        DESCRIPTION
            "An Advanced Anti-Malware Channel Down trap signifies that
             AAMW to-cloud connection is down."
        ::= { jnxJsAAMWNotifications 2 }

END
