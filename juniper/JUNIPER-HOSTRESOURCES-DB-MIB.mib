JUNIPER-HOSTRESOURCES-DB-MIB DEFINITIONS ::= BEGIN


IMPORTS
    MODULE-IDENTITY, OBJECT-TYPE, Gauge32, Unsigned32
        FROM SNMPv2-SMI
    jnxHostResourcesMIB
        FROM JUNIPER-HOSTRESOURCES-MIB;

jnxHostResourcesDBMIB  MODULE-IDENTITY
        LAST-UPDATED "202412020000Z" -- Dec 02, 2024
        ORGANIZATION "Juniper Networks, Inc."
        CONTACT-INFO
                "        Juniper Technical Assistance Center
                     Juniper Networks, Inc.
                     1133 Innovation Way
                     Sunnyvale, CA 94089
                     E-mail: support@juniper.net"

        DESCRIPTION
                "Extends the HOST-RESOURCES-MIB for config DB storage."

        -- revision history
        REVISION  "202412020000Z"
        DESCRIPTION
                "Initial revision."

        ::= { jnxHostResourcesMIB 3 }

jnxDbStorage OBJECT IDENTIFIER ::= { jnxHostResourcesDBMIB 1 }

 dbStorageMaxSize OBJECT-TYPE
       SYNTAX     Unsigned32 (1..4294967295)
       UNITS      "Bytes"
       MAX-ACCESS read-only
       STATUS     current
       DESCRIPTION
           "The value of the maximum size of the database."
       ::= { jnxDbStorage 1 }

 dbStorageCurSize OBJECT-TYPE
     SYNTAX     Unsigned32 (1..4294967295)
     UNITS      "Bytes"
     MAX-ACCESS read-only
     STATUS     current
     DESCRIPTION
         "The value of the current database size on disk."
     ::= { jnxDbStorage 2 }

 dbStorageUsageSpace OBJECT-TYPE
     SYNTAX     Unsigned32 (1..4294967295)
     UNITS      "Bytes"
     MAX-ACCESS read-only
     STATUS     current
     DESCRIPTION
         "The value of the actual database usage."
     ::= { jnxDbStorage 3 }

 dbStorageAvailableSpace OBJECT-TYPE
       SYNTAX     Unsigned32 (1..4294967295)
       UNITS      "Bytes"
       MAX-ACCESS read-only
       STATUS     current
       DESCRIPTION
           "The value of the available database space."
       ::= { jnxDbStorage 4 }

END
