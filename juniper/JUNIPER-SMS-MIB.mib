-- *******************************************************************
-- Juniper SMS objects MIB.
--
-- Copyright (c) 2020, Juniper Networks, Inc.
-- All rights reserved.
--
-- The contents of this document are subject to change without notice.
-- *******************************************************************

    JUNIPER-SMS-MIB DEFINITIONS ::= BEGIN

    IMPORTS
        Integer32,
        NOTIFICATION-TYPE,
        MODULE-IDENTITY, OBJECT-TYPE   FROM SNMPv2-SMI
        DisplayString                  FROM SNMPv2-TC
        jnxJsSMS                       FROM JUNIPER-JS-SMI;

    jnxJsSMSMib    MODULE-IDENTITY
        LAST-UPDATED "202009020000Z"
        ORGANIZATION  "Juniper Networks, Inc."
        CONTACT-INFO
            "Juniper Technical Assistance Center
             Juniper Networks, Inc.
             1133 Innovation Way
             Sunnyvale, CA 94089

             E-mail: support@juniper.net
             HTTP://www.juniper.net"
        DESCRIPTION
            "This module defines the objects pertaining to Advanced Anti-Malware"
        REVISION      "202009020000Z"
        DESCRIPTION   "Creation Date"
        ::= { jnxJsSMS 1 }


    jnxJsSMSNotifications OBJECT IDENTIFIER ::= { jnxJsSMSMib 0 }
    jnxJsSMSObjects       OBJECT IDENTIFIER ::= { jnxJsSMSMib 1 }


    -- ***************************************************************
    --  Next Branch node.
    -- ***************************************************************

    jnxJsSMSTrapVars           OBJECT IDENTIFIER ::= { jnxJsSMSObjects 1 }

    -- ********************************************************************
    -- Objects used for the traps
    -- ********************************************************************
    jnxJsSMSChannelType   OBJECT-TYPE
        SYNTAX      DisplayString
        MAX-ACCESS  accessible-for-notify
        STATUS      current
        DESCRIPTION
            "The Channel Type of Advanced Anti-Malware to-cloud connection."
        ::= { jnxJsSMSTrapVars 1 }


    --
    -- SMS Channel is UP
    --
    jnxJsSMSChannelUp NOTIFICATION-TYPE
        OBJECTS         { jnxJsSMSChannelType }
        STATUS          current
        DESCRIPTION
            "An Advanced Anti-Malware Channel Up trap signifies that
             SMS to-cloud connection is up."
        ::= { jnxJsSMSNotifications 1 }


    --
    -- SMS Channel is Down
    --
    jnxJsSMSChannelDown NOTIFICATION-TYPE
        OBJECTS         { jnxJsSMSChannelType }
        STATUS          current
        DESCRIPTION
            "An Advanced Anti-Malware Channel Down trap signifies that
             SMS to-cloud connection is down."
        ::= { jnxJsSMSNotifications 2 }

END
