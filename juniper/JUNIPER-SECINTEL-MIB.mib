-- *******************************************************************
-- Juniper SecIntel objects MIB.
--
-- Copyright (c) 2020, Juniper Networks, Inc.
-- All rights reserved.
--
-- The contents of this document are subject to change without notice.
-- *******************************************************************

    JUNIPER-SECINTEL-MIB DEFINITIONS ::= BEGIN

    IMPORTS
        Integer32,
        NOTIFICATION-TYPE,
        MODULE-IDENTITY, OBJECT-TYPE   FROM SNMPv2-SMI
        DisplayString                  FROM SNMPv2-TC
        jnxJsSecIntel                  FROM JUNIPER-JS-SMI;

    jnxJsSecIntelMib    MODULE-IDENTITY
        LAST-UPDATED "202009020000Z"
        ORGANIZATION  "Juniper Networks, Inc."
        CONTACT-INFO
            "Juniper Technical Assistance Center
             Juniper Networks, Inc.
             1133 Innovation Way
             Sunnyvale, CA 94089

             E-mail: support@juniper.net
             HTTP://www.juniper.net"
        DESCRIPTION
            "This module defines the objects pertaining to Advanced Anti-Malware"
        REVISION      "202009020000Z"
        DESCRIPTION   "Creation Date"
        ::= { jnxJsSecIntel 1 }


    jnxJsSecIntelNotifications OBJECT IDENTIFIER ::= { jnxJsSecIntelMib 0 }
    jnxJsSecIntelObjects       OBJECT IDENTIFIER ::= { jnxJsSecIntelMib 1 }


    -- ***************************************************************
    --  Next Branch node.
    -- ***************************************************************

    jnxJsSecIntelTrapVars           OBJECT IDENTIFIER ::= { jnxJsSecIntelObjects 1 }

    -- ********************************************************************
    -- Objects used for the traps
    -- ********************************************************************
    jnxJsSecIntelChannelType   OBJECT-TYPE
        SYNTAX      DisplayString
        MAX-ACCESS  accessible-for-notify
        STATUS      current
        DESCRIPTION
            "The Channel Type of Advanced Anti-Malware to-cloud connection."
        ::= { jnxJsSecIntelTrapVars 1 }


    --
    -- SecIntel Channel is UP
    --
    jnxJsSecIntelChannelUp NOTIFICATION-TYPE
        OBJECTS         { jnxJsSecIntelChannelType }
        STATUS          current
        DESCRIPTION
            "An Advanced Anti-Malware Channel Up trap signifies that
             SecIntel to-cloud connection is up."
        ::= { jnxJsSecIntelNotifications 1 }


    --
    -- SecIntel Channel is Down
    --
    jnxJsSecIntelChannelDown NOTIFICATION-TYPE
        OBJECTS         { jnxJsSecIntelChannelType }
        STATUS          current
        DESCRIPTION
            "An Advanced Anti-Malware Channel Down trap signifies that
             SecIntel to-cloud connection is down."
        ::= { jnxJsSecIntelNotifications 2 }

END
