-- Cambium MIB Release CAMBIUM_MIB_VERSION
   CAMBIUM-TRAP-MIB DEFINITIONS ::= BEGIN

   IMPORTS
       OBJECT-TYPE, MODULE-IDENTITY, NOTIFICATION-TYPE,
       enterprises, IpAddress, Integer32, Counter32, Counter64, TimeTicks, snmpModules
           FROM SNMPv2-SMI
       OBJECT-GROUP
           FROM SNMPv2-CONF
       MacAddress, DisplayString, TEXTUAL-CONVENTION
           FROM SNMPv2-TC
       cnPilotMIB
           FROM CAMBIUM-MIB;

   cambiumTrapGroup                OBJECT IDENTIFIER ::= { cnPilotMIB 2 }

   
   clientConnected NOTIFICATION-TYPE
          STATUS      current
          DESCRIPTION
               "Client [client] connected to wireless lan [wlan]"
          ::= { cambiumTrapGroup 1 }

   clientDisconnected NOTIFICATION-TYPE
          STATUS      current
          DESCRIPTION
               "Client [client] disconnected from WLAN [wlan] after [age] secs roamed [roamed] txbytes [tx_bytes] rxbytes [rx_bytes] avgtx [avgtx] maxtx [maxtx] mintx [mintx] avgrx [avgrx] maxrx [maxrx] minrx [minrx]"
          ::= { cambiumTrapGroup 2 }

   meshClientConnected NOTIFICATION-TYPE
          STATUS      current
          DESCRIPTION
               "Mesh Client [client] connected to wireless lan [wlan]"
          ::= { cambiumTrapGroup 3 }

   meshClientDisconnected NOTIFICATION-TYPE
          STATUS      current
          DESCRIPTION
               "Mesh Client [client] with base [base_mac] disconnected from WLAN [wlan] after [age] secs roamed [roamed] txbytes [tx_bytes] rxbytes [rx_bytes] avgtx [avgtx] maxtx [maxtx] mintx [mintx] avgrx [avgrx] maxrx [maxrx] minrx [minrx]"
          ::= { cambiumTrapGroup 4 }

   clientRadiusAuthSuccess NOTIFICATION-TYPE
          STATUS      current
          DESCRIPTION
               "RADIUS authentication success for client [client] on wireless lan [wlan]"
          ::= { cambiumTrapGroup 5 }

   clientRadiusAuthReject NOTIFICATION-TYPE
          STATUS      current
          DESCRIPTION
               "RADIUS authentication rejected for client [client] on wireless lan [wlan] by server [server]"
          ::= { cambiumTrapGroup 6 }

   clientRadiusAuthTimeout NOTIFICATION-TYPE
          STATUS      current
          DESCRIPTION
               "RADIUS authentication timed out for client [client] on wireless lan [wlan] server [server]"
          ::= { cambiumTrapGroup 7 }

   clientRadiusAcctTimeout NOTIFICATION-TYPE
          STATUS      current
          DESCRIPTION
               "Client [client] RADIUS accounting timeout on server [server]"
          ::= { cambiumTrapGroup 8 }

   clientLdapAuthSuccess NOTIFICATION-TYPE
          STATUS      current
          DESCRIPTION
               "LDAP authentication success for client [client] on wireless lan [wlan]"
          ::= { cambiumTrapGroup 9 }

   clientLdapAuthReject NOTIFICATION-TYPE
          STATUS      current
          DESCRIPTION
               "LDAP authentication rejected for client [client] on wireless lan [wlan] by server [server]"
          ::= { cambiumTrapGroup 10 }

   clientLdapAuthTimeout NOTIFICATION-TYPE
          STATUS      current
          DESCRIPTION
               "LDAP authentication timed out for client [client] on wireless lan [wlan] server [server]"
          ::= { cambiumTrapGroup 11 }

   clientGuestLoginSuccess NOTIFICATION-TYPE
          STATUS      current
          DESCRIPTION
               "Guest Client [client] logged in on wireless lan[wlan]"
          ::= { cambiumTrapGroup 12 }

   clientGuestLogoutSuccess NOTIFICATION-TYPE
          STATUS      current
          DESCRIPTION
               "Guest Client [client] logged out on wireless lan[wlan]"
          ::= { cambiumTrapGroup 13 }

   clientGuestSessionTimeout NOTIFICATION-TYPE
          STATUS      current
          DESCRIPTION
               "Guest Client [client] session expired on wireless lan[wlan]"
          ::= { cambiumTrapGroup 14 }

   clientWpa2InvalidPsk NOTIFICATION-TYPE
          STATUS      current
          DESCRIPTION
               "Client [client] failed handshake on wireless lan [wlan] due to invalid pre-shared key"
          ::= { cambiumTrapGroup 15 }

   clientEroamDisconnected NOTIFICATION-TYPE
          STATUS      current
          DESCRIPTION
               "Client [client] with snr [snr] disconnected from wireless lan [wlan] due to enhanced roaming threshold [threshold]"
          ::= { cambiumTrapGroup 16 }

   clientArpFlood NOTIFICATION-TYPE
          STATUS      current
          DESCRIPTION
               "Client [client] arp flood [status] drop counter [count]"
          ::= { cambiumTrapGroup 17 }

   dynAuthDisconnectReq NOTIFICATION-TYPE
          STATUS      current
          DESCRIPTION
               "Received Dynamic Authorization Disconnect-Request from [server] for client [client]"
          ::= { cambiumTrapGroup 18 }

   dynAuthCoaReq NOTIFICATION-TYPE
          STATUS      current
          DESCRIPTION
               "Received Dynamic Authorization CoA from [server] for client [client]"
          ::= { cambiumTrapGroup 19 }

   meshXtndedDev NOTIFICATION-TYPE
          STATUS      current
          DESCRIPTION
               "Mesh xtnded device [mesh_xtnded_dev] connected through mesh client [client]"
          ::= { cambiumTrapGroup 20 }

   meshBaseRecTriggered NOTIFICATION-TYPE
          STATUS      current
          DESCRIPTION
               "Toggling between Mesh Base and recovery [reason]"
          ::= { cambiumTrapGroup 21 }

   meshLoop NOTIFICATION-TYPE
          STATUS      current
          DESCRIPTION
               "Mesh Loop detected"
          ::= { cambiumTrapGroup 22 }

   acsTriggeredOnRadio NOTIFICATION-TYPE
          STATUS      current
          DESCRIPTION
               "Triggered auto channel selection on radio [radio-num]"
          ::= { cambiumTrapGroup 23 }

   acsChannelSwitch NOTIFICATION-TYPE
          STATUS      current
          DESCRIPTION
               "Channel switched to [channel] on radio [radio-num]"
          ::= { cambiumTrapGroup 24 }

   chanwidthChange NOTIFICATION-TYPE
          STATUS      current
          DESCRIPTION
               "Channel width on radio [radio-num] fallback to [BW]"
          ::= { cambiumTrapGroup 25 }

   autorfIcaComplete NOTIFICATION-TYPE
          STATUS      current
          DESCRIPTION
               "Initial Channel Assignment complete on [radio] radio"
          ::= { cambiumTrapGroup 26 }

   autorfChannelSwitch NOTIFICATION-TYPE
          STATUS      current
          DESCRIPTION
               "Channel switched from [channel] to [channel] on [radio] radio, [reason_code_str]"
          ::= { cambiumTrapGroup 27 }

   autorfTxpower NOTIFICATION-TYPE
          STATUS      current
          DESCRIPTION
               "Autocell triggered txpower change from [oldtxpower] to [txpower] on radio [ridx]"
          ::= { cambiumTrapGroup 28 }

   autocellBybandRequiresOcsEnable NOTIFICATION-TYPE
          STATUS      current
          DESCRIPTION
               "Autocell by-band mode requires OCS enable on radio [ridx]"
          ::= { cambiumTrapGroup 29 }



   nfChannelSwitch NOTIFICATION-TYPE
          STATUS      current
          DESCRIPTION
               "Channel switched from [channel] to [cchannel] on [radio] radio due to NF"
          ::= { cambiumTrapGroup 32 }

   radarDetected NOTIFICATION-TYPE
          STATUS      current
          DESCRIPTION
               "Radar detected on channel [channel] new channel [cchannel]"
          ::= { cambiumTrapGroup 33 }

   restartingProcess NOTIFICATION-TYPE
          STATUS      current
          DESCRIPTION
               "Restarting unresponsive process [procname]"
          ::= { cambiumTrapGroup 34 }

   lowMemoryRestart NOTIFICATION-TYPE
          STATUS      current
          DESCRIPTION
               "Restarting system, free memory [freemem] lower than threshold"
          ::= { cambiumTrapGroup 35 }

   configApplied NOTIFICATION-TYPE
          STATUS      current
          DESCRIPTION
               "System configuration change applied"
          ::= { cambiumTrapGroup 36 }

   ccNotset NOTIFICATION-TYPE
          STATUS      current
          DESCRIPTION
               "Country Code is not Configured"
          ::= { cambiumTrapGroup 37 }

   configDefaulted NOTIFICATION-TYPE
          STATUS      current
          DESCRIPTION
               "System configuration was reset to default"
          ::= { cambiumTrapGroup 38 }

   configCapPower NOTIFICATION-TYPE
          STATUS      current
          DESCRIPTION
               "The radio power is capped to regulatory max"
          ::= { cambiumTrapGroup 39 }

   configApplyFail NOTIFICATION-TYPE
          STATUS      current
          DESCRIPTION
               "Error applying configuration [error]"
          ::= { cambiumTrapGroup 40 }

   fwUpgradeFailed NOTIFICATION-TYPE
          STATUS      current
          DESCRIPTION
               "System firmware upgrade failed [reason]"
          ::= { cambiumTrapGroup 41 }

   fwUpgradeSuccess NOTIFICATION-TYPE
          STATUS      current
          DESCRIPTION
               "System firmware was successfully upgraded to [firmware]"
          ::= { cambiumTrapGroup 42 }

   watchdogReset NOTIFICATION-TYPE
          STATUS      current
          DESCRIPTION
               "System rebooted due to watchdog reset"
          ::= { cambiumTrapGroup 43 }

   cnmaestroMonitorReset NOTIFICATION-TYPE
          STATUS      current
          DESCRIPTION
               "System rebooted due to cnMaestro connection failure"
          ::= { cambiumTrapGroup 44 }

   renewInterfaceIp NOTIFICATION-TYPE
          STATUS      current
          DESCRIPTION
               "Renewed the interface IP on link [ifname] status move to up and running state"
          ::= { cambiumTrapGroup 45 }

   dhcpMtuIgnored NOTIFICATION-TYPE
          STATUS      current
          DESCRIPTION
               "DHCP MTU [mtu] is being ignored on the interface [interface]"
          ::= { cambiumTrapGroup 46 }

   adminReboot NOTIFICATION-TYPE
          STATUS      current
          DESCRIPTION
               "Administrator initiated system reboot"
          ::= { cambiumTrapGroup 47 }

   tunnelUp NOTIFICATION-TYPE
          STATUS      current
          DESCRIPTION
               "Tunnel on interface [interface] is up and running"
          ::= { cambiumTrapGroup 48 }

   tunnelDown NOTIFICATION-TYPE
          STATUS      current
          DESCRIPTION
               "Tunnel on interface [interface] went down"
          ::= { cambiumTrapGroup 49 }

   wwanUp NOTIFICATION-TYPE
          STATUS      current
          DESCRIPTION
               "USB Cellular modem dongle on interface [interface] is up"
          ::= { cambiumTrapGroup 50 }

   wwanDown NOTIFICATION-TYPE
          STATUS      current
          DESCRIPTION
               "USB Cellular modem dongle on interface [interface] went down"
          ::= { cambiumTrapGroup 51 }

   wwanBackup NOTIFICATION-TYPE
          STATUS      current
          DESCRIPTION
               "Ethernet backhaul is [status], Trying to connect using [type] network"
          ::= { cambiumTrapGroup 52 }

   pppoeConnected NOTIFICATION-TYPE
          STATUS      current
          DESCRIPTION
               "PPPOE tunnel on interface[interface] connected successfully"
          ::= { cambiumTrapGroup 53 }

   pppoeDisconnected NOTIFICATION-TYPE
          STATUS      current
          DESCRIPTION
               "PPPOE tunnel on interface[interface] disconnected successfully"
          ::= { cambiumTrapGroup 54 }

   pppoeAuthFailed NOTIFICATION-TYPE
          STATUS      current
          DESCRIPTION
               "PPPOE on interface[interface] authentication failed. Username:[username]"
          ::= { cambiumTrapGroup 55 }

   monitorHostDown NOTIFICATION-TYPE
          STATUS      current
          DESCRIPTION
               "Disabling WLAN [wlan] as monitor host [server] is unreachable"
          ::= { cambiumTrapGroup 56 }

   monitorHostUp NOTIFICATION-TYPE
          STATUS      current
          DESCRIPTION
               "Enabling WLAN [wlan] as monitor host [server] is reachable"
          ::= { cambiumTrapGroup 57 }

   monitorHostUpWlanDown NOTIFICATION-TYPE
          STATUS      current
          DESCRIPTION
               "Disabled WLAN [wlan] even though monitor host [server] is reachable but ssid timing disabled WLAN"
          ::= { cambiumTrapGroup 58 }

   autoDetectBackhaul NOTIFICATION-TYPE
          STATUS      current
          DESCRIPTION
               "Ethernet backhaul is [status], Trying to connect using [type] network"
          ::= { cambiumTrapGroup 59 }

   ipAssigned NOTIFICATION-TYPE
          STATUS      current
          DESCRIPTION
               "Client [mac], assigned [type] IP [ip] from DHCP pool [pool]"
          ::= { cambiumTrapGroup 60 }

   watchdogUnresp NOTIFICATION-TYPE
          STATUS      current
          DESCRIPTION
               "System going to reboot due to unresponsive process [procname]"
          ::= { cambiumTrapGroup 61 }

   cfgFallbackReboot NOTIFICATION-TYPE
          STATUS      current
          DESCRIPTION
               "System rebooted after fallback to last good configuration"
          ::= { cambiumTrapGroup 62 }

   cfgOverwriteReboot NOTIFICATION-TYPE
          STATUS      current
          DESCRIPTION
               "System rebooted after config overwrite"
          ::= { cambiumTrapGroup 63 }

   apConnected NOTIFICATION-TYPE
          STATUS      current
          DESCRIPTION
               "Access Point [name] MAC [mac] connected to Autopilot Master-AP"
          ::= { cambiumTrapGroup 64 }

   apDisconnected NOTIFICATION-TYPE
          STATUS      current
          DESCRIPTION
               "Access Point [name] MAC [mac] disconnected from Autopilot Master-AP"
          ::= { cambiumTrapGroup 65 }

   addedAp NOTIFICATION-TYPE
          STATUS      current
          DESCRIPTION
               "Access Point [name] MAC [mac] added to Autopilot management"
          ::= { cambiumTrapGroup 66 }

   removedAp NOTIFICATION-TYPE
          STATUS      current
          DESCRIPTION
               "Access Point [name] MAC [mac] removed from Autopilot management"
          ::= { cambiumTrapGroup 67 }

   disallowClient NOTIFICATION-TYPE
          STATUS      current
          DESCRIPTION
               "Disconnecting client [mac] as devices of type [type] not allowed on wlan"
          ::= { cambiumTrapGroup 68 }

   clientAuthSuccess NOTIFICATION-TYPE
          STATUS      current
          DESCRIPTION
               "Authentication success for client[client_mac] IP [client_ip] User [user] SSID [ssid]"
          ::= { cambiumTrapGroup 69 }

   assocFlood NOTIFICATION-TYPE
          STATUS      current
          DESCRIPTION
               "Excessive association requests detected on AP"
          ::= { cambiumTrapGroup 70 }

   disconnectFlood NOTIFICATION-TYPE
          STATUS      current
          DESCRIPTION
               "Excessive disassociations and disconnects detected on AP"
          ::= { cambiumTrapGroup 71 }

   eapolFlood NOTIFICATION-TYPE
          STATUS      current
          DESCRIPTION
               "Excessive EAPOL packets detected on AP"
          ::= { cambiumTrapGroup 72 }

   guestLoginFails NOTIFICATION-TYPE
          STATUS      current
          DESCRIPTION
               "Excessive guest login failures detected on AP"
          ::= { cambiumTrapGroup 73 }

   invalidAddr NOTIFICATION-TYPE
          STATUS      current
          DESCRIPTION
               "Detected packet with invalid address"
          ::= { cambiumTrapGroup 74 }

   apUplinkStatus NOTIFICATION-TYPE
          STATUS      current
          DESCRIPTION
               "Gateway [gateway_ip] reachable through [ap_uplink] interface"
          ::= { cambiumTrapGroup 75 }


   END
