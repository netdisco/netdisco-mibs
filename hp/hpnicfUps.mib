-- ===========================================================
-- Copyright (c) 2010-2013 Hewlett-Packard Development Company, L.P.
-- Description: The MIB is designed to manage the UPS.
-- Reference:
-- Version: V1.0
-- History:
--   V1.0 2007-09-04 created by lizhicheng
-- =================================================================
HPN-ICF-UPS-MIB DEFINITIONS ::= BEGIN
IMPORTS
        Counter32, Integer32,
        OBJECT-TYPE, MODULE-IDENTITY, NOTIFICATION-TYPE
    FROM SNMPv2-SMI
        TEXTUAL-CONVENTION
    FROM SNMPv2-TC
        InetAddressType, InetAddress
    FROM INET-ADDRESS-MIB
        entPhysicalIndex
    FROM ENTITY-MIB
        hpnicfCommon
    FROM HPN-ICF-OID-MIB;

hpnicfUps MODULE-IDENTITY
    LAST-UPDATED "200709041452Z"
    ORGANIZATION
        ""
    CONTACT-INFO
        ""
    DESCRIPTION
        "This MIB describes the general information of UPS(Uninterrupted
        Power Supply) device."
    ::= { hpnicfCommon 82 }

hpnicfUpsMibObjects OBJECT IDENTIFIER ::= { hpnicfUps 1 }

HpnicfActionType  ::=   TEXTUAL-CONVENTION
    STATUS      current
    DESCRIPTION
        "A control variable used to trigger an operator events,
        when read, always returns a value of invalid."
    SYNTAX      INTEGER
        {
            action(1),
            invalid(2)
        }

-- UPS Entity Extend Table
-- This table described some information about the UPS.

hpnicfUpsConfigEnable OBJECT-TYPE
    SYNTAX      HpnicfActionType
    MAX-ACCESS  read-write
    STATUS      current
    DESCRIPTION
        "This object identifies the operation which will make the UPS(Uninterrupted
        Power Supply)'s new configure become effective."
    ::={ hpnicfUpsMibObjects 1 }

hpnicfUpsConfigTable OBJECT-TYPE
    SYNTAX      SEQUENCE OF HpnicfUpsConfigEntry
    MAX-ACCESS  not-accessible
    STATUS      current
    DESCRIPTION
        "This table contains an entry for user to get some information
        about the UPS device."
    ::= { hpnicfUpsMibObjects 2 }



hpnicfUpsConfigEntry OBJECT-TYPE
    SYNTAX      HpnicfUpsConfigEntry
    MAX-ACCESS  not-accessible
    STATUS      current
    DESCRIPTION
        "An entry containing management information applicable
        to a particular UPS."
    INDEX
        {
            hpnicfUpsIndex
        }

    ::= { hpnicfUpsConfigTable 1 }

HpnicfUpsConfigEntry ::= SEQUENCE
    {
        hpnicfUpsIndex            Integer32,
        hpnicfUpsType             INTEGER,
        hpnicfUpsIpAddress        InetAddress,
        hpnicfUpsIpAddressType    InetAddressType
    }

hpnicfUpsIndex OBJECT-TYPE
    SYNTAX      Integer32
    MAX-ACCESS  not-accessible
    STATUS      current
    DESCRIPTION
        "This object identifies the index of hpnicfUpsConfigTable. The object
        identified by this index is the same object as identified by the
        same value of entPhysicalIndex."
    ::= { hpnicfUpsConfigEntry 1 }

hpnicfUpsType OBJECT-TYPE
    SYNTAX      INTEGER
        {
            emersonUart(1),
            mge(2),
            common(3),
            emersonEth(4),
            liebert(5)
        }
    MAX-ACCESS  read-only
    STATUS      current
    DESCRIPTION
        "This object identifies the type of UPS.
        The value 'emersonUart' means an EMERSON UPS support UART interface.
        The value 'mge' means a MGE UPS support ethernet interface.
        The value 'common' means a common UPS support standard UPSMIB.
        The value 'emersonEth' means an EMERSON UPS support ethernet interface.
        The value 'liebert' means a Liebert UPS support ethernet interface."
    ::= { hpnicfUpsConfigEntry 2 }

hpnicfUpsIpAddress OBJECT-TYPE
    SYNTAX      InetAddress
    MAX-ACCESS  read-write
    STATUS      current
    DESCRIPTION
        "This object describes the address of UPS. The value of this object
        is invalid if the UPS do not support ethernet interface."
    ::= { hpnicfUpsConfigEntry 3 }

hpnicfUpsIpAddressType OBJECT-TYPE
    SYNTAX      InetAddressType
    MAX-ACCESS  read-write
    STATUS      current
    DESCRIPTION
        "This object describes the address type of UPS. The value of this object
        is invalid if the UPS do not support ethernet interface."
    ::= { hpnicfUpsConfigEntry 4 }

END
