-- =====================================================================
-- Copyright (c) 2010-2013 Hewlett-Packard Development Company, L.P.
--
-- Description: IPv6 address MIB
-- Reference:
-- Version: V1.1
-- History:
--   V1.0 2006-03-15 Created by Zhang Jun and Yu Hongqiang
--     Initial version
--   V1.1 2013-01-22 Modified by yuguoqing
--     Modify the description of hpnicfIpv6AddrSetSourceType
--     and hpnicfIpv6AddrReadSourceType
-- =====================================================================
HPN-ICF-IPV6-ADDRESS-MIB DEFINITIONS ::= BEGIN

    IMPORTS
        hpnicfCommon
            FROM HPN-ICF-OID-MIB
        Integer32, OBJECT-TYPE, MODULE-IDENTITY
            FROM SNMPv2-SMI
        RowStatus
            FROM SNMPv2-TC
        InetAddress, InetAddressType
            FROM INET-ADDRESS-MIB;

    hpnicfIpv6AddrMIB MODULE-IDENTITY
        LAST-UPDATED "200603150000Z"
        ORGANIZATION
            ""
        CONTACT-INFO
            ""
        DESCRIPTION
            "The MIB module for managing IPv6 address"
        REVISION "200603150000Z"
        DESCRIPTION
            "The initial revision of this MIB module."
        ::= { hpnicfCommon 71 }


--
-- Node definitions
--
    hpnicfIpv6AddressObjects OBJECT IDENTIFIER ::= { hpnicfIpv6AddrMIB 1 }

    hpnicfIpv6AddressConfig OBJECT IDENTIFIER ::= { hpnicfIpv6AddressObjects 1 }

    hpnicfIpv6AddrSetTable OBJECT-TYPE
        SYNTAX      SEQUENCE OF HpnicfIpv6AddrSetEntry
        MAX-ACCESS  not-accessible
        STATUS      current
        DESCRIPTION
            "The table of address information is relevant to this
            entity's IPv6 addresses for setting. The address information
            that can be read and set in this table is a subset of the
            address information that can be read in hpnicfIpv6AddrReadTable
            and ipv6AddrTable in IPV6-MIB. This table is used to configure IPv6
            addresses of an interface identified by hpnicfIpv6AddrSetIfIndex.
            When users create or delete an entry in this table, the agent also
            increases or reduces a corresponding entry in the
            hpnicfIpv6AddrReadTable and ipv6AddrTable in IPV6-MIB.
            When an interface which has been assigned IPv6 address is deleted,
            the agent also deletes the entry corresponding to
            the interface in this table and hpnicfIpv6AddrReadTable.
            All IPv6 addresses in this table will also show in ipv6AddrTable in
            IPV6-MIB."
        REFERENCE
            "RFC 2456"
        ::= { hpnicfIpv6AddressConfig 1 }

    hpnicfIpv6AddrSetEntry OBJECT-TYPE
        SYNTAX      HpnicfIpv6AddrSetEntry
        MAX-ACCESS  not-accessible
        STATUS      current
        DESCRIPTION
            "Define the IPv6 address information."
        INDEX
        {
            hpnicfIpv6AddrSetIfIndex,
            hpnicfIpv6AddrSetAddrType,
            hpnicfIpv6AddrSetAddr
        }
        ::= { hpnicfIpv6AddrSetTable 1 }

    HpnicfIpv6AddrSetEntry ::=
    SEQUENCE
    {
        hpnicfIpv6AddrSetIfIndex       Integer32,
        hpnicfIpv6AddrSetAddrType      InetAddressType,
        hpnicfIpv6AddrSetAddr          InetAddress,
        hpnicfIpv6AddrSetPfxLength     Integer32,
        hpnicfIpv6AddrSetSourceType    INTEGER,
        hpnicfIpv6AddrSetRowStatus     RowStatus
    }

    hpnicfIpv6AddrSetIfIndex OBJECT-TYPE
        SYNTAX      Integer32(1..2147483647)
        MAX-ACCESS  not-accessible
        STATUS      current
        DESCRIPTION
            "The index value which uniquely identifies the interface to
            which this entry is applicable. The interface identified by
            a particular value of this index is the same interface as
            identified by the same value of RFC 1573's ifIndex."
        ::= { hpnicfIpv6AddrSetEntry 1 }

    hpnicfIpv6AddrSetAddrType OBJECT-TYPE
        SYNTAX      InetAddressType
        MAX-ACCESS  not-accessible
        STATUS      current
        DESCRIPTION
            "The IP address type to which this entry's address
            information pertains. The value must be ipv6."
        ::= { hpnicfIpv6AddrSetEntry 2 }

    hpnicfIpv6AddrSetAddr OBJECT-TYPE
        SYNTAX      InetAddress
        MAX-ACCESS  not-accessible
        STATUS      current
        DESCRIPTION
            "The IPv6 address to which this entry's address
            information pertains."
        ::= { hpnicfIpv6AddrSetEntry 3 }

    hpnicfIpv6AddrSetPfxLength OBJECT-TYPE
        SYNTAX      Integer32(1..128)
        MAX-ACCESS  read-create
        STATUS      current
        DESCRIPTION
            "The length of the prefix (in bits) associated with
            the IPv6 address of this entry."
        ::= { hpnicfIpv6AddrSetEntry 4 }

    hpnicfIpv6AddrSetSourceType OBJECT-TYPE
        SYNTAX      INTEGER
                    {
                        assignedIp(1),
                        assignedEUI64Ip(2),
                        assignedLinklocalIp(3)
                    }
        MAX-ACCESS  read-create
        STATUS      current
        DESCRIPTION
            "Indicate the type of source of IPv6 address.
            The value can be one of following:
            'assignedIp':
                Assigned global/site-local IPv6 address;
            'assignedEUI64Ip':
                Assigned global/site-local IPv6 address
                by using EUI-64 interface identifier;
            'assignedLinklocalIp':
                Assigned link-local IPv6 address.
            The value of hpnicfIpv6AddrSetSourceType is relevant to
                hpnicfIpv6AddrReadSourceType and hpnicfIpv6AddrReadCatalog .
            For example, if the value of hpnicfIpv6AddrSetSourceType is set to
                'assignedIp', then the value of hpnicfIpv6AddrReadSourceType is
                'assignedIp' and the value of hpnicfIpv6AddrReadCatalog is
                'global' or 'sitelocal'.
            The relation listed in the following table.
            ----------------------------------------------------------------
             hpnicfIpv6Addr-       | hpnicfIpv6Addr-     | hpnicfIpv6Addr-
             SetSourceType       | ReadSourceType    | ReadCatalog
            ----------------------------------------------------------------
             assignedIp          | assignedIp        | global or sitelocal
            ----------------------------------------------------------------
             assignedEUI64Ip     | assignedEUI64Ip   | global or sitelocal
            ----------------------------------------------------------------
             assignedLinklocalIp | assignedIp        | linklocal
            ----------------------------------------------------------------
            "
        ::= { hpnicfIpv6AddrSetEntry 5 }

    hpnicfIpv6AddrSetRowStatus OBJECT-TYPE
        SYNTAX      RowStatus
        MAX-ACCESS  read-create
        STATUS      current
        DESCRIPTION
            "This object is used to create a new row or delete an
            existing row in this table, only supports active(1),
            createAndGo(4) and destroy(6)."
        ::= { hpnicfIpv6AddrSetEntry 6 }

    hpnicfIpv6AddrReadTable OBJECT-TYPE
        SYNTAX      SEQUENCE OF HpnicfIpv6AddrReadEntry
        MAX-ACCESS  not-accessible
        STATUS      current
        DESCRIPTION
            "The table of address information is relevant to this
            entity's IPv6 addresses for reading.
            This is the extension of the ipv6AddrTable in IPV6-MIB.
            All IPv6 addresses in this table will also show in ipv6AddrTable
            in IPV6-MIB."
        REFERENCE
            "RFC 2456"
        ::= { hpnicfIpv6AddressConfig 2 }

    hpnicfIpv6AddrReadEntry OBJECT-TYPE
        SYNTAX      HpnicfIpv6AddrReadEntry
        MAX-ACCESS  not-accessible
        STATUS      current
        DESCRIPTION
            "Define the IPv6 address information."
        INDEX
        {
            hpnicfIpv6AddrReadIfIndex,
            hpnicfIpv6AddrReadAddrType,
            hpnicfIpv6AddrReadAddr
        }
        ::= { hpnicfIpv6AddrReadTable 1 }

    HpnicfIpv6AddrReadEntry ::=
        SEQUENCE
        {
            hpnicfIpv6AddrReadIfIndex       Integer32,
            hpnicfIpv6AddrReadAddrType      InetAddressType,
            hpnicfIpv6AddrReadAddr          InetAddress,
            hpnicfIpv6AddrReadPfxLength     Integer32,
            hpnicfIpv6AddrReadSourceType    INTEGER,
            hpnicfIpv6AddrReadCatalog       INTEGER
        }

    hpnicfIpv6AddrReadIfIndex OBJECT-TYPE
        SYNTAX      Integer32(1..2147483647)
        MAX-ACCESS  not-accessible
        STATUS      current
        DESCRIPTION
            "The index value which uniquely identifies the interface to
            which this entry is applicable. The interface identified by
            a particular value of this index is the same interface as
            identified by the same value of RFC 1573's ifIndex."
        ::= { hpnicfIpv6AddrReadEntry 1 }

    hpnicfIpv6AddrReadAddrType OBJECT-TYPE
        SYNTAX      InetAddressType
        MAX-ACCESS  not-accessible
        STATUS      current
        DESCRIPTION
            "The IP address type to which this entry's address information
            pertains. The value must be ipv6."
        ::= { hpnicfIpv6AddrReadEntry 2 }

    hpnicfIpv6AddrReadAddr OBJECT-TYPE
        SYNTAX      InetAddress
        MAX-ACCESS  not-accessible
        STATUS      current
        DESCRIPTION
            "The IPv6 address to which this entry's address information
            pertains."
        ::= { hpnicfIpv6AddrReadEntry 3 }

    hpnicfIpv6AddrReadPfxLength OBJECT-TYPE
        SYNTAX      Integer32(1..128)
        MAX-ACCESS  read-only
        STATUS      current
        DESCRIPTION
            "The length of the prefix (in bits) associated with
            the IPv6 address of this entry."
        ::= { hpnicfIpv6AddrReadEntry 4 }

    hpnicfIpv6AddrReadSourceType OBJECT-TYPE
        SYNTAX      INTEGER
                    {
                        assignedIp(1),
                        assignedEUI64Ip(2),
                        assignedAutoIp(3),
                        autoIp(4),
                        dhcpv6(5),
                        negotiate(6),
                        cluster(7)
                    }
        MAX-ACCESS  read-only
        STATUS      current
        DESCRIPTION
            "Indicate the type of source of IPv6 address.
            The value can be one of following:
                'assignedIp':      Assigned IPv6 address;
                'assignedEUI64Ip': Assigned IPv6 address by using EUI-64
                                   interface identifier;
                'assignedAutoIp':  Auto generated IPv6 address by user setting;
                'autoIp':          Auto generated IPv6 address as a result
                                   of non-linklocal anycast/unicast address
                                   configuration;
                'dhcpv6':          Assigned IPv6 address through DHCPv6
                                   protocol;
                'negotiate':       Assigned IPv6 address through negotiation;
                'cluster':         Assigned IPv6 address through cluster
                                   module."
        ::= { hpnicfIpv6AddrReadEntry 5 }

    hpnicfIpv6AddrReadCatalog OBJECT-TYPE
        SYNTAX      INTEGER
                    {
                        nodelocal(1),
                        linklocal(2),
                        sitelocal(3),
                        orglocal(4),
                        global(5)
                    }
        MAX-ACCESS  read-only
        STATUS      current
        DESCRIPTION
            "Indicate the category of the IPv6 address.
            The value can be one of following:
            'nodelocal': node-local scope;
            'linklocal': link-local scope;
            'sitelocal': site-local scope;
            'orglocal': organization-local scope;
            'global': global scope. "
        ::= { hpnicfIpv6AddrReadEntry 6 }
END
