-- =================================================================
-- Copyright (c) 2010-2013 Hewlett-Packard Development Company, L.P.
--
-- Description: description of Web Authentication
-- Reference:
-- Version: V1.0
-- History:
--   V1.0 2008-6-25, Created by dupengfei
-- =================================================================
HPN-ICF-WEB-AUTHENTICATION-MIB DEFINITIONS ::= BEGIN

IMPORTS
    hpnicfCommon
        FROM HPN-ICF-OID-MIB
    ifDescr
        FROM RFC1213-MIB
    OBJECT-TYPE, NOTIFICATION-TYPE, MODULE-IDENTITY, Integer32
        FROM SNMPv2-SMI
    MacAddress
        FROM SNMPv2-TC;

hpnicfWebAuthentication MODULE-IDENTITY
    LAST-UPDATED "200806250000Z"
    ORGANIZATION
        ""
    CONTACT-INFO
        ""
    DESCRIPTION
        "The MIB module is used for web authentication to send traps."
    REVISION "200806250000Z"
    DESCRIPTION
        "The initial version of hpnicfWebAuthenticationMIB"
    ::= { hpnicfCommon 93 }


hpnicfWaTrapObjects OBJECT IDENTIFIER ::= { hpnicfWebAuthentication 1 }

--
-- WEB AUTHENTICATION TRAPS OBJECT
--
hpnicfWaVlanID OBJECT-TYPE
    SYNTAX      Integer32
    MAX-ACCESS  accessible-for-notify
    STATUS      current
    DESCRIPTION
        "The Vlan ID associate with the port and the MAC address."
    ::= { hpnicfWaTrapObjects 1 }

hpnicfWaReasonCode OBJECT-TYPE
    SYNTAX INTEGER
    {
         globalNumberMax(1),
         configNumberMax(2),
         portNumberMax(3),
         invalidUsername(4),
         authFail(5),
         setACLFail(6),
         changeVlanFail(7),
         other(8),
         onlineOverTime(9),
         noTransferData(10),
         cutOperation(11),
         portDisabled(12),
         portDown(13),
         userLogout(14),
         vlanChanged(15),
         vlanDelted(16)
    }
    MAX-ACCESS  accessible-for-notify
    STATUS      current
    DESCRIPTION
        "The code indicates the reason for the action of this trap.
         globalNumberMax:
            The global number of connections is up to max.
         configNumberMax:
            The global number of connections is up to configured max value.
         portNumberMax:
            The interface number of connections is up to max.
         invalidUsername:
            The username or password is too long or username is empty.
         authFail:
            Wrong username or password.
         setACLFail:
            Failed to set ACL.
         changeVlanFail:
            Failed to set VLAN.
         other:
            Other reasons.
         onlineOverTime:
            The online time is over the max value.
         noTransferData:
            There was no data flow for the connection.
         cutOperation:
            There was a cut operation.
         portDisabled:
            Web authentication was disabled on interface.
         portDown:
            The interface turned down.
         userLogout:
            The client required to logout.
         vlanChanged:
            The interface VLAN value was changed.
         vlanDelted:
            The interface VLAN was deleted."
    ::= { hpnicfWaTrapObjects 2 }

hpnicfWaActionCode OBJECT-TYPE
    SYNTAX INTEGER
    {
        enabled(1),
        disabled(2)
    }
    MAX-ACCESS  accessible-for-notify
    STATUS      current
    DESCRIPTION
        "The code indicates the system action.
         enabled:
            Web authentication turns enabled.
         disabled:
            Web authentication turns disabled."
    ::= { hpnicfWaTrapObjects 3 }

hpnicfWaClientMacAddr OBJECT-TYPE
    SYNTAX      MacAddress
    MAX-ACCESS  accessible-for-notify
    STATUS      current
    DESCRIPTION
        "The MAC address of the client."
    ::= { hpnicfWaTrapObjects 4 }

hpnicfWaTrap OBJECT IDENTIFIER ::= { hpnicfWebAuthentication 2 }

hpnicfWaTrapPrefix OBJECT IDENTIFIER ::= { hpnicfWaTrap 0 }


hpnicfWaClientLogon NOTIFICATION-TYPE
    OBJECTS
        {
            hpnicfWaClientMacAddr,
            ifDescr,
            hpnicfWaVlanID
        }
    STATUS      current
    DESCRIPTION
        "It is generated when a client succeeded to logon."
    ::= { hpnicfWaTrapPrefix 1 }

hpnicfWaClientLogonFail NOTIFICATION-TYPE
    OBJECTS
        {
            hpnicfWaClientMacAddr,
            ifDescr,
            hpnicfWaVlanID,
            hpnicfWaReasonCode
        }
    STATUS      current
    DESCRIPTION
        "It is generated when a client failed to logon, the hpnicfWaReasonCode
         shows the failure reason."
    ::= { hpnicfWaTrapPrefix 2 }

hpnicfWaClientLogout NOTIFICATION-TYPE
    OBJECTS
        {
            hpnicfWaClientMacAddr,
            ifDescr,
            hpnicfWaVlanID,
            hpnicfWaReasonCode
        }
    STATUS      current
    DESCRIPTION
        "It is generated when a client logout, the hpnicfWaReasonCode
         shows the logout reason."
    ::= { hpnicfWaTrapPrefix 3 }

hpnicfWaSysAction NOTIFICATION-TYPE
    OBJECTS
        {
            hpnicfWaActionCode
        }
    STATUS      current
    DESCRIPTION
        "It is generated when a system action was occurred, the hpnicfWaActionCode
         shows the action information."
    ::= { hpnicfWaTrapPrefix 4 }

END
