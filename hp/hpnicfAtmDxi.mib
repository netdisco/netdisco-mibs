-- ============================================================================
-- Copyright (c) 2010-2013 Hewlett-Packard Development Company, L.P.
-- Description:  This MIB is used for configuration of ATM-DXI.
--               include :1.ATM-DXI PVC
--                        2.ATM-DXI MAP
-- Reference:
-- Version: V1.0
-- History:
--   V1.0 2005/04/14 created by Liguanmin
-- ============================================================================
HPN-ICF-ATM-DXI-MIB DEFINITIONS ::= BEGIN

      IMPORTS
                hpnicfCommon
                    FROM HPN-ICF-OID-MIB
                ifIndex
                    FROM RFC1213-MIB
                OBJECT-GROUP,MODULE-COMPLIANCE
                    FROM SNMPv2-CONF
                Integer32, OBJECT-TYPE, MODULE-IDENTITY
                    FROM SNMPv2-SMI
                InetAddressType,InetAddress
                    FROM INET-ADDRESS-MIB
                RowStatus
                    FROM SNMPv2-TC;

      hpnicfAtmDxi MODULE-IDENTITY
                LAST-UPDATED "200504141518Z"            -- 14 April, 2005 at 15:18 GMT
                ORGANIZATION
                    ""
                CONTACT-INFO
                    ""
                DESCRIPTION
                        "This MIB contains objects to manage configuration of ATM-DXI.
                         There are no constraints on this MIB."
                REVISION "200504141518Z"                -- 14 April, 2005 at 15:18 GMT
                DESCRIPTION
                        "The initial revision of this MIB module."
                ::= { hpnicfCommon 49 }

--
-- Node definitions
--
        hpnicfAtmDxiScalarGroup OBJECT IDENTIFIER ::= { hpnicfAtmDxi 1 }

        hpnicfAtmDxiConfMode OBJECT-TYPE
                SYNTAX INTEGER
                        {
                        mode1a(1),
                        mode1b(2),
                        mode2(3)
                        }
                MAX-ACCESS read-only
                STATUS current
                DESCRIPTION
                        "This node identifies the ATM-DXI mode being
                        used at the ATM-DXI port."
                ::= { hpnicfAtmDxiScalarGroup 1 }


        hpnicfAtmDxiIfObjects OBJECT IDENTIFIER ::= { hpnicfAtmDxi 2 }


        hpnicfAtmDxiPvcTable OBJECT-TYPE
                SYNTAX SEQUENCE OF HpnicfAtmDxiPvcEntry
                MAX-ACCESS not-accessible
                STATUS current
                DESCRIPTION
                        "This table describes information of PVC in ATM-DXI interface."
                ::= { hpnicfAtmDxiIfObjects 1 }


        hpnicfAtmDxiPvcEntry OBJECT-TYPE
                SYNTAX HpnicfAtmDxiPvcEntry
                MAX-ACCESS not-accessible
                STATUS current
                DESCRIPTION
                        "The entry of hpnicfAtmDxiPvcTable."
                INDEX { ifIndex, hpnicfAtmDxiPvcVpi, hpnicfAtmDxiPvcVci }
                ::= { hpnicfAtmDxiPvcTable 1 }


        HpnicfAtmDxiPvcEntry ::=
                SEQUENCE {
                        hpnicfAtmDxiPvcVpi
                                Integer32,
                        hpnicfAtmDxiPvcVci
                                Integer32,
                        hpnicfAtmDxiPvcDFA
                                Integer32,
                        hpnicfAtmDxiPvcEncType
                                INTEGER,
                        hpnicfAtmDxiPvcMapCount
                                Integer32,
                        hpnicfAtmDxiPvcRowStatus
                                RowStatus
                 }


        hpnicfAtmDxiPvcVpi OBJECT-TYPE
                SYNTAX Integer32 (0..15)
                MAX-ACCESS not-accessible
                STATUS current
                DESCRIPTION
                        "The value of VPI.  It can't be 0 if hpnicfAtmDxiPvcVci is 0."
                ::= { hpnicfAtmDxiPvcEntry 1 }


        hpnicfAtmDxiPvcVci OBJECT-TYPE
                SYNTAX Integer32 (0..63)
                MAX-ACCESS not-accessible
                STATUS current
                DESCRIPTION
                        "The value of VCI.  It can't be 0 if hpnicfAtmDxiPvcVpi is 0."
                ::= { hpnicfAtmDxiPvcEntry 2 }


        hpnicfAtmDxiPvcDFA OBJECT-TYPE
                SYNTAX Integer32
                MAX-ACCESS read-create
                STATUS current
                DESCRIPTION
                        "The index of PVC.  It is equal with vci and VPI.  And this node value
                        is correlate with hpnicfAtmDxiPvcVpi and hpnicfAtmDxiPvcVci. "
                ::= { hpnicfAtmDxiPvcEntry 3 }


        hpnicfAtmDxiPvcEncType OBJECT-TYPE
                SYNTAX INTEGER
                        {
                        snap(1),
                        nlpid(2),
                        mux(3)
                        }
                MAX-ACCESS read-create
                STATUS current
                DESCRIPTION
                        "Encapsulation type of the frame."
                DEFVAL { snap }
                ::= { hpnicfAtmDxiPvcEntry 4 }


        hpnicfAtmDxiPvcMapCount OBJECT-TYPE
                SYNTAX Integer32 (0..32)
                MAX-ACCESS read-create
                STATUS current
                DESCRIPTION
                        "The number of map.  One map can only associate with one PVC, but
                        one PVC can associate with 32 maps.  This node is the map count
                        which one PVC associated with."
                ::= { hpnicfAtmDxiPvcEntry 5 }


        hpnicfAtmDxiPvcRowStatus OBJECT-TYPE
                SYNTAX RowStatus
                MAX-ACCESS read-create
                STATUS current
                DESCRIPTION
                        "Only support 'destroy' 'createAndGo' and 'active'."
                ::= { hpnicfAtmDxiPvcEntry 6 }


        hpnicfAtmDxiMapTable OBJECT-TYPE
                SYNTAX SEQUENCE OF HpnicfAtmDxiMapEntry
                MAX-ACCESS not-accessible
                STATUS current
                DESCRIPTION
                        "This table describes PVC map information."
                ::= { hpnicfAtmDxiIfObjects 2 }


        hpnicfAtmDxiMapEntry OBJECT-TYPE
                SYNTAX HpnicfAtmDxiMapEntry
                MAX-ACCESS not-accessible
                STATUS current
                DESCRIPTION
                        "The entry of hpnicfAtmDxiMapTable."
                INDEX { ifIndex,
                        hpnicfAtmDxiMapPeerIpType,
                        hpnicfAtmDxiMapPeerIp,
                        hpnicfAtmDxiMapPvcVpi,
                        hpnicfAtmDxiMapPvcVci,
                        hpnicfAtmDxiMapType
                      }
                ::= { hpnicfAtmDxiMapTable 1 }


        HpnicfAtmDxiMapEntry ::=
                SEQUENCE {
                        hpnicfAtmDxiMapPeerIpType
                                InetAddressType,
                        hpnicfAtmDxiMapPeerIp
                                InetAddress,
                        hpnicfAtmDxiMapPvcVpi
                                Integer32,
                        hpnicfAtmDxiMapPvcVci
                                Integer32,
                        hpnicfAtmDxiMapType
                                INTEGER,
                        hpnicfAtmDxiMapInarpTime
                                Integer32,
                        hpnicfAtmDxiMapBroEnable
                                INTEGER,
                        hpnicfAtmDxiMapRowStatus
                                RowStatus
                 }

        hpnicfAtmDxiMapPeerIpType OBJECT-TYPE
                SYNTAX InetAddressType
                MAX-ACCESS not-accessible
                STATUS current
                DESCRIPTION
                        "The type of ip address: IPv4 or IPv6."
                ::= { hpnicfAtmDxiMapEntry 1 }

        hpnicfAtmDxiMapPeerIp OBJECT-TYPE
                SYNTAX InetAddress
                MAX-ACCESS not-accessible
                STATUS current
                DESCRIPTION
                        "The peer ip address.  This ip address is the peer ip
                        address which the frame will arrive."
                ::= { hpnicfAtmDxiMapEntry 2 }

        hpnicfAtmDxiMapPvcVpi OBJECT-TYPE
                SYNTAX Integer32 (0..15)
                MAX-ACCESS not-accessible
                STATUS current
                DESCRIPTION
                        "The VPI of PVC.  It can't be 0 if hpnicfAtmDxiMapPvcVci is 0."
                ::= { hpnicfAtmDxiMapEntry 3 }

        hpnicfAtmDxiMapPvcVci OBJECT-TYPE
                SYNTAX Integer32 (0..63)
                MAX-ACCESS not-accessible
                STATUS current
                DESCRIPTION
                        "The VCI of PVC.  It can't be 0 if hpnicfAtmDxiMapPvcVpi is 0."
                ::= { hpnicfAtmDxiMapEntry 4 }

        hpnicfAtmDxiMapType OBJECT-TYPE
                SYNTAX INTEGER
                        {
                        address(1),
                        inarp(2),
                        default(3)
                        }
                MAX-ACCESS not-accessible
                STATUS current
                DESCRIPTION
                        "Pvc map type."
                ::= { hpnicfAtmDxiMapEntry 5 }

        hpnicfAtmDxiMapInarpTime OBJECT-TYPE
                SYNTAX Integer32 (0 | 5..10)
                MAX-ACCESS read-create
                STATUS current
                DESCRIPTION
                        "The interval time of inarp request.  This node describes
                        the interval time inarp request frame sent.  If the hpnicfAtmDxiMapType
                        isn't inarp, this value is 0.  Its unit is minute."
                DEFVAL { 10 }
                ::= { hpnicfAtmDxiMapEntry 6 }

        hpnicfAtmDxiMapBroEnable OBJECT-TYPE
                SYNTAX INTEGER
                        {
                        enable(1),
                        disable(2)
                        }
                MAX-ACCESS read-create
                STATUS current
                DESCRIPTION
                        "Whether ATM-DXI map enable broadcast or not."
                DEFVAL { 2 }
                ::= { hpnicfAtmDxiMapEntry 7 }

        hpnicfAtmDxiMapRowStatus OBJECT-TYPE
                SYNTAX RowStatus
                MAX-ACCESS read-create
                STATUS current
                DESCRIPTION
                        "Only support 'destroy', 'createAndGo' and 'active'."
                ::= { hpnicfAtmDxiMapEntry 8 }


        hpnicfAtmDxiConformance OBJECT IDENTIFIER ::= { hpnicfAtmDxi 3 }

        hpnicfAtmDxiCompliances OBJECT IDENTIFIER ::= { hpnicfAtmDxiConformance 1 }

        hpnicfAtmDxiCompliance MODULE-COMPLIANCE
               STATUS current
               DESCRIPTION
                       "The compliance statement."
               MODULE
               MANDATORY-GROUPS { hpnicfPVCMAPGroup }
               GROUP hpnicfAtmDxiGeneralGroup
               DESCRIPTION
                       "If ATM-DXI protocol supports other ATM-DXI modes,
                       this group must be supported."
               ::= { hpnicfAtmDxiCompliances 1 }

        hpnicfAtmDxiGroup OBJECT IDENTIFIER ::= { hpnicfAtmDxiConformance 2 }

        hpnicfPVCMAPGroup OBJECT-GROUP
                OBJECTS { hpnicfAtmDxiPvcDFA, hpnicfAtmDxiPvcEncType, hpnicfAtmDxiPvcMapCount,
                          hpnicfAtmDxiPvcRowStatus, hpnicfAtmDxiMapBroEnable, hpnicfAtmDxiMapInarpTime,
                          hpnicfAtmDxiMapRowStatus }
                STATUS current
                DESCRIPTION
                        "This group includes nodes which are associated with interface."
                ::= { hpnicfAtmDxiGroup 1 }

        hpnicfAtmDxiGeneralGroup OBJECT-GROUP
                OBJECTS { hpnicfAtmDxiConfMode }
                STATUS current
                DESCRIPTION
                        "This group includes the general nodes about ATM-DXI."
                ::= { hpnicfAtmDxiGroup 2 }

END
