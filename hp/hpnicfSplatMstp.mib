-- ==================================================================
-- Copyright (c) 2010-2013 Hewlett-Packard Development Company, L.P.
--
-- Description: MSTP MIB
-- Reference:
-- Version: V1.15
-- History:
--      v1.0 (1) Created by Zhang Shilin, 2001.6.29
--           (2) Revised by Qi Zhenglin, 2002.01.08
--      v1.01 2004-7-13 remove default value
--         of hpnicfdot1sMstDefaultVlanAllo & hpnicfdot1sMstDefaultRegionName
--      v1.02 2004-08-19 Revised by Song Jianyong,
--            add hpnicfdot1sStpPathCostStandard in mstp global table
--      v1.1 2004-10-12 updated by gaolong
--           Import OBJECT-IDENTITY, NOTIFICATION-TYPE, TEXTUAL-CONVENTION.
--           Import dot1dStpPort.
--           Relocate hpnicfdot1sMstp MODULE-IDENTITY clause.
--           Fix default value errors for hpnicfdot1sMstBpduGuard, hpnicfdot1sMstiStpPortEdgeport,
--           hpnicfdot1sMstiStpStatus, hpnicfdot1sMstiPortRootGuard, hpnicfdot1sMstiPortLoopGuard.
--      v1.11 2004-10-23 Revised by Song Jianyong,
--            modify the range of hpnicfdot1sMstiPathCost value in hpnicfdot1sPortTable
--      v1.12 2005-01-22 Revised by Song Jianyong,
--            Add an enumeration for hpnicfdot1sStpForceVersion in mstp global table
--            Add an enumeration for hpnicfdot1sStpPathCostStandard in hpnicfdot1sPortTable
--            Adjust format of objects' description
--     V1.13 2005-6-30 Updated by zhanghaihong
--            add hpnicfdot1sMstiStpPortSendingBPDUType, hpnicfdot1sMstiStpOperPortPointToPoint
--            in hpnicfdot1sPortTable
--     V1.14 2005-11-07 Updated by zhanghaihong
--            Modify the description of hpnicfdot1sMstiStpOperPortPointToPoint in
--            hpnicfdot1sPortTable.
--            Add hpnicfdot1sMstiStpPortAdminBPDUFmt, hpnicfdot1sMstiStpPortOperBPDUFmt
--            in hpnicfdot1sPortTable.
--     V1.15 2011-8-11 Updated by zhangwei
--            Modify the range of hpnicfdot1sAdminMstID, hpnicfdot1sOperMstID in
--            hpnicfdot1sPortTable and hpnicfdot1sInstanceID in hpnicfdot1sInstanceTable.
--            Remove the default value of hpnicfdot1sMstiStpTransLimit.
--            Add hpnicfdot1sMstiStpPortRoleRestriction, hpnicfdot1sMstiStpPortTcRestriction and
--            hpnicfdot1sMstiStpPortDisputed in hpnicfdot1sPortTable.
-- ==================================================================
-- ==================================================================
--
-- Variables and types be imported
--
-- ==================================================================
-- ------------------------------------------------------------------
-- ------------------------------------------------------------------
HPN-ICF-LswMSTP-MIB DEFINITIONS ::= BEGIN

IMPORTS

    MODULE-IDENTITY,OBJECT-TYPE,Counter32, OBJECT-IDENTITY, NOTIFICATION-TYPE
        FROM SNMPv2-SMI
    TEXTUAL-CONVENTION, TruthValue
        FROM SNMPv2-TC
    dot1dStpPortEntry, dot1dStpPort
        FROM BRIDGE-MIB
    hpnicflswCommon
        FROM HPN-ICF-OID-MIB;

    hpnicfdot1sMstp MODULE-IDENTITY
            LAST-UPDATED "200106290000Z"
            ORGANIZATION
                ""
            CONTACT-INFO
                ""
            DESCRIPTION
            ""
            REVISION "200106290000Z"
            DESCRIPTION
            ""
            ::= { hpnicflswCommon  14 }

    EnabledStatus ::= TEXTUAL-CONVENTION
    STATUS      current
    DESCRIPTION
        "A simple status value for the object."
    SYNTAX      INTEGER { enabled(1), disabled(2) }

    BridgeId ::= OCTET STRING (SIZE (8))

    Hpnicfdot1sFormatStatus ::= TEXTUAL-CONVENTION
    STATUS      current
    DESCRIPTION
        "Legacy means that the BPDU format is legacy.  Dot1s means that the
        BPDU format is IEEE 802.1s.  Auto means that the format of BPDU sending
        on the port is determined by the BPDU format of its connective port."
    SYNTAX      INTEGER { legacy(1), dot1s(2), auto(3) }


  hpnicfdot1sStpStatus OBJECT-TYPE
    SYNTAX      EnabledStatus
    MAX-ACCESS  read-write
    STATUS      current
    DESCRIPTION
      "Whether the Bridge MSTP is enabled."
    DEFVAL      { 2 }
    ::= { hpnicfdot1sMstp 1 }

  hpnicfdot1sStpForceVersion OBJECT-TYPE
    SYNTAX      INTEGER{stp(0),rstp(2),mstp(3)}
    MAX-ACCESS  read-write
    STATUS      current
    DESCRIPTION
      " The mode of this Bridge spanning-tree protocol."
    DEFVAL      { mstp}
    ::= { hpnicfdot1sMstp 2 }

  hpnicfdot1sStpDiameter OBJECT-TYPE
    SYNTAX      INTEGER(2..7)
    MAX-ACCESS  read-write
    STATUS      current
    DESCRIPTION
      "The diameter of Bridge."
    DEFVAL      { 7}
    ::= { hpnicfdot1sMstp 3 }

  hpnicfdot1sMstBridgeMaxHops OBJECT-TYPE
    SYNTAX      INTEGER(1..40)
    MAX-ACCESS  read-write
    STATUS      current
    DESCRIPTION
      "The maximum value of the  Bridge hops."
    DEFVAL      { 20}
    ::= { hpnicfdot1sMstp 4 }

  hpnicfdot1sMstMasterBridgeID OBJECT-TYPE
    SYNTAX      BridgeId
    MAX-ACCESS  read-only
    STATUS      current
    DESCRIPTION
      "The Bridge Identifier of the current Master Bridge."
    ::= { hpnicfdot1sMstp 5 }

  hpnicfdot1sMstMasterPathCost OBJECT-TYPE
    SYNTAX      INTEGER
    MAX-ACCESS  read-only
    STATUS      current
    DESCRIPTION
      "The CIST path cost from the transmitting Bridge to the Master Bridge."
    DEFVAL      { 0}
    ::= { hpnicfdot1sMstp 6 }

  hpnicfdot1sMstBpduGuard OBJECT-TYPE
    SYNTAX      EnabledStatus
    MAX-ACCESS  read-write
    STATUS      current
    DESCRIPTION
      "Whether the Bridge BPDU Guard function is enabled. If the function
      is enabled, the port will shutdown when received BPDU and the port
      is configured as portfast."
    DEFVAL      { disabled}
    ::= { hpnicfdot1sMstp 7 }

  hpnicfdot1sMstAdminFormatSelector OBJECT-TYPE
    SYNTAX      INTEGER
    MAX-ACCESS  read-write
    STATUS      current
    DESCRIPTION
      "The administrative Configuration Identifier Format Selector in use
      by the Bridge. This has a value of 0 indicate the format specified
      in the Standard of IEEE 802.1s."
    DEFVAL      { 0}
    ::= { hpnicfdot1sMstp 8 }

  hpnicfdot1sMstAdminRegionName OBJECT-TYPE
    SYNTAX      OCTET STRING(SIZE(1..32))
    MAX-ACCESS  read-write
    STATUS      current
    DESCRIPTION
      "This MSTP administrative region name."
    ::= { hpnicfdot1sMstp 9 }

  hpnicfdot1sMstAdminRevisionLevel OBJECT-TYPE
    SYNTAX      INTEGER(0..65535)
    MAX-ACCESS  read-write
    STATUS      current
    DESCRIPTION
      "This MSTP administrative revision level."
    DEFVAL      { 0}
    ::= { hpnicfdot1sMstp 10 }

  hpnicfdot1sMstOperFormatSelector OBJECT-TYPE
    SYNTAX      INTEGER
    MAX-ACCESS  read-only
    STATUS      current
    DESCRIPTION
      "The operative Configuration Identifier Format Selector in use by the
      Bridge. This has a value of 0 indicate the format specified in the
      Standard of IEEE 802.1s."
    DEFVAL      { 0}
    ::= { hpnicfdot1sMstp 11 }

  hpnicfdot1sMstOperRegionName OBJECT-TYPE
    SYNTAX      OCTET STRING( SIZE(0..32) )
    MAX-ACCESS  read-only
    STATUS      current
    DESCRIPTION
      "This MSTP operative region name."
    ::= { hpnicfdot1sMstp 12 }

  hpnicfdot1sMstOperRevisionLevel OBJECT-TYPE
    SYNTAX      INTEGER(0..65535)
    MAX-ACCESS  read-only
    STATUS      current
    DESCRIPTION
      "This MSTP operative revision level."
    DEFVAL      { 0}
    ::= { hpnicfdot1sMstp 13 }

  hpnicfdot1sMstOperConfigDigest OBJECT-TYPE
    SYNTAX      OCTET STRING(SIZE(0..16))
    MAX-ACCESS  read-only
    STATUS      current
    DESCRIPTION
      "This MSTP Region's Configuration Digest Signature Key."
    ::= { hpnicfdot1sMstp 14 }

  hpnicfdot1sMstRegionConfActive OBJECT-TYPE
    SYNTAX      INTEGER{enable(1),disable(2)}
    MAX-ACCESS  read-write
    STATUS      current
    DESCRIPTION
      "Active the region configuration."
    DEFVAL      { disable }
    ::= { hpnicfdot1sMstp 15 }

  hpnicfdot1sMstDefaultVlanAllo OBJECT-TYPE
    SYNTAX      INTEGER{enable(1),unused(65535)}
    MAX-ACCESS  read-write
    STATUS      current
    DESCRIPTION
      "Set default configuration about VLAN allocation and all VLANs
      are mapped to CIST."
    ::= { hpnicfdot1sMstp 16 }

  hpnicfdot1sMstDefaultRegionName OBJECT-TYPE
    SYNTAX      INTEGER{enable(1),unused(65535)}
    MAX-ACCESS  read-write
    STATUS      current
    DESCRIPTION
      "Set default region name."
    ::= { hpnicfdot1sMstp 17 }

-- TABLE: hpnicfdot1sVIDAllocationTable ------
  hpnicfdot1sVIDAllocationTable OBJECT-TYPE
    SYNTAX      SEQUENCE OF Hpnicfdot1sVIDAllocationEntry
    MAX-ACCESS  not-accessible
    STATUS      current
    DESCRIPTION
      ""
    ::= { hpnicfdot1sMstp 18 }

  hpnicfdot1sVIDAllocationEntry OBJECT-TYPE
    SYNTAX      Hpnicfdot1sVIDAllocationEntry
    MAX-ACCESS  not-accessible
    STATUS      current
    DESCRIPTION
      ""
    INDEX {
              hpnicfdot1sMstVID
             }
    ::= { hpnicfdot1sVIDAllocationTable 1 }

  Hpnicfdot1sVIDAllocationEntry ::=
    SEQUENCE
    {
      hpnicfdot1sMstVID INTEGER,
      hpnicfdot1sAdminMstID INTEGER,
      hpnicfdot1sOperMstID  INTEGER
    }

  hpnicfdot1sMstVID OBJECT-TYPE
    SYNTAX      INTEGER(1..4094)
    MAX-ACCESS  read-only
    STATUS      current
    DESCRIPTION
        "VLAN Identifier"
    ::={ hpnicfdot1sVIDAllocationEntry 1 }

  hpnicfdot1sAdminMstID OBJECT-TYPE
    SYNTAX      INTEGER(0..4094)
    MAX-ACCESS  read-write
    STATUS      current
    DESCRIPTION
        "Administrative Multiple spanning-tree instance Identifier."
    ::={ hpnicfdot1sVIDAllocationEntry 2 }

  hpnicfdot1sOperMstID OBJECT-TYPE
    SYNTAX      INTEGER(0..4094)
    MAX-ACCESS  read-only
    STATUS      current
    DESCRIPTION
        "Operative Multiple spanning-tree instance Identifier."
    ::={ hpnicfdot1sVIDAllocationEntry 3 }

-- TABLE: hpnicfdot1sInstanceTable ------
  hpnicfdot1sInstanceTable OBJECT-TYPE
    SYNTAX      SEQUENCE OF Hpnicfdot1sInstanceEntry
    MAX-ACCESS  not-accessible
    STATUS      current
    DESCRIPTION
      ""
    ::= { hpnicfdot1sMstp 19 }

  hpnicfdot1sInstanceEntry OBJECT-TYPE
    SYNTAX      Hpnicfdot1sInstanceEntry
    MAX-ACCESS  not-accessible
    STATUS      current
    DESCRIPTION
      ""
    INDEX {
              hpnicfdot1sInstanceID
             }
    ::= { hpnicfdot1sInstanceTable 1 }

  Hpnicfdot1sInstanceEntry ::=
    SEQUENCE
    {
      hpnicfdot1sInstanceID INTEGER,
      hpnicfdot1sMstiBridgeID   BridgeId,
      hpnicfdot1sMstiBridgePriority INTEGER,
      hpnicfdot1sMstiDesignedRoot   BridgeId,
      hpnicfdot1sMstiRootPathCost   INTEGER,
      hpnicfdot1sMstiRootPort   INTEGER,
      hpnicfdot1sMstiRootType   INTEGER,
      hpnicfdot1sMstiRemainingHops  INTEGER,
      hpnicfdot1sMstiAdminMappedVlanListLow OCTET STRING,
      hpnicfdot1sMstiAdminMappedVlanListHigh OCTET STRING,
      hpnicfdot1sMstiOperMappedVlanListLow OCTET STRING,
      hpnicfdot1sMstiOperMappedVlanListHigh OCTET STRING
    }

  hpnicfdot1sInstanceID OBJECT-TYPE
    SYNTAX      INTEGER(0..4094)
    MAX-ACCESS  read-only
    STATUS      current
    DESCRIPTION
        "Multiple spanning-tree instance Identifier"
    ::={ hpnicfdot1sInstanceEntry 1 }

  hpnicfdot1sMstiBridgeID OBJECT-TYPE
    SYNTAX      BridgeId
    MAX-ACCESS  read-only
    STATUS      current
    DESCRIPTION
        "The Bridge Identifier for the spanning tree instance
        identified by MSTID"
    ::={ hpnicfdot1sInstanceEntry 2 }

  hpnicfdot1sMstiBridgePriority OBJECT-TYPE
    SYNTAX      INTEGER(0..61440)
    MAX-ACCESS  read-write
    STATUS      current
    DESCRIPTION
        "The Bridge Priority for the spanning tree instance
        identified by MSTID. Step of 4096"
    DEFVAL      { 32768 }
    ::={ hpnicfdot1sInstanceEntry 3 }

  hpnicfdot1sMstiDesignedRoot OBJECT-TYPE
    SYNTAX      BridgeId
    MAX-ACCESS  read-only
    STATUS      current
    DESCRIPTION
        "The Bridge Identifier of the Root Bridge for the spanning
        tree instance identified by MSTID"
    ::={ hpnicfdot1sInstanceEntry 4 }

  hpnicfdot1sMstiRootPathCost OBJECT-TYPE
    SYNTAX      INTEGER
    MAX-ACCESS  read-only
    STATUS      current
    DESCRIPTION
        "The path cost from the transmitting Bridge to the Root Bridge
        for the spanning tree instance  identified by MSTID"
    ::={ hpnicfdot1sInstanceEntry 5 }

  hpnicfdot1sMstiRootPort OBJECT-TYPE
    SYNTAX      INTEGER
    MAX-ACCESS  read-only
    STATUS      current
    DESCRIPTION
        "The Root Port for the spanning tree instance identified by the MSTID"
    ::={ hpnicfdot1sInstanceEntry 6 }

  hpnicfdot1sMstiRootType OBJECT-TYPE
    SYNTAX      INTEGER{normal(0), secondary(1), primary(2)}
    MAX-ACCESS  read-write
    STATUS      current
    DESCRIPTION
        "Config this Bridge as a primary root or secondary root and or cancel
        the root for this spanning tree instance  identified by MSTID"
    DEFVAL      { normal }
    ::={ hpnicfdot1sInstanceEntry 7 }

  hpnicfdot1sMstiRemainingHops OBJECT-TYPE
    SYNTAX      INTEGER
    MAX-ACCESS  read-only
    STATUS      current
    DESCRIPTION
        "The remaining hops of the spanning tree instance  identified by MSTID"
    ::={ hpnicfdot1sInstanceEntry 8 }

  hpnicfdot1sMstiAdminMappedVlanListLow  OBJECT-TYPE
    SYNTAX  OCTET STRING (SIZE(0..256))
    MAX-ACCESS read-only
    STATUS current
    DESCRIPTION
        " The lower part of administrative Vlan list mapped to the spanning
        tree instance identified by MSTID"
    ::= { hpnicfdot1sInstanceEntry 9 }

  hpnicfdot1sMstiAdminMappedVlanListHigh  OBJECT-TYPE
    SYNTAX  OCTET STRING (SIZE(0..256))
    MAX-ACCESS read-only
    STATUS current
    DESCRIPTION
        " The higher part of administrative Vlan  list mapped to the spanning
        tree instance identified by MSTID"
    ::= { hpnicfdot1sInstanceEntry 10 }

  hpnicfdot1sMstiOperMappedVlanListLow  OBJECT-TYPE
    SYNTAX  OCTET STRING (SIZE(0..256))
    MAX-ACCESS read-only
    STATUS current
    DESCRIPTION
        " The lower part of operative Vlan list mapped to the spanning
        tree instance identified by MSTID"
    ::= { hpnicfdot1sInstanceEntry 11 }

  hpnicfdot1sMstiOperMappedVlanListHigh  OBJECT-TYPE
    SYNTAX  OCTET STRING (SIZE(0..256))
    MAX-ACCESS read-only
    STATUS current
    DESCRIPTION
        " The higher part of operative Vlan list mapped to the spanning
        tree instance identified by MSTID"
    ::= { hpnicfdot1sInstanceEntry 12 }

-- TABLE: hpnicfdot1sPortTable ------
  hpnicfdot1sPortTable OBJECT-TYPE
    SYNTAX      SEQUENCE OF Hpnicfdot1sPortEntry
    MAX-ACCESS  not-accessible
    STATUS      current
    DESCRIPTION
      ""
    ::= { hpnicfdot1sMstp 20 }

  hpnicfdot1sPortEntry OBJECT-TYPE
    SYNTAX      Hpnicfdot1sPortEntry
    MAX-ACCESS  not-accessible
    STATUS      current
    DESCRIPTION
      ""
    INDEX {   hpnicfdot1sInstanceID,
              hpnicfdot1sMstiPortIndex
             }
    ::= { hpnicfdot1sPortTable 1 }

  Hpnicfdot1sPortEntry ::=
    SEQUENCE
    {
      hpnicfdot1sMstiPortIndex  INTEGER,
      hpnicfdot1sMstiState  INTEGER,
      hpnicfdot1sMstiPortPriority   INTEGER,
      hpnicfdot1sMstiPathCost   INTEGER,
      hpnicfdot1sMstiDesignatedRoot BridgeId,
      hpnicfdot1sMstiDesignatedCost INTEGER,
      hpnicfdot1sMstiDesignatedBridge   BridgeId,
      hpnicfdot1sMstiDesignatedPort OCTET STRING,
      hpnicfdot1sMstiMasterBridgeID BridgeId,
      hpnicfdot1sMstiMasterPortCost INTEGER,
      hpnicfdot1sMstiStpPortEdgeport    EnabledStatus,
      hpnicfdot1sMstiStpPortPointToPoint    INTEGER,
      hpnicfdot1sMstiStpMcheck  INTEGER,
      hpnicfdot1sMstiStpTransLimit  INTEGER,
      hpnicfdot1sMstiStpRXStpBPDU   Counter32,
      hpnicfdot1sMstiStpTXStpBPDU   Counter32,
      hpnicfdot1sMstiStpRXTCNBPDU   Counter32,
      hpnicfdot1sMstiStpTXTCNBPDU   Counter32,
      hpnicfdot1sMstiStpRXRSTPBPDU  Counter32,
      hpnicfdot1sMstiStpTXRSTPBPDU  Counter32,
      hpnicfdot1sMstiStpRXMSTPBPDU  Counter32,
      hpnicfdot1sMstiStpTXMSTPBPDU  Counter32,
      hpnicfdot1sMstiStpClearStatistics INTEGER,
      hpnicfdot1sMstiStpDefaultPortCost INTEGER,
      hpnicfdot1sMstiStpStatus  EnabledStatus,
      hpnicfdot1sMstiPortRootGuard  EnabledStatus,
      hpnicfdot1sMstiPortLoopGuard  EnabledStatus,
      hpnicfdot1sMstiStpPortSendingBPDUType  INTEGER,
      hpnicfdot1sMstiStpOperPortPointToPoint INTEGER,
      hpnicfdot1sMstiStpPortAdminBPDUFmt  Hpnicfdot1sFormatStatus,
      hpnicfdot1sMstiStpPortOperBPDUFmt  Hpnicfdot1sFormatStatus,
      hpnicfdot1sMstiStpPortRoleRestriction  EnabledStatus,
      hpnicfdot1sMstiStpPortTcRestriction  EnabledStatus,
      hpnicfdot1sMstiStpPortDisputed  TruthValue
    }

  hpnicfdot1sMstiPortIndex OBJECT-TYPE
    SYNTAX      INTEGER
    MAX-ACCESS  read-only
    STATUS      current
    DESCRIPTION
        "The index of the Bridge Port"
    ::={ hpnicfdot1sPortEntry 1 }

  hpnicfdot1sMstiState OBJECT-TYPE
    SYNTAX      INTEGER{disabled(1),discarding(2),learning(4),forwarding(5)}
    MAX-ACCESS  read-only
    STATUS      current
    DESCRIPTION
        "The current state of the Port (i.e., Disabled, Discarding ,
        Learning, Forwarding)"
    ::={ hpnicfdot1sPortEntry 2 }

  hpnicfdot1sMstiPortPriority OBJECT-TYPE
    SYNTAX      INTEGER(0..240)
    MAX-ACCESS  read-write
    STATUS      current
    DESCRIPTION
        "The value of the priority field which is contained in the
        first (in network byte order)  four bits of the (2 octet long) Port ID.
        The other octet of the Port ID is given by the value of mstiPortIndex.
        And step of 16"
    DEFVAL      { 128 }
    ::={ hpnicfdot1sPortEntry 3 }

  hpnicfdot1sMstiPathCost OBJECT-TYPE
    SYNTAX      INTEGER(1..200000000)
    MAX-ACCESS  read-write
    STATUS      current
    DESCRIPTION
        "The contribution of this port to the path cost of paths towards the
        spanning tree root which include this port. The range of path cost
        is 1..65535 for 802.1d standard, is 1..200000000 for 802.1t standard,
        and is 1..200000 for the legacy standard. "
    ::={ hpnicfdot1sPortEntry 4 }

  hpnicfdot1sMstiDesignatedRoot OBJECT-TYPE
    SYNTAX      BridgeId
    MAX-ACCESS  read-only
    STATUS      current
    DESCRIPTION
        "The Bridge Identifier of the Root Bridge for the port of the Spanning
         Tree instance identified by the MSTID"
    ::={ hpnicfdot1sPortEntry 5 }

  hpnicfdot1sMstiDesignatedCost OBJECT-TYPE
    SYNTAX      INTEGER
    MAX-ACCESS  read-only
    STATUS      current
    DESCRIPTION
        "The path cost of the Designated Port of the segment connected to
        this port.  This value is compared to the Root Path Cost field
        in received bridge PDUs."
    ::={ hpnicfdot1sPortEntry 6 }

  hpnicfdot1sMstiDesignatedBridge OBJECT-TYPE
    SYNTAX      BridgeId
    MAX-ACCESS  read-only
    STATUS      current
    DESCRIPTION
        "The Bridge Identifier of the bridge which this port considers to
        be the Designated Bridge for this port's segment."
    ::={ hpnicfdot1sPortEntry 7 }

  hpnicfdot1sMstiDesignatedPort OBJECT-TYPE
    SYNTAX      OCTET STRING(SIZE (2))
    MAX-ACCESS  read-only
    STATUS      current
    DESCRIPTION
        "The Port Identifier of the port on the Designated Bridge
        for this port's segment."
    ::={ hpnicfdot1sPortEntry 8 }

  hpnicfdot1sMstiMasterBridgeID OBJECT-TYPE
    SYNTAX      BridgeId
    MAX-ACCESS  read-only
    STATUS      current
    DESCRIPTION
        "The Bridge Idnetifier of the current Master Bridge.
        Effective in CIST."
    ::={ hpnicfdot1sPortEntry 9 }

  hpnicfdot1sMstiMasterPortCost OBJECT-TYPE
    SYNTAX      INTEGER
    MAX-ACCESS  read-only
    STATUS      current
    DESCRIPTION
        "The CIST path cost from the transmitting Bridge to
        the Master Bridge. Effective in CIST."
    ::={ hpnicfdot1sPortEntry 10 }

  hpnicfdot1sMstiStpPortEdgeport OBJECT-TYPE
    SYNTAX      EnabledStatus
    MAX-ACCESS  read-write
    STATUS      current
    DESCRIPTION
        " Whether the port fast is enabled. Effective in CIST."
    DEFVAL      { disabled }
    ::={ hpnicfdot1sPortEntry 11 }

  hpnicfdot1sMstiStpPortPointToPoint OBJECT-TYPE
    SYNTAX      INTEGER{forceTrue (1),forceFalse (2),auto  (3)}
    MAX-ACCESS  read-write
    STATUS      current
    DESCRIPTION
        " Whether the port connects the point to point link. Effective in CIST."
    DEFVAL      { auto }
    ::={ hpnicfdot1sPortEntry 12 }

  hpnicfdot1sMstiStpMcheck OBJECT-TYPE
    SYNTAX      INTEGER{enable(1),unused(65535)}
    MAX-ACCESS  read-write
    STATUS      current
    DESCRIPTION
        " Forcing the state machine to send MST BPDUs in this manner
        can be used to test whether all legacy Bridges on a given LAN
        have been removed. Effective in CIST."
    ::={ hpnicfdot1sPortEntry 13 }

  hpnicfdot1sMstiStpTransLimit OBJECT-TYPE
    SYNTAX      INTEGER(1..255)
    MAX-ACCESS  read-write
    STATUS      current
    DESCRIPTION
        "The value used by the Port Transmit state machine to limit
        the maximum transmission rate. Effective in CIST."
    ::={ hpnicfdot1sPortEntry 14 }

  hpnicfdot1sMstiStpRXStpBPDU OBJECT-TYPE
    SYNTAX      Counter32
    MAX-ACCESS  read-only
    STATUS      current
    DESCRIPTION
        "The number of received Config BPDU. Effective in CIST."
    ::={ hpnicfdot1sPortEntry 15 }

  hpnicfdot1sMstiStpTXStpBPDU OBJECT-TYPE
    SYNTAX      Counter32
    MAX-ACCESS  read-only
    STATUS      current
    DESCRIPTION
        "The number of transmitted Config BPDU. Effective in CIST."
    ::={ hpnicfdot1sPortEntry 16 }

  hpnicfdot1sMstiStpRXTCNBPDU OBJECT-TYPE
    SYNTAX      Counter32
    MAX-ACCESS  read-only
    STATUS      current
    DESCRIPTION
        "The number of received TCN BPDU. Effective in CIST."
    ::={ hpnicfdot1sPortEntry 17 }

  hpnicfdot1sMstiStpTXTCNBPDU OBJECT-TYPE
    SYNTAX      Counter32
    MAX-ACCESS  read-only
    STATUS      current
    DESCRIPTION
        "The number of transimitted TCN BPDU. Effective in CIST."
    ::={ hpnicfdot1sPortEntry 18 }

  hpnicfdot1sMstiStpRXRSTPBPDU OBJECT-TYPE
    SYNTAX      Counter32
    MAX-ACCESS  read-only
    STATUS      current
    DESCRIPTION
        "The number of received RST BPDU. Effective in CIST."
    ::={ hpnicfdot1sPortEntry 19 }

  hpnicfdot1sMstiStpTXRSTPBPDU OBJECT-TYPE
    SYNTAX      Counter32
    MAX-ACCESS  read-only
    STATUS      current
    DESCRIPTION
        "The number of transimitted RST BPDU. Effective in CIST."
    ::={ hpnicfdot1sPortEntry 20 }

  hpnicfdot1sMstiStpRXMSTPBPDU OBJECT-TYPE
    SYNTAX      Counter32
    MAX-ACCESS  read-only
    STATUS      current
    DESCRIPTION
        "The number of received MST BPDU. Effective in CIST."
    ::={ hpnicfdot1sPortEntry 21 }

  hpnicfdot1sMstiStpTXMSTPBPDU OBJECT-TYPE
    SYNTAX      Counter32
    MAX-ACCESS  read-only
    STATUS      current
    DESCRIPTION
        "The number of transimitted MST BPDU. Effective in CIST."
    ::={ hpnicfdot1sPortEntry 22 }

  hpnicfdot1sMstiStpClearStatistics OBJECT-TYPE
    SYNTAX      INTEGER{clear(1),unused(65535)}
    MAX-ACCESS  read-write
    STATUS      current
    DESCRIPTION
        "Clear the spanning tree statistic. Effective in CIST."
    ::={ hpnicfdot1sPortEntry 23 }

  hpnicfdot1sMstiStpDefaultPortCost OBJECT-TYPE
    SYNTAX      INTEGER{enable(1),unused(65535)}
    MAX-ACCESS  read-write
    STATUS      current
    DESCRIPTION
        "Set default Port path cost. "
    ::={ hpnicfdot1sPortEntry 24 }

  hpnicfdot1sMstiStpStatus OBJECT-TYPE
    SYNTAX      EnabledStatus
    MAX-ACCESS  read-write
    STATUS      current
    DESCRIPTION
        "Whether the spanning tree protocol is enabled on this port.
        Effective in CIST."
    DEFVAL      { enabled}
    ::={ hpnicfdot1sPortEntry 25 }

  hpnicfdot1sMstiPortRootGuard OBJECT-TYPE
    SYNTAX      EnabledStatus
    MAX-ACCESS  read-write
    STATUS      current
    DESCRIPTION
        "Whether the root guard is enabled. Effective in CIST."
    DEFVAL      { disabled }
    ::={ hpnicfdot1sPortEntry 26 }

  hpnicfdot1sMstiPortLoopGuard OBJECT-TYPE
    SYNTAX      EnabledStatus
    MAX-ACCESS  read-write
    STATUS      current
    DESCRIPTION
        "Whether the loop protection is enabled. Effective in CIST."
    DEFVAL      { disabled }
    ::={ hpnicfdot1sPortEntry 27 }

  hpnicfdot1sMstiStpPortSendingBPDUType  OBJECT-TYPE
    SYNTAX  INTEGER {
                    stp(1),
                    rstp(2),
                    mstp(3)
                    }
    MAX-ACCESS read-only
    STATUS     current
    DESCRIPTION
        "Type of BPDU which the port is sending."
    ::= { hpnicfdot1sPortEntry 28 }

  hpnicfdot1sMstiStpOperPortPointToPoint  OBJECT-TYPE
    SYNTAX  INTEGER {
                    true(1),
                    false(2)
                    }
    MAX-ACCESS read-only
    STATUS current
    DESCRIPTION
        "This object indicates whether the port has connected to a
        point-to-point link or not.  The value of the node is an operative value.
        The administrative value can be read from the node
        hpnicfdot1sMstiStpPortPointToPoint.  If the value of
        hpnicfdot1sMstiStpPortPointToPoint is auto, the value of this node
        should be calculated by the network topology of this port.  If the
        value of hpnicfdot1sMstiStpPortPointToPoint is forceFalse, the value of this
        node is false.  If the value of hpnicfdot1sMstiStpPortPointToPoint is
        forceTrue, the value of this node is true."
    ::= { hpnicfdot1sPortEntry 29 }

  hpnicfdot1sMstiStpPortAdminBPDUFmt  OBJECT-TYPE
    SYNTAX     Hpnicfdot1sFormatStatus
    MAX-ACCESS read-write
    STATUS     current
    DESCRIPTION
       "The value of the node is an administrative value.  Value legacy means that
       the MST BPDU format is forced to legacy.  Value dot1s means that the MST BPDU format
       is forced to IEEE 802.1s.  Value auto means that the format of MST BPDU sending
       on the port is determined by the MST BPDU that the port has received.  Effective in
       CIST."
      ::= { hpnicfdot1sPortEntry 30 }

  hpnicfdot1sMstiStpPortOperBPDUFmt  OBJECT-TYPE
    SYNTAX     Hpnicfdot1sFormatStatus
    MAX-ACCESS read-only
    STATUS     current
    DESCRIPTION
      "The format of MST BPDU which the port is sending.  Value legacy means that the
      format of MST BPDU sending on the port is legacy.  Value dot1s means that the
      format of MST BPDU sending on the port is IEEE 802.1s.  Effective in CIST."
    ::= { hpnicfdot1sPortEntry 31 }

  hpnicfdot1sMstiStpPortRoleRestriction OBJECT-TYPE
    SYNTAX      EnabledStatus
    MAX-ACCESS  read-write
    STATUS      current
    DESCRIPTION
        "Whether the role-restriction is enabled.  Effective in CIST.
         The role-restriction causes the port not to be selected as root port for the
         CIST or any MSTI."
    DEFVAL      { disabled }
    ::= { hpnicfdot1sPortEntry 32 }

  hpnicfdot1sMstiStpPortTcRestriction OBJECT-TYPE
    SYNTAX      EnabledStatus
    MAX-ACCESS  read-write
    STATUS      current
    DESCRIPTION
        "Whether the tc-restriction is enabled.  Effective in CIST.
         The tc-restriction causes the port not to propagate topology changes to
         other ports."
    DEFVAL      { disabled }
    ::= { hpnicfdot1sPortEntry 33 }

  hpnicfdot1sMstiStpPortDisputed OBJECT-TYPE
    SYNTAX      TruthValue
    MAX-ACCESS  read-only
    STATUS      current
    DESCRIPTION
        "Whether the port is disputed for the CIST or MSTI."
    ::= { hpnicfdot1sPortEntry 34 }

  hpnicfdot1sStpPathCostStandard  OBJECT-TYPE
    SYNTAX      INTEGER{legacy(0),dot1d-1998(1),dot1t(2)}
    MAX-ACCESS  read-write
    STATUS      current
    DESCRIPTION
      "Path cost standard of the bridge.  Value dot1d-1998 is
      IEEE 802.1d standard in 1998, value dot1t is IEEE 802.1t standard,
      and value legacy is a private legacy standard."
    ::= { hpnicfdot1sMstp 21 }

--  Mstp Traps

  hpnicfMstpEventsV2 OBJECT-IDENTITY
     STATUS      current
     DESCRIPTION "Definition point for Mstp notifications."
     ::= { hpnicfdot1sMstp 0 }

  hpnicfPortMstiStateForwarding NOTIFICATION-TYPE
     OBJECTS  { hpnicfdot1sInstanceID , hpnicfdot1sMstiPortIndex}
     STATUS   current
     DESCRIPTION
         "The SNMP trap that is generated when a port turns into
         forwarding state form other state."
     ::= { hpnicfMstpEventsV2 1 }

  hpnicfPortMstiStateDiscarding NOTIFICATION-TYPE
     OBJECTS  { hpnicfdot1sInstanceID , hpnicfdot1sMstiPortIndex}
     STATUS   current
     DESCRIPTION
         "The SNMP trap that is generated when a port turns into
         discarding state form forwarding state."
     ::= { hpnicfMstpEventsV2 2 }


  hpnicfBridgeLostRootPrimary NOTIFICATION-TYPE
     OBJECTS  { hpnicfdot1sInstanceID }
     STATUS   current
     DESCRIPTION
         "The SNMP trap that is generated when the bridge is no longer
         the root bridge of the instance. Another switch with higher
         priority has already been the root bridge of the instance."
     ::= { hpnicfMstpEventsV2 3 }

  hpnicfPortMstiRootGuarded NOTIFICATION-TYPE
     OBJECTS  { hpnicfdot1sInstanceID , hpnicfdot1sMstiPortIndex}
     STATUS   current
     DESCRIPTION
         "The SNMP trap that is generated when a root-guard port
         receives a superior message on the relevant instance."
     ::= { hpnicfMstpEventsV2 4 }

  hpnicfPortMstiBpduGuarded NOTIFICATION-TYPE
     OBJECTS  { dot1dStpPort }
     STATUS   current
     DESCRIPTION
         "The SNMP trap that is generated when an edged port of
         the BPDU-guard switch receives BPDU packets."
     ::= { hpnicfMstpEventsV2 5 }

  hpnicfPortMstiLoopGuarded NOTIFICATION-TYPE
     OBJECTS  { hpnicfdot1sInstanceID , hpnicfdot1sMstiPortIndex}
     STATUS   current
     DESCRIPTION
         "The SNMP trap that is generated when an Alternate-Port
         or Root-Port is aged out."
     ::= { hpnicfMstpEventsV2 6 }

END
