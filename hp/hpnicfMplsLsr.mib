-- =========================================================================
-- Copyright (c) 2010-2013 Hewlett-Packard Development Company, L.P.
--
-- Description:This file describes the MIB implementation of mpls lsr.
-- Reference:
-- Version: V1.0
-- History:
-- 	    V1.0 6th Mar 2004
--		Initial version
-- =========================================================================
HPN-ICF-MPLS-LSR-MIB DEFINITIONS ::= BEGIN

IMPORTS
   MODULE-IDENTITY, OBJECT-TYPE, NOTIFICATION-TYPE,
   Integer32, Counter32, Unsigned32,
   Counter64, Gauge32
      FROM SNMPv2-SMI
      
   MODULE-COMPLIANCE, OBJECT-GROUP, NOTIFICATION-GROUP
      FROM SNMPv2-CONF
      
   TEXTUAL-CONVENTION, TruthValue, RowStatus, StorageType,
   RowPointer, TimeStamp
      FROM SNMPv2-TC
      
   InterfaceIndex, InterfaceIndexOrZero
      FROM IF-MIB

   hpnicfMpls
      FROM HPN-ICF-OID-MIB

   AddressFamilyNumbers
      FROM IANA-ADDRESS-FAMILY-NUMBERS-MIB
      
   InetAddressIPv4, InetAddressIPv6, InetAddressType
      FROM INET-ADDRESS-MIB;

hpnicfMplsLsr MODULE-IDENTITY
   LAST-UPDATED "200007121200Z"  -- 12 July 2000 12:00:00 EST
   ORGANIZATION
       ""
   CONTACT-INFO
       ""
   DESCRIPTION
       "This MIB contains managed object definitions for the
        Multiprotocol Label Switching (MPLS) Router as
        defined in: Rosen, E., Viswanathan, A., and R.
        Callon, Multiprotocol Label Switching Architecture,
        Internet Draft <draft-ietf-mpls-arch-06.txt>,
        August 1999."
   
   -- Revision history.
   REVISION
       "200007121200Z"  -- 12 July 2000 12:00:00 EST
   DESCRIPTION
       "Seventh draft version. Fix minor compilation errors."
   REVISION
       "200007071200Z"  -- 07 July 2000 12:00:00 EST
   DESCRIPTION
       "Sixth draft version. Made minor typographical corrections 
        noted from WG mailing list during second working group last
        call."
   REVISION
       "200004261200Z"  -- 26 April 2000 12:00:00 EST
   DESCRIPTION
       "Fifth draft version. Made minor typographical corrections 
        noted from WG mailing list."
   REVISION
       "200004211200Z"  -- 21 April 2000 12:00:00 EST
   DESCRIPTION
       "Fourth draft version.  Made corrections from WG Last 
        Call comments."
   REVISION
       "200003061200Z"  -- 6 March 2000 12:00:00 EST
   DESCRIPTION
       "Third draft version."
   REVISION
       "200002161200Z"  -- 16 February 2000 12:00:00 EST
   DESCRIPTION
       "Second draft version."
   REVISION
       "199906161200Z"  -- 16 June 1999 12:00:00 EST
   DESCRIPTION
      "Initial draft version."
   ::= { hpnicfMpls 1 }


-- Textual Conventions.

HpnicfMplsLSPID ::= TEXTUAL-CONVENTION
   STATUS        current
   DESCRIPTION
       "An identifier that is assigned to each LSP and is
        used to uniquely identify it.  This is assigned at
        the head end of the LSP and can be used by all LSRs
        to identify this LSP.  This value is piggybacked by
        the signaling protocol when this LSP is signaled
        within the network.  This identifier can then be
        used at each LSR to identify which labels are being
        swapped to other labels for this LSP.  For IPv4
        addresses this results in a 6-octet long cookie."
   SYNTAX        OCTET STRING (SIZE (0..31))

-- An MPLS label.
HpnicfMplsLabel ::= TEXTUAL-CONVENTION
   STATUS        current
   DESCRIPTION
       "This value represents an MPLS label.  Note that the
        contents of a label field are interpreted in an
        interface-type specific fashion.  For example, the
        20-bit wide label carried in the MPLS shim header is
        contained in bits 0-19 and bits 20-31 must be zero.
        The frame relay label can be either 10 or 23 bits
        wide depending on the size of the DLCI field and
        bits 10-31, or 23-31 must be zero, respectively.
        For an ATM interface, bits 0-15 must be interpreted
        as the VCI, bits 16-23 as the VPI and bits 24-31
        must be zero.  Note that the permissible label
        values are also a function of the interface type.
        For example, the value 3 has special semantics in
        the control plane for an MPLS shim header label and
        is not a valid label value in the data path."
   REFERENCE
       "1. MPLS Label Stack Encoding, Rosen et al, draft-
          ietf-mpls-label-encaps-07.txt, March 2000.
        2. Use of Label Switching on Frame Relay Networks,
          Conta et al, draft-ietf-mpls-fr-03.txt, Nov.
          1998.
        3. MPLS using LDP and ATM VC switching, Davie et al,
          draft-ietf-mpls-atm-02.txt, April 1999."
   SYNTAX  Unsigned32 (0..4294967295)

HpnicfMplsBitRate ::= TEXTUAL-CONVENTION
   DISPLAY-HINT "d"
   STATUS      current
   DESCRIPTION
       "An estimate of bandwidth in units of 1,000 bits per
        second.  If this object reports a value of 'n' then
        the rate of the object is somewhere in the range of
        'n-500' to 'n+499'. For objects which do not vary in
        bitrate, or for those where no accurate estimation
        can be made, this object should contain the nominal
        bitrate."
   SYNTAX  Integer32 (1..2147483647)

HpnicfMplsBurstSize ::= TEXTUAL-CONVENTION
   DISPLAY-HINT "d"
   STATUS      current
   DESCRIPTION
       "The number of octets of MPLS data that the stream
        may send back-to-back without concern for policing."
   SYNTAX  Integer32 (1..2147483647)

HpnicfMplsObjectOwner ::= TEXTUAL-CONVENTION
   STATUS      current
   DESCRIPTION
           "The entity which owns the object in question."
   SYNTAX   INTEGER {
                other(1),
                snmp(2),
                ldp(3),
                rsvp(4),
                crldp(5),
                policyAgent(6),
                unknown (7)
             }

-- Top level components of this MIB.

-- Tables, Scalars
hpnicfmplsLsrObjects       OBJECT IDENTIFIER ::= { hpnicfMplsLsr 1 }
-- traps
hpnicfmplsLsrNotifications OBJECT IDENTIFIER ::= { hpnicfMplsLsr 2 }
hpnicfmplsLsrNotifyPrefix OBJECT IDENTIFIER ::= { hpnicfmplsLsrNotifications 0 }
-- conformance
hpnicfmplsLsrConformance   OBJECT IDENTIFIER ::= { hpnicfMplsLsr 3 }


-- MPLS Interface Configuration Table.

hpnicfmplsInterfaceConfTable  OBJECT-TYPE
   SYNTAX        SEQUENCE OF HpnicfMplsInterfaceConfEntry
   MAX-ACCESS    not-accessible
   STATUS        current
   DESCRIPTION
       "This table specifies per-interface MPLS capability
        and associated information."
   ::= { hpnicfmplsLsrObjects 1 }

hpnicfmplsInterfaceConfEntry OBJECT-TYPE
   SYNTAX        HpnicfMplsInterfaceConfEntry
   MAX-ACCESS    not-accessible
   STATUS        current
   DESCRIPTION
       "An entry in this table is created by an LSR for
        every interface capable of supporting MPLS. The
        entry with index 0 represents the per-platform label
        space and contains parameters that apply to all
        interfaces that participate in the per-platform
        label space. Other entries defined in this table
        represent additional MPLS interfaces that may
        participate in either the per-platform or per-
        interface label spaces, or both. Additional
        information about label space participation of an
        interface is provided in the description clause of
        hpnicfmplsInterfaceLabelParticipationType."
   INDEX       { hpnicfmplsInterfaceConfIndex }
      ::= { hpnicfmplsInterfaceConfTable 1 }

HpnicfMplsInterfaceConfEntry ::= SEQUENCE {
  hpnicfmplsInterfaceConfIndex              InterfaceIndexOrZero,
  hpnicfmplsInterfaceLabelMinIn             HpnicfMplsLabel,
  hpnicfmplsInterfaceLabelMaxIn             HpnicfMplsLabel,
  hpnicfmplsInterfaceLabelMinOut            HpnicfMplsLabel,
  hpnicfmplsInterfaceLabelMaxOut            HpnicfMplsLabel,
  hpnicfmplsInterfaceTotalBandwidth         HpnicfMplsBitRate,
  hpnicfmplsInterfaceAvailableBandwidth     HpnicfMplsBitRate,
  hpnicfmplsInterfaceLabelParticipationType BITS,
  hpnicfmplsInterfaceConfStorageType        StorageType
}

hpnicfmplsInterfaceConfIndex OBJECT-TYPE
   SYNTAX        InterfaceIndexOrZero
   MAX-ACCESS    not-accessible
   STATUS        current
   DESCRIPTION
       "This is a unique index for an entry in the
        hpnicfmplsInterfaceConfTable.  A non-zero index for an
        entry indicates the ifIndex for the corresponding
        interface entry in of the MPLS-layer in the ifTable.
        Note that the per-platform label space may apply to
        several interfaces, and therefore the configuration
        of the per-platform label space interface parameters
        will apply to all of the interfaces that are
        participating in the per-platform label space."
   REFERENCE
       "RFC 2233 - The Interfaces Group MIB using SMIv2,
        McCloghrie, K., and F. Kastenholtz, Nov. 1997"
   ::= { hpnicfmplsInterfaceConfEntry 1 }

hpnicfmplsInterfaceLabelMinIn OBJECT-TYPE
   SYNTAX        HpnicfMplsLabel
   MAX-ACCESS    read-only
   STATUS        current
   DESCRIPTION
       "This is the minimum value of an MPLS label that this
        LSR is willing to receive on this interface."
   ::= { hpnicfmplsInterfaceConfEntry 2 }

hpnicfmplsInterfaceLabelMaxIn OBJECT-TYPE
   SYNTAX        HpnicfMplsLabel
   MAX-ACCESS    read-only
   STATUS        current
   DESCRIPTION
       "This is the maximum value of an MPLS label that this
        LSR is willing to receive on this interface."
   ::= { hpnicfmplsInterfaceConfEntry 3 }

hpnicfmplsInterfaceLabelMinOut OBJECT-TYPE
   SYNTAX        HpnicfMplsLabel
   MAX-ACCESS    read-only
   STATUS        current
   DESCRIPTION
       "This is the minimum value of an MPLS label that this
        LSR is willing to send on this interface."
   ::= { hpnicfmplsInterfaceConfEntry 4 }

hpnicfmplsInterfaceLabelMaxOut OBJECT-TYPE
   SYNTAX        HpnicfMplsLabel
   MAX-ACCESS    read-only
   STATUS        current
   DESCRIPTION
       "This is the maximum value of an MPLS label that this
        LSR is willing to send on this interface."
   ::= { hpnicfmplsInterfaceConfEntry 5 }

hpnicfmplsInterfaceTotalBandwidth        OBJECT-TYPE
   SYNTAX        HpnicfMplsBitRate
   MAX-ACCESS    read-only
   STATUS        current
   DESCRIPTION
       "This value indicates the total amount of usable
        bandwidth on this interface and is specified in
        kilobits per second (Kbps).  This variable is
        not applicable when applied to the interface with
        index 0."
::= { hpnicfmplsInterfaceConfEntry 6 }

hpnicfmplsInterfaceAvailableBandwidth       OBJECT-TYPE
   SYNTAX        HpnicfMplsBitRate
   MAX-ACCESS    read-only
   STATUS        current
   DESCRIPTION
       "This value indicates the total amount of available
        bandwidth available on this interface and is
        specified in kilobits per second (Kbps).  This
        value is calculated as the difference between the
        amount of bandwidth currently in use and that
        specified in hpnicfmplsInterfaceTotalBandwidth.  This
        variable is not applicable when applied to the
        interface with index 0."
::= { hpnicfmplsInterfaceConfEntry 7 }

hpnicfmplsInterfaceLabelParticipationType OBJECT-TYPE
   SYNTAX  BITS {
                perPlatform (0),
                perInterface (1)
              }
   MAX-ACCESS    read-only
   STATUS        current
   DESCRIPTION
       "Either the perPlatform(0) or perInterface(1) bit
        MUST be set. If the value of the
        hpnicfmplsInterfaceConfIndex for this entry is zero, then
        only the perPlatform(0) bit MUST be set and the
        perInterface(1) bit is meaningless. If the
        perInterface(1) bit is set then the value of
        hpnicfmplsInterfaceLabelMinIn, hpnicfmplsInterfaceLabelMaxIn,
        hpnicfmplsInterfaceLabelMinOut, and
        hpnicfmplsInterfaceLabelMaxOut for this entry reflect the
        label ranges for this interface.  If only the
        perPlatform(0) bit is set, then the value of
        hpnicfmplsInterfaceLabelMinIn, hpnicfmplsInterfaceLabelMaxIn,
        hpnicfmplsInterfaceLabelMinOut, and
        hpnicfmplsInterfaceLabelMaxOut for this entry must be
        identical to the instance of these objects with
        index 0."
   REFERENCE
      "Multiprotocol Label Switching, Rosen et al, draft-ietf-mpls-
       arch-06.txt, August 1999."
::= { hpnicfmplsInterfaceConfEntry 8 }

hpnicfmplsInterfaceConfStorageType  OBJECT-TYPE
   SYNTAX      StorageType
   MAX-ACCESS  read-create
   STATUS      current
   DESCRIPTION
       "The storage type for this entry."
   ::= { hpnicfmplsInterfaceConfEntry 9 }

-- End of hpnicfmplsInterfaceConfTable


-- MPLS Interface Performance Table.
hpnicfmplsInterfacePerfTable  OBJECT-TYPE
   SYNTAX        SEQUENCE OF HpnicfMplsInterfacePerfEntry
   MAX-ACCESS    not-accessible
   STATUS        current
   DESCRIPTION
       "This table provides MPLS performance information on
        a per-interface basis."
   ::= { hpnicfmplsLsrObjects 2 }

hpnicfmplsInterfacePerfEntry OBJECT-TYPE
   SYNTAX        HpnicfMplsInterfacePerfEntry
   MAX-ACCESS    not-accessible
   STATUS        current
   DESCRIPTION
       "An entry in this table is created by the LSR for
        every interface capable of supporting MPLS.  Its is
        an extension to the hpnicfmplsInterfaceConfEntry table."
   AUGMENTS      { hpnicfmplsInterfaceConfEntry }
      ::= { hpnicfmplsInterfacePerfTable 1 }

HpnicfMplsInterfacePerfEntry ::= SEQUENCE {
      -- incoming direction
      hpnicfmplsInterfaceInLabelsUsed          Gauge32,
      hpnicfmplsInterfaceFailedLabelLookup     Counter32,
      
      -- outgoing direction
      hpnicfmplsInterfaceOutLabelsUsed         Gauge32,
      hpnicfmplsInterfaceOutFragments          Counter32
   }

hpnicfmplsInterfaceInLabelsUsed OBJECT-TYPE
   SYNTAX        Gauge32
   MAX-ACCESS    read-only
   STATUS        current
   DESCRIPTION
       "This object counts the number of labels
        that are in use at this point in time on this
        interface in the incoming direction. If the interface
        participates in the per-platform label space only,
        then this instance of this object MUST be identical
        with the instance with index 0. If the interface
        participates in the per-interface label space, then this
        this instance of this object MUST represent the number of
        of per-interface labels that are in use at this point in
        time on this interface."
   ::= { hpnicfmplsInterfacePerfEntry 1 }

hpnicfmplsInterfaceFailedLabelLookup OBJECT-TYPE
   SYNTAX        Counter32
   MAX-ACCESS    read-only
   STATUS        current
   DESCRIPTION
       "This object counts the number of labeled packets
        that have been received on this interface and were
        discarded because there was no matching cross-connect
        entry. This object MUST count on a per-interface basis
        regardless of which label space the interface participates
        in."
   ::= { hpnicfmplsInterfacePerfEntry 2 }

hpnicfmplsInterfaceOutLabelsUsed OBJECT-TYPE
   SYNTAX        Gauge32
   MAX-ACCESS    read-only
   STATUS        current
   DESCRIPTION
       "This object counts the number of top-most labels in the
        outgoing label stacks that are in use at this point
        in time on this interface. This object
        MUST count on a per-interface basis regardless of
        which label space the interface participates in."
   ::= { hpnicfmplsInterfacePerfEntry 3 }

hpnicfmplsInterfaceOutFragments OBJECT-TYPE
   SYNTAX        Counter32
   MAX-ACCESS    read-only
   STATUS        current
   DESCRIPTION
       "This object counts the number of outgoing MPLS
        packets that required fragmentation before
        transmission on this interface. This object
        transmission on this interface. This object
        MUST count on a per-interface basis regardless of 
        which label space the interface participates in."
::= { hpnicfmplsInterfacePerfEntry 4 }

-- In-segment table.

hpnicfmplsInSegmentTable  OBJECT-TYPE
   SYNTAX        SEQUENCE OF HpnicfMplsInSegmentEntry
   MAX-ACCESS    not-accessible
   STATUS        current
   DESCRIPTION
       "This table contains a collection of incoming
        segments to an LSR."
   ::= { hpnicfmplsLsrObjects 3 }

hpnicfmplsInSegmentEntry  OBJECT-TYPE
   SYNTAX        HpnicfMplsInSegmentEntry
   MAX-ACCESS    not-accessible
   STATUS        current
   DESCRIPTION
       "An entry in this table represents one incoming
        segment.  An entry can be created by a network
        administrator or an SNMP agent, or an MPLS signaling
        protocol.  The creator of the entry is denoted by
        hpnicfmplsInSegmentOwner.  An entry in this table is
        indexed by the ifIndex of the incoming interface and
        the (top) label."
   INDEX         { hpnicfmplsInSegmentIfIndex, hpnicfmplsInSegmentLabel }
   ::= { hpnicfmplsInSegmentTable 1 }

HpnicfMplsInSegmentEntry ::= SEQUENCE {
  hpnicfmplsInSegmentIfIndex              InterfaceIndexOrZero,
  hpnicfmplsInSegmentLabel                HpnicfMplsLabel,
  hpnicfmplsInSegmentNPop                 Integer32,
  hpnicfmplsInSegmentAddrFamily           AddressFamilyNumbers,
  hpnicfmplsInSegmentXCIndex              Integer32,
  hpnicfmplsInSegmentOwner                HpnicfMplsObjectOwner,
  hpnicfmplsInSegmentTrafficParamPtr      RowPointer,
  hpnicfmplsInSegmentRowStatus            RowStatus,
  hpnicfmplsInSegmentStorageType          StorageType
}

hpnicfmplsInSegmentIfIndex OBJECT-TYPE
   SYNTAX        InterfaceIndexOrZero
   MAX-ACCESS    accessible-for-notify
   STATUS        current
   DESCRIPTION
       "This is a unique index for an entry in the
        hpnicfmplsInSegmentTable.  This value represents the
        interface index for the incoming MPLS interface.  A
        value of zero represents an incoming label from the
        per-platform label space.  In this case, the
        hpnicfmplsInSegmentLabel is interpreted to be an MPLS-type
        label."
   ::= { hpnicfmplsInSegmentEntry 1 }

hpnicfmplsInSegmentLabel OBJECT-TYPE
   SYNTAX        HpnicfMplsLabel
   MAX-ACCESS    accessible-for-notify
   STATUS        current
   DESCRIPTION
       "The incoming label for this segment."
   ::= { hpnicfmplsInSegmentEntry 2 }

hpnicfmplsInSegmentNPop OBJECT-TYPE
   SYNTAX        Integer32 (1..2147483647)
   MAX-ACCESS    read-create
   STATUS        current
   DESCRIPTION
       "The number of labels to pop from the incoming
        packet.  Normally only the top label is popped from
        the packet and used for all switching decisions for
        that packet.  Note that technologies which do not
        support label popping should set this value to its
        default value of 1."
   DEFVAL        { 1 }
   ::= { hpnicfmplsInSegmentEntry 3 }

hpnicfmplsInSegmentAddrFamily OBJECT-TYPE
   SYNTAX        AddressFamilyNumbers
   MAX-ACCESS    read-create
   STATUS        current
   DESCRIPTION
       "The IANA address family [IANAFamily] of the incoming
        packet.  A value of other(0) indicates that the
        family type is either unknown or undefined."
   DEFVAL        { other }
   ::= { hpnicfmplsInSegmentEntry 4 }

hpnicfmplsInSegmentXCIndex OBJECT-TYPE
SYNTAX        Integer32 (0..2147483647)
   MAX-ACCESS    read-only
   STATUS        current
   DESCRIPTION
       "Index into hpnicfmplsXCTable which identifies which cross-
        connect entry this segment is part of.  A value of
        zero indicates that this entry is not referred to by
        any cross-connect entry.  When a cross-connect entry
        is created which this in-segment is a part of, this
        object is automatically updated to reflect the value
        of hpnicfmplsXCIndex of that cross-connect entry."
   DEFVAL        { 0 }
   ::= { hpnicfmplsInSegmentEntry 5 }
   
hpnicfmplsInSegmentOwner OBJECT-TYPE
   SYNTAX        HpnicfMplsObjectOwner
   MAX-ACCESS    read-create
   STATUS        current
   DESCRIPTION
       "Denotes the entity that created and is responsible
        for managing this segment."
   DEFVAL { unknown }
   ::= { hpnicfmplsInSegmentEntry 6 }

hpnicfmplsInSegmentTrafficParamPtr OBJECT-TYPE
   SYNTAX            RowPointer
   MAX-ACCESS        read-create
   STATUS            current
   DESCRIPTION
     "This variable represents a pointer to the traffic
     parameter specification for this in-segment.  This
     value may point at an entry in the
     hpnicfmplsTrafficParamTable to indicate which
     hpnicfmplsTrafficParamEntry is to be assigned to this
     segment.  This value may optionally point at an
     externally defined traffic parameter specification
     table.  A value of zero-dot-zero indicates best-effort
     treatment.  By having the same value of this object,
     two or more segments can indicate resource sharing."
   ::= { hpnicfmplsInSegmentEntry 7 }

hpnicfmplsInSegmentRowStatus OBJECT-TYPE
   SYNTAX        RowStatus
   MAX-ACCESS    read-create
   STATUS        current
   DESCRIPTION
       "This variable is used to create, modify, and/or
        delete a row in this table."
   ::= { hpnicfmplsInSegmentEntry 8 }
   
hpnicfmplsInSegmentStorageType OBJECT-TYPE
   SYNTAX        StorageType
   MAX-ACCESS    read-create
   STATUS        current
   DESCRIPTION
       "This variable indicates the storage type for this
        object."
   ::= { hpnicfmplsInSegmentEntry 9 }

-- End of hpnicfmplsInSegmentTable

-- In-segment performance table.

hpnicfmplsInSegmentPerfTable  OBJECT-TYPE
   SYNTAX        SEQUENCE OF HpnicfMplsInSegmentPerfEntry
   MAX-ACCESS    not-accessible
   STATUS        current
   DESCRIPTION
       "This table contains statistical information for
        incoming MPLS segments to an LSR."
   ::= { hpnicfmplsLsrObjects 4 }

hpnicfmplsInSegmentPerfEntry  OBJECT-TYPE
   SYNTAX        HpnicfMplsInSegmentPerfEntry
   MAX-ACCESS    not-accessible
   STATUS        current
   DESCRIPTION
       "An entry in this table contains statistical
        information about one incoming segment which was
        configured in the hpnicfmplsInSegmentTable. The counters
        in this entry should behave in a manner similar to
        that of the interface."
   AUGMENTS      { hpnicfmplsInSegmentEntry }
   ::= { hpnicfmplsInSegmentPerfTable 1 }

HpnicfMplsInSegmentPerfEntry ::= SEQUENCE {
    hpnicfmplsInSegmentOctets                 Counter32,
    hpnicfmplsInSegmentPackets                Counter32,
    hpnicfmplsInSegmentErrors                 Counter32,
    hpnicfmplsInSegmentDiscards               Counter32,
    
    -- high capacity counter
    hpnicfmplsInSegmentHCOctets               Counter64,
    
    hpnicfmplsInSegmentPerfDiscontinuityTime  TimeStamp
   }
hpnicfmplsInSegmentOctets OBJECT-TYPE
   SYNTAX        Counter32
   MAX-ACCESS    read-only
   STATUS        current
   DESCRIPTION
       "This value represents the total number of octets
        received by this segment."
   ::= { hpnicfmplsInSegmentPerfEntry 1 }

hpnicfmplsInSegmentPackets OBJECT-TYPE
   SYNTAX        Counter32
   MAX-ACCESS    read-only
   STATUS        current
   DESCRIPTION
       "Total number of packets received by this segment."
   ::= { hpnicfmplsInSegmentPerfEntry 2 }

hpnicfmplsInSegmentErrors OBJECT-TYPE
   SYNTAX        Counter32
   MAX-ACCESS    read-only
   STATUS        current
   DESCRIPTION
       "The number of errored packets received on this
        segment."
   ::= { hpnicfmplsInSegmentPerfEntry 3 }

hpnicfmplsInSegmentDiscards OBJECT-TYPE
   SYNTAX        Counter32
   MAX-ACCESS    read-only
   STATUS        current
   DESCRIPTION
       "The number of labeled packets received on this in-
        segment, which were chosen to be discarded even
        though no errors had been detected to prevent their
        being transmitted.  One possible reason for
        discarding such a labeled packet could be to free up
        buffer space."
   ::= { hpnicfmplsInSegmentPerfEntry 4 }

hpnicfmplsInSegmentHCOctets OBJECT-TYPE
   SYNTAX        Counter64
   MAX-ACCESS    read-only
   STATUS        current
   DESCRIPTION
       "The total number of octets received.  This is the 64
        bit version of hpnicfmplsInSegmentOctets."
   ::= { hpnicfmplsInSegmentPerfEntry 5 }
   
hpnicfmplsInSegmentPerfDiscontinuityTime OBJECT-TYPE

       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { hpnicfmplsInSegmentPerfEntry 6 }
   

-- End of hpnicfmplsInSegmentPerfTable.

-- Out-segment table.

hpnicfmplsOutSegmentIndexNext OBJECT-TYPE
   SYNTAX        Integer32 (0..2147483647)
   MAX-ACCESS    read-only
   STATUS        current
   DESCRIPTION
       "This object contains the next appropriate value to
        be used for hpnicfmplsOutSegmentIndex when creating
        entries in the hpnicfmplsOutSegmentTable.  If the number
        of unassigned entries is exhausted, this object will
        take on the value of 0.  To obtain the
        hpnicfmplsOutSegmentIndex value for a new entry, the
        manager must first issue a management protocol
        retrieval operation to obtain the current value of
        this object.  The agent should modify the value to
        reflect the next unassigned index after each
        retrieval operation.  After a manager retrieves a
        value the agent will determine through its local
        policy when this index value will be made available
        for reuse."
   ::= { hpnicfmplsLsrObjects 5 }


hpnicfmplsOutSegmentTable  OBJECT-TYPE
   SYNTAX        SEQUENCE OF HpnicfMplsOutSegmentEntry
   MAX-ACCESS    not-accessible
   STATUS        current
   DESCRIPTION
       "This table contains a representation of the outgoing
        segments from an LSR."
   ::= { hpnicfmplsLsrObjects 6 }

hpnicfmplsOutSegmentEntry  OBJECT-TYPE
   SYNTAX        HpnicfMplsOutSegmentEntry
   MAX-ACCESS    not-accessible
   STATUS        current
   DESCRIPTION
       "An entry in this table represents one outgoing
        segment.  An entry can be created by a network
        administrator or an SNMP agent, or an MPLS signaling
        protocol.  The object hpnicfmplsOutSegmentOwner indicates
        the creator of this entry."
   INDEX         { hpnicfmplsOutSegmentIndex }
   ::= { hpnicfmplsOutSegmentTable 1 }

HpnicfMplsOutSegmentEntry ::= SEQUENCE {
  hpnicfmplsOutSegmentIndex                Integer32,
  hpnicfmplsOutSegmentIfIndex              InterfaceIndex,
  hpnicfmplsOutSegmentPushTopLabel         TruthValue,
  hpnicfmplsOutSegmentTopLabel             HpnicfMplsLabel,
  hpnicfmplsOutSegmentNextHopIpAddrType    InetAddressType,
  hpnicfmplsOutSegmentNextHopIpv4Addr      InetAddressIPv4,
  hpnicfmplsOutSegmentNextHopIpv6Addr      InetAddressIPv6,
  hpnicfmplsOutSegmentXCIndex              Integer32,
  hpnicfmplsOutSegmentOwner                HpnicfMplsObjectOwner,
  hpnicfmplsOutSegmentTrafficParamPtr      RowPointer,
  hpnicfmplsOutSegmentRowStatus            RowStatus,
  hpnicfmplsOutSegmentStorageType          StorageType
}

hpnicfmplsOutSegmentIndex OBJECT-TYPE
   SYNTAX        Integer32(0..2147483647)
   MAX-ACCESS    accessible-for-notify
   STATUS        current
   DESCRIPTION
       "This value contains a unique index for this row.
        While a value of 0 is not valid as an index for this
        row it can be supplied as a valid value to index
        hpnicfmplsXCTable to access entries for which no out-
        segment has been configured."
   ::= { hpnicfmplsOutSegmentEntry 1 }

hpnicfmplsOutSegmentIfIndex OBJECT-TYPE
   SYNTAX        InterfaceIndex
   MAX-ACCESS    read-create
   STATUS        current
   DESCRIPTION
       "This value contains the interface index of the
        outgoing interface."
   ::= { hpnicfmplsOutSegmentEntry 2 }

hpnicfmplsOutSegmentPushTopLabel OBJECT-TYPE
   SYNTAX        TruthValue
   MAX-ACCESS    read-create
   STATUS        current
   DESCRIPTION
       "This value indicates whether or not a top label
        should be pushed onto the outgoing packet's label
        stack.  The value of this variable must be set to
        true if the outgoing interface does not support pop-
        and-go (for example an ATM interface) or if it is a
        tunnel origination.  Note that it is considered an
        error in the case that hpnicfmplsOutSegmentPushTopLabel is
        set to false, but the cross-connect entry which
        refers to this out-segment has a non-zero
        hpnicfmplsLabelStackIndex.  The LSR MUST ensure that this
        situation does not happen "
   ::= { hpnicfmplsOutSegmentEntry 3 }

hpnicfmplsOutSegmentTopLabel OBJECT-TYPE
   SYNTAX        HpnicfMplsLabel
   MAX-ACCESS    read-create
   STATUS        current
   DESCRIPTION
       "If hpnicfmplsOutSegmentPushTopLabel is true then this
        represents the label that should be pushed onto the
        top of the outgoing packet's label stack."
   ::= { hpnicfmplsOutSegmentEntry 4 }

hpnicfmplsOutSegmentNextHopIpAddrType OBJECT-TYPE
   SYNTAX        InetAddressType
   MAX-ACCESS    read-create
   STATUS        current
   DESCRIPTION
       "Indicates whether the next hop address is IPv4 or
        IPv6.  Note that a value of unknown (0) is valid
        only when the outgoing interface is of type point-to-
        point."
   DEFVAL        { unknown }
   ::= { hpnicfmplsOutSegmentEntry 5 }

hpnicfmplsOutSegmentNextHopIpv4Addr OBJECT-TYPE
   SYNTAX        InetAddressIPv4
   MAX-ACCESS    read-create
   STATUS        current
   DESCRIPTION
       "IPv4 Address of the next hop.  Its value is
        significant only when
        hpnicfmplsOutSegmentNextHopIpAddrType is ipV4 (1),
        otherwise it should return a value of 0."
   ::= { hpnicfmplsOutSegmentEntry 6 }

hpnicfmplsOutSegmentNextHopIpv6Addr OBJECT-TYPE
   SYNTAX        InetAddressIPv6
   MAX-ACCESS    read-create
   STATUS        current
   DESCRIPTION
       "IPv6 address of the next hop.  Its value is
        significant only when
        hpnicfmplsOutSegmentNextHopIpAddrType is ipV6 (2),
        otherwise it should return a value of 0."
   ::= { hpnicfmplsOutSegmentEntry 7 }

hpnicfmplsOutSegmentXCIndex OBJECT-TYPE
   SYNTAX        Integer32 (0..2147483647)
   MAX-ACCESS    read-only
   STATUS        current
   DESCRIPTION
       "Index into hpnicfmplsXCTable which identifies which cross-
        connect entry this segment is part of.  A value of
        zero indicates that this entry is not referred to by
        any cross-connect entry.  When a cross-connect entry
        is created which this out-segment is a part of, this
        object is automatically updated to reflect the value
        of hpnicfmplsXCIndex of that cross-connect entry."
   DEFVAL        { 0 }
   ::= { hpnicfmplsOutSegmentEntry 8 }

hpnicfmplsOutSegmentOwner OBJECT-TYPE
   SYNTAX        HpnicfMplsObjectOwner
   MAX-ACCESS    read-create
   STATUS        current
   DESCRIPTION
       "Denotes the entity which created and is responsible
        for managing this segment."
   DEFVAL { unknown }
   ::= { hpnicfmplsOutSegmentEntry 9 }

hpnicfmplsOutSegmentTrafficParamPtr OBJECT-TYPE
   SYNTAX        RowPointer
   MAX-ACCESS    read-create
   STATUS        current
   DESCRIPTION
     "This variable represents a pointer to the traffic
      parameter specification for this out-segment.  This
      value may point at an entry in the
      hpnicfmplsTrafficParamTable to indicate which
      hpnicfmplsTrafficParamEntry is to be assigned to this
      segment.  This value may optionally point at an
      externally defined traffic parameter specification
      table.  A value of zero-dot-zero indicates best-
      effort treatment.  By having the same value of this
      object, two or more segments can indicate resource
      sharing."
   ::= { hpnicfmplsOutSegmentEntry 10 }

hpnicfmplsOutSegmentRowStatus OBJECT-TYPE
   SYNTAX        RowStatus
   MAX-ACCESS    read-create
   STATUS        current
   DESCRIPTION
       "For creating, modifying, and deleting this row."
   ::= { hpnicfmplsOutSegmentEntry 11 }

hpnicfmplsOutSegmentStorageType OBJECT-TYPE
   SYNTAX        StorageType
   MAX-ACCESS    read-create
   STATUS        current
   DESCRIPTION
       "This variable indicates the storage type for this
        object."
   ::= { hpnicfmplsOutSegmentEntry 12 }

-- End of hpnicfmplsOutSegmentTable


-- Out-segment performance table.

hpnicfmplsOutSegmentPerfTable  OBJECT-TYPE
   SYNTAX        SEQUENCE OF HpnicfMplsOutSegmentPerfEntry
   MAX-ACCESS    not-accessible
   STATUS        current
   DESCRIPTION
       "This table contains statistical information about
        outgoing segments from an LSR. The counters in this
        entry should behave in a manner similar to that of
        the interface."
   ::= { hpnicfmplsLsrObjects 7 }

hpnicfmplsOutSegmentPerfEntry  OBJECT-TYPE
   SYNTAX        HpnicfMplsOutSegmentPerfEntry
   MAX-ACCESS    not-accessible
   STATUS        current
   DESCRIPTION
       "An entry in this table contains statistical
        information about one outgoing segment configured in
        hpnicfmplsOutSegmentTable."
   AUGMENTS      { hpnicfmplsOutSegmentEntry }
      ::= { hpnicfmplsOutSegmentPerfTable 1 }

HpnicfMplsOutSegmentPerfEntry ::= SEQUENCE {
      hpnicfmplsOutSegmentOctets                Counter32,
      hpnicfmplsOutSegmentPackets               Counter32,
      hpnicfmplsOutSegmentErrors                Counter32,
      hpnicfmplsOutSegmentDiscards              Counter32,
      
      -- HC counter
      hpnicfmplsOutSegmentHCOctets              Counter64,
      
      hpnicfmplsOutSegmentPerfDiscontinuityTime  TimeStamp
   }

hpnicfmplsOutSegmentOctets OBJECT-TYPE
   SYNTAX        Counter32
   MAX-ACCESS    read-only
   STATUS        current
   DESCRIPTION
       "This value contains the total number of octets sent
        on this segment."
   ::= { hpnicfmplsOutSegmentPerfEntry 1 }

hpnicfmplsOutSegmentPackets OBJECT-TYPE
   SYNTAX        Counter32
   MAX-ACCESS    read-only
   STATUS        current
   DESCRIPTION
       "This value contains the total number of packets sent
        on this segment."
   ::= { hpnicfmplsOutSegmentPerfEntry 2 }

hpnicfmplsOutSegmentErrors OBJECT-TYPE
   SYNTAX        Counter32
   MAX-ACCESS    read-only
   STATUS        current
   DESCRIPTION
       "Number of packets that could not be sent due to
        errors on this segment."
   ::= { hpnicfmplsOutSegmentPerfEntry 3 }

hpnicfmplsOutSegmentDiscards OBJECT-TYPE
   SYNTAX        Counter32
   MAX-ACCESS    read-only
   STATUS        current
   DESCRIPTION
       "The number of labeled packets received on this out-
        segment, which were chosen to be discarded even
        though no errors had been detected to prevent their
        being transmitted.  One possible reason for
        discarding such a labeled packet could be to free up
        buffer space."
   ::= { hpnicfmplsOutSegmentPerfEntry 4 }

hpnicfmplsOutSegmentHCOctets OBJECT-TYPE
   SYNTAX        Counter64
   MAX-ACCESS    read-only
   STATUS        current
   DESCRIPTION
       "Total number of octets sent.  This is the 64 bit
        version of hpnicfmplsOutSegmentOctets."
   ::= { hpnicfmplsOutSegmentPerfEntry 5 }
   
hpnicfmplsOutSegmentPerfDiscontinuityTime OBJECT-TYPE
       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { hpnicfmplsOutSegmentPerfEntry 6 }
   

-- End of hpnicfmplsOutSegmentPerfTable.

-- Cross-connect table.

hpnicfmplsXCIndexNext OBJECT-TYPE
   SYNTAX        Integer32 (0..2147483647)
   MAX-ACCESS    read-only
   STATUS        current
   DESCRIPTION
       "This object contains an appropriate value to be used
        for hpnicfmplsXCIndex when creating entries in the
        hpnicfmplsXCTable.  The value 0 indicates that no
        unassigned entries are available.  To obtain the
        value of hpnicfmplsXCIndex for a new entry in the
        hpnicfmplsXCTable, the manager issues a management
        protocol retrieval operation to obtain the current
        value of hpnicfmplsXCIndex.  After each retrieval
        operation, the agent should modify the value to
        reflect the next unassigned index.  After a manager
        retrieves a value the agent will determine through
        its local policy when this index value will be made
        available for reuse."
   ::= { hpnicfmplsLsrObjects 8 }

hpnicfmplsXCTable  OBJECT-TYPE
   SYNTAX        SEQUENCE OF HpnicfMplsXCEntry
   MAX-ACCESS    not-accessible
   STATUS        current
   DESCRIPTION

       "This table specifies information for switching
        between LSP segments.  It supports point-to-point,
        point-to-multipoint and multipoint-to-point
        connections.  hpnicfmplsLabelStackTable specifies the
        label stack information for a cross-connect LSR and
        is referred to from hpnicfmplsXCTable."
   ::= { hpnicfmplsLsrObjects 9 }

hpnicfmplsXCEntry  OBJECT-TYPE
   SYNTAX        HpnicfMplsXCEntry
   MAX-ACCESS    not-accessible
   STATUS        current
   DESCRIPTION
       "A row in this table represents one cross-connect
        entry.  The following objects index it:
       
        - cross-connect index hpnicfmplsXCIndex that uniquely
          identifies a group of cross-connect entries
        - interface index of the in-segment,
          hpnicfmplsInSegmentIfIndex
        - incoming label(s), hpnicfmplsInSegmentLabel
        - out-segment index, hpnicfmplsOutSegmentIndex
       
       Originating LSPs:
        These are represented by using the special
        combination of values hpnicfmplsInSegmentIfIndex=0 and
        hpnicfmplsInSegmentLabel=0 as indexes.  In this case the
        hpnicfmplsOutSegmentIndex MUST be non-zero.
       
       Terminating LSPs:
       These are represented by using the special value
        hpnicfmplsOutSegmentIndex=0 as index.

       Special labels:
        Entries indexed by reserved MPLS label values 0
        through 15 imply terminating LSPs and MUST have
        hpnicfmplsOutSegmentIfIndex = 0.  Note that situations
        where LSPs are terminated with incoming label equal
        to 0, should have hpnicfmplsInSegmentIfIndex = 0 as well,
        but can be distinguished from originating LSPs
        because the hpnicfmplsOutSegmentIfIndex = 0.  The
        hpnicfmplsOutSegmentIfIndex MUST only be set to 0 in
        cases of terminating LSPs.
       
        An entry can be created by a network administrator
        or by an SNMP agent as instructed by an MPLS
        signaling protocol."
   INDEX  { hpnicfmplsXCIndex, hpnicfmplsInSegmentIfIndex,
            hpnicfmplsInSegmentLabel,
            hpnicfmplsOutSegmentIndex }

      ::= { hpnicfmplsXCTable 1 }

HpnicfMplsXCEntry ::= SEQUENCE {
      hpnicfmplsXCIndex                 Integer32,
      hpnicfmplsXCLspId                 HpnicfMplsLSPID,
      hpnicfmplsXCLabelStackIndex       Integer32,
      hpnicfmplsXCIsPersistent          TruthValue,
      hpnicfmplsXCOwner                 HpnicfMplsObjectOwner,
      hpnicfmplsXCRowStatus             RowStatus,
      hpnicfmplsXCStorageType           StorageType,
      hpnicfmplsXCAdminStatus           INTEGER,
      hpnicfmplsXCOperStatus            INTEGER
   }

hpnicfmplsXCIndex OBJECT-TYPE
   SYNTAX        Integer32 (1..2147483647)
   MAX-ACCESS    accessible-for-notify
   STATUS        current
   DESCRIPTION
       "Primary index for the conceptual row identifying 
        a group of cross-connect segments."
   ::= { hpnicfmplsXCEntry 1 }

hpnicfmplsXCLspId OBJECT-TYPE
   SYNTAX        HpnicfMplsLSPID
   MAX-ACCESS    read-create
   STATUS        current
   DESCRIPTION
       "This value identifies the label switched path that
        this cross-connect entry belongs to."
   ::= { hpnicfmplsXCEntry 2 }

hpnicfmplsXCLabelStackIndex OBJECT-TYPE
   SYNTAX        Integer32 (0..2147483647)
   MAX-ACCESS    read-create
   STATUS        current
   DESCRIPTION
       "Primary index into hpnicfmplsLabelStackTable identifying a
        stack of labels to be pushed beneath the top label.
        Note that the top label identified by the out-
        segment ensures that all the components of a
        multipoint-to-point connection have the same
        outgoing label.  A value of 0 indicates that no
        labels are to be stacked beneath the top label."
   ::= { hpnicfmplsXCEntry 3 }

hpnicfmplsXCIsPersistent OBJECT-TYPE
   SYNTAX        TruthValue
   MAX-ACCESS    read-create
   STATUS        current
   DESCRIPTION
       "Denotes whether or not this cross-connect entry and
        associated in- and out-segments should be restored
        automatically after failures.  This value MUST be
        set to false in cases where this cross-connect entry
        was created by a signaling protocol."
   DEFVAL        { false }
   ::= { hpnicfmplsXCEntry 4 }
   
hpnicfmplsXCOwner OBJECT-TYPE
   SYNTAX    HpnicfMplsObjectOwner
   MAX-ACCESS    read-create
   STATUS        current
   DESCRIPTION
       "Denotes the entity that created and is responsible
        for managing this cross-connect."
   ::= { hpnicfmplsXCEntry 5 }

hpnicfmplsXCRowStatus OBJECT-TYPE
   SYNTAX        RowStatus
   MAX-ACCESS    read-create
   STATUS        current
   DESCRIPTION
       "For creating, modifying, and deleting this row."
   ::= { hpnicfmplsXCEntry 6 }
   
hpnicfmplsXCStorageType OBJECT-TYPE
   SYNTAX        StorageType
   MAX-ACCESS    read-create
   STATUS        current
   DESCRIPTION
       "Defines the storage type for this object."
   ::= { hpnicfmplsXCEntry 7 }

hpnicfmplsXCAdminStatus OBJECT-TYPE
   SYNTAX   INTEGER {
                up(1),     -- ready to pass packets
                down(2),
                testing(3) -- in some test mode
                }
   MAX-ACCESS    read-create
   STATUS        current
   DESCRIPTION
       "The desired operational status of this segment."
   ::= { hpnicfmplsXCEntry 8 }

hpnicfmplsXCOperStatus OBJECT-TYPE
   SYNTAX   INTEGER {
         up(1),            -- ready to pass packets
         down(2),
         testing(3),       -- in some test mode
         unknown(4),       -- status cannot be determined
                           -- for some reason.
         dormant(5),
         notPresent(6),    -- some component is missing
         lowerLayerDown(7) -- down due to the state of
                           -- lower layer interfaces
      }
   MAX-ACCESS    read-only
   STATUS        current
   DESCRIPTION
       "The actual operational status of this cross-
        connect."
   ::= { hpnicfmplsXCEntry 9 }

-- End of hpnicfmplsXCTable


-- Label stack table.
hpnicfmplsMaxLabelStackDepth  OBJECT-TYPE
   SYNTAX        Integer32 (1..2147483647)
   MAX-ACCESS    read-only
   STATUS        current
   DESCRIPTION
       "The maximum stack depth supported by this LSR."
::= { hpnicfmplsLsrObjects 10 }

hpnicfmplsLabelStackIndexNext  OBJECT-TYPE
   SYNTAX        Integer32 (0..2147483647)
   MAX-ACCESS    read-only
   STATUS        current
   DESCRIPTION
       "This object contains an appropriate value to be used
        for hpnicfmplsLabelStackIndex when creating entries in the
        hpnicfmplsLabelStackTable.  The value 0 indicates that no
        unassigned entries are available.  To obtain an
        hpnicfmplsLabelStackIndex value for a new entry, the
        manager issues a management protocol retrieval
        operation to obtain the current value of this
        object.  After each retrieval operation, the agent
        should modify the value to reflect the next
        unassigned index.  After a manager retrieves a value
        the agent will determine through its local policy
        when this index value will be made available for
        reuse."
::= { hpnicfmplsLsrObjects 11 }

hpnicfmplsLabelStackTable OBJECT-TYPE
   SYNTAX        SEQUENCE OF HpnicfMplsLabelStackEntry
   MAX-ACCESS    not-accessible
   STATUS        current
   DESCRIPTION
       "This table specifies the label stack to be pushed
        onto a packet, beneath the top label.  Entries into
        this table are referred to from hpnicfmplsXCTable."
   ::= { hpnicfmplsLsrObjects 12 }

hpnicfmplsLabelStackEntry OBJECT-TYPE
   SYNTAX        HpnicfMplsLabelStackEntry
   MAX-ACCESS    not-accessible
   STATUS        current
   DESCRIPTION
       "An entry in this table represents one label which is
        to be pushed onto an outgoing packet, beneath the
        top label.  An entry can be created by a network
        administrator or by an SNMP agent as instructed by
        an MPLS signaling protocol."
   INDEX         { hpnicfmplsLabelStackIndex, hpnicfmplsLabelStackLabelIndex }
      ::= { hpnicfmplsLabelStackTable 1 }

HpnicfMplsLabelStackEntry ::= SEQUENCE {
      hpnicfmplsLabelStackIndex             Integer32,
      hpnicfmplsLabelStackLabelIndex        Integer32,
      hpnicfmplsLabelStackLabel             HpnicfMplsLabel,
      hpnicfmplsLabelStackRowStatus         RowStatus,
      hpnicfmplsLabelStackStorageType       StorageType
   }

hpnicfmplsLabelStackIndex OBJECT-TYPE
   SYNTAX        Integer32 (1..2147483647)
   MAX-ACCESS    not-accessible
   STATUS        current
   DESCRIPTION
       "Primary index for this row identifying a stack of
        labels to be pushed on an outgoing packet, beneath
        the top label."
   ::= { hpnicfmplsLabelStackEntry 1 }

hpnicfmplsLabelStackLabelIndex OBJECT-TYPE
   SYNTAX        Integer32 (1..2147483647)
   MAX-ACCESS    not-accessible
   STATUS        current
   DESCRIPTION
       "Secondary index for this row identifying one label
        of the stack.  Note that an entry with a smaller
        hpnicfmplsLabelStackLabelIndex would refer to a label
        higher up the label stack and would be popped at a
        downstream LSR before a label represented by a
        higher hpnicfmplsLabelStackLabelIndex at a downstream
        LSR."

   ::= { hpnicfmplsLabelStackEntry 2 }

hpnicfmplsLabelStackLabel OBJECT-TYPE
   SYNTAX        HpnicfMplsLabel
   MAX-ACCESS    read-create
   STATUS        current
   DESCRIPTION
       "The label to pushed."
   ::= { hpnicfmplsLabelStackEntry 3 }

hpnicfmplsLabelStackRowStatus OBJECT-TYPE
   SYNTAX        RowStatus
   MAX-ACCESS    read-create
   STATUS        current
   DESCRIPTION
       "For creating, modifying, and deleting this row."
   ::= { hpnicfmplsLabelStackEntry 4 }
   
hpnicfmplsLabelStackStorageType OBJECT-TYPE
   SYNTAX        StorageType
   MAX-ACCESS    read-create
   STATUS        current
   DESCRIPTION
       "Defines the storage type for this object."
   ::= { hpnicfmplsLabelStackEntry 5 }

-- End of hpnicfmplsLabelStackTable

-- Traffic Parameter table.

hpnicfmplsTrafficParamIndexNext OBJECT-TYPE
   SYNTAX        Integer32 (0..2147483647)
   MAX-ACCESS    read-only
   STATUS        current
   DESCRIPTION
       "This object contains an appropriate value which will
        be used for hpnicfmplsTrafficParamIndex when creating
        entries in the hpnicfmplsTrafficParamTable.  The value 0
        indicates that no unassigned entries are available.
        To obtain the hpnicfmplsTrafficParamIndex value for a new
        entry, the manager issues a management protocol
        retrieval operation to obtain the current value of
        this object.  After each retrieval operation, the
        agent should modify the value to reflect the next
        unassigned index.  After a manager retrieves a value
        the agent will determine through its local policy
        when this index value will be made available for
        reuse."
   ::= { hpnicfmplsLsrObjects 13 }


hpnicfmplsTrafficParamTable OBJECT-TYPE
   SYNTAX        SEQUENCE OF HpnicfMplsTrafficParamEntry
   MAX-ACCESS    not-accessible
   STATUS        current
   DESCRIPTION
       "This table specifies the Traffic Parameter objects
        for in and out-segments."
   ::= { hpnicfmplsLsrObjects 14 }

hpnicfmplsTrafficParamEntry OBJECT-TYPE
   SYNTAX        HpnicfMplsTrafficParamEntry
   MAX-ACCESS    not-accessible
   STATUS        current
   DESCRIPTION
       "An entry in this table represents the TrafficParam
        objects for one or more in or out segments.  A
        single entry can be pointed to by multiple segments
        indicating resource sharing."
   INDEX         { hpnicfmplsTrafficParamIndex }
      ::= { hpnicfmplsTrafficParamTable 1 }

HpnicfMplsTrafficParamEntry ::= SEQUENCE {
      hpnicfmplsTrafficParamIndex           Integer32,
      hpnicfmplsTrafficParamMaxRate         HpnicfMplsBitRate,
      hpnicfmplsTrafficParamMeanRate        HpnicfMplsBitRate,
      hpnicfmplsTrafficParamMaxBurstSize    HpnicfMplsBurstSize,
      hpnicfmplsTrafficParamRowStatus       RowStatus,
      hpnicfmplsTrafficParamStorageType     StorageType
   }

hpnicfmplsTrafficParamIndex OBJECT-TYPE
   SYNTAX        Integer32 (1..2147483647)
   MAX-ACCESS    not-accessible
   STATUS        current
   DESCRIPTION
       "Uniquely identifies this row of the table.  Note
        that zero represents an invalid index."
   ::= { hpnicfmplsTrafficParamEntry 1 }

hpnicfmplsTrafficParamMaxRate OBJECT-TYPE
   SYNTAX        HpnicfMplsBitRate
   UNITS         "kilobits per second"
   MAX-ACCESS    read-create
   STATUS        current
   DESCRIPTION
       "Maximum rate in kilobits/second."
   ::= { hpnicfmplsTrafficParamEntry 2 }

hpnicfmplsTrafficParamMeanRate OBJECT-TYPE
   SYNTAX        HpnicfMplsBitRate
   UNITS         "kilobits per second"
   MAX-ACCESS    read-create
   STATUS        current
   DESCRIPTION
       "Mean rate in kilobits/second."
   ::= { hpnicfmplsTrafficParamEntry 3 }

hpnicfmplsTrafficParamMaxBurstSize OBJECT-TYPE
   SYNTAX        HpnicfMplsBurstSize
   UNITS         "bytes"
   MAX-ACCESS    read-create
   STATUS        current
   DESCRIPTION
       "Maximum burst size in bytes."
   ::= { hpnicfmplsTrafficParamEntry 4 }

hpnicfmplsTrafficParamRowStatus OBJECT-TYPE
   SYNTAX        RowStatus
   MAX-ACCESS    read-create
   STATUS        current
   DESCRIPTION
       "For creating, modifying, and deleting this row."
   ::= { hpnicfmplsTrafficParamEntry 5 }
   
hpnicfmplsTrafficParamStorageType OBJECT-TYPE
   SYNTAX        StorageType
   MAX-ACCESS    read-create
   STATUS        current
   DESCRIPTION
       "The storage type for this object."
   ::= { hpnicfmplsTrafficParamEntry 6 }

-- End of hpnicfmplsTrafficParamTable

-- Notification Configuration

hpnicfmplsXCTrapEnable OBJECT-TYPE
   SYNTAX        TruthValue
   MAX-ACCESS    read-write
   STATUS        current
   DESCRIPTION
       "If this object is true, then it enables the
        generation of hpnicfmplsXCUp and hpnicfmplsXCDown traps,
        otherwise these traps are not emitted."
   DEFVAL { false }
   ::= { hpnicfmplsLsrObjects 15 }

-- Cross-connect.

hpnicfmplsXCUp NOTIFICATION-TYPE
   OBJECTS     { hpnicfmplsXCIndex,
                  hpnicfmplsInSegmentIfIndex,
                  hpnicfmplsInSegmentLabel,
                  hpnicfmplsOutSegmentIndex,
                  hpnicfmplsXCAdminStatus,
                  hpnicfmplsXCOperStatus }
   STATUS      current
   DESCRIPTION
       "This notification is generated when a
        hpnicfmplsXCOperStatus object for one of the configured
        cross-connect entries is about to leave the down
        state and transition into some other state (but not
        into the notPresent state).  This other state is
        indicated by the included value of
        hpnicfmplsXCOperStatus."
   ::= { hpnicfmplsLsrNotifyPrefix 1 }

hpnicfmplsXCDown NOTIFICATION-TYPE
   OBJECTS     { hpnicfmplsXCIndex,
                 hpnicfmplsInSegmentIfIndex,
                 hpnicfmplsInSegmentLabel,
                 hpnicfmplsOutSegmentIndex,
                 hpnicfmplsXCAdminStatus,
                 hpnicfmplsXCOperStatus }
   STATUS      current
   DESCRIPTION
       "This notification is generated when a
        hpnicfmplsXCOperStatus object for one of the configured
        cross-connect entries is about to enter the down
        state from some other state (but not from the
        notPresent state).  This other state is indicated by
        the included value of hpnicfmplsXCOperStatus."
   ::= { hpnicfmplsLsrNotifyPrefix 2 }

-- End of notifications.


-- Module compliance.

hpnicfmplsLsrGroups
   OBJECT IDENTIFIER ::= { hpnicfmplsLsrConformance 1 }

hpnicfmplsLsrCompliances
   OBJECT IDENTIFIER ::= { hpnicfmplsLsrConformance 2 }

hpnicfmplsLsrModuleCompliance MODULE-COMPLIANCE
   STATUS current
   DESCRIPTION
       "Compliance statement for agents that support the
        MPLS LSR MIB."
   MODULE -- this module

      -- The mandatory groups have to be implemented
      -- by all LSRs.  However, they may all be supported
      -- as read-only objects in the case where manual
      -- configuration is unsupported.

      MANDATORY-GROUPS    { hpnicfmplsInSegmentGroup,
                            hpnicfmplsOutSegmentGroup,
                            hpnicfmplsXCGroup,
                            hpnicfmplsInterfaceGroup,
                            hpnicfmplsPerfGroup,
                            hpnicfmplsSegmentDiscontinuityGroup }

      GROUP hpnicfmplsHCInSegmentPerfGroup
      DESCRIPTION
          "This group is mandatory for those in-segment
           entries for which the object
           hpnicfmplsInSegmentOutOctets wraps around too
           quickly."

      GROUP hpnicfmplsHCOutSegmentPerfGroup
      DESCRIPTION
          "This group is mandatory for those out-segment
           entries for which the object
           hpnicfmplsOutSegmentOctets wraps around too quickly."
          
      GROUP hpnicfmplsTrafficParamGroup
      DESCRIPTION
          "This group is mandatory for those LSRs that
           support QoS resource reservation."

      -- Depending on whether the device implements
      -- persistent cross-connects or not one of the
      -- following two groups is mandatory.

      GROUP hpnicfmplsXCIsPersistentGroup
      DESCRIPTION
          "This group is mandatory for devices which
           support persistent cross-connects.  The
           following constraints apply: hpnicfmplsXCIsPersistent
           must at least be read-only returning true(2)."

      GROUP hpnicfmplsXCIsNotPersistentGroup
      DESCRIPTION
          "This group is mandatory for devices which
           support non-persistent cross-connects.  The
           following constraints apply: hpnicfmplsXCIsPersistent
           must at least be read-only returning false(1)."

      -- hpnicfmplsInterfaceConfTable

      OBJECT      hpnicfmplsInterfaceConfStorageType
      SYNTAX      INTEGER { other(1) }
      MIN-ACCESS  read-only
      DESCRIPTION
          "Only other(1) needs to be supported."
      
      -- hpnicfmplsInSegmentTable
          
      OBJECT     hpnicfmplsInSegmentXCIndex
      DESCRIPTION
          "Write access is not required."

      OBJECT      hpnicfmplsInSegmentNPop
      MIN-ACCESS  read-only
      DESCRIPTION
          "Write access if not required.  This object
           should be set to 1 if it is read-only."

      OBJECT      hpnicfmplsInSegmentAddrFamily
      DESCRIPTION
          "Write access is not required.  A <value of
           other(0) should be supported because there may
           be cases where the agent may not know about or
           support any address types."

      OBJECT      hpnicfmplsInSegmentStorageType
      SYNTAX      INTEGER { other(1) }
      MIN-ACCESS  read-only

      DESCRIPTION
          "Only other(1) needs to be supported."

      -- hpnicfmplsOutSegmentTable

      OBJECT      hpnicfmplsOutSegmentIfIndex
      MIN-ACCESS  read-only
      DESCRIPTION
          "Write access is not required."
      
      OBJECT      hpnicfmplsOutSegmentPushTopLabel
      MIN-ACCESS  read-only
      DESCRIPTION
          "Write access is not required."

      OBJECT      hpnicfmplsOutSegmentTopLabel
      MIN-ACCESS  read-only
      DESCRIPTION
          "Write access is not required."

      OBJECT      hpnicfmplsOutSegmentNextHopIpAddrType
      MIN-ACCESS  read-only
      DESCRIPTION
          "ipV6(3) need not be supported."

      OBJECT      hpnicfmplsOutSegmentNextHopIpv4Addr
      MIN-ACCESS  read-only
      DESCRIPTION
          "Write access is not required."

      OBJECT      hpnicfmplsOutSegmentNextHopIpv6Addr
      MIN-ACCESS  read-only
      DESCRIPTION
          "Write access is not required."

      OBJECT      hpnicfmplsOutSegmentRowStatus
      SYNTAX      INTEGER { active(1), notInService(2),
                            createAndGo(4), destroy(6) }
      MIN-ACCESS  read-only
      DESCRIPTION
          "The notReady(3) and createAndWait(5) states need
           not be supported."
      OBJECT      hpnicfmplsOutSegmentStorageType
      SYNTAX      INTEGER { other(1) }
      MIN-ACCESS  read-only
      DESCRIPTION
          "Only other(1) needs to be supported."

      -- hpnicfmplsXCTable

      OBJECT      hpnicfmplsXCLabelStackIndex
      MIN-ACCESS  read-only
      DESCRIPTION
          "Write access is not required."

      OBJECT      hpnicfmplsXCIsPersistent
      MIN-ACCESS  read-only
      DESCRIPTION
          "Write access is not required."

      OBJECT      hpnicfmplsXCAdminStatus
      SYNTAX      INTEGER { up(1), down(2) }
      MIN-ACCESS  read-only
      DESCRIPTION
          "A value of testing(3) need not be supported."

      OBJECT      hpnicfmplsXCOperStatus
      SYNTAX      INTEGER { up(1), down(2) }
      DESCRIPTION
          "Only up(1) and down(2) need to be supported."
      
      OBJECT      hpnicfmplsXCRowStatus
      SYNTAX      INTEGER { active(1),
                             notInService(2),
                             createAndGo(4),
                             destroy(6) }
      MIN-ACCESS  read-only
      DESCRIPTION
          "The notReady(3) and createAndWait(5) states need
           not be supported."
      
      OBJECT      hpnicfmplsXCStorageType
      SYNTAX      INTEGER { other(1) }
      MIN-ACCESS  read-only
      DESCRIPTION
          "Only other(1) needs to be supported."

   ::= { hpnicfmplsLsrCompliances 1 }

-- Units of conformance.

hpnicfmplsInterfaceGroup OBJECT-GROUP
   OBJECTS { hpnicfmplsInterfaceLabelMinIn,
             hpnicfmplsInterfaceLabelMaxIn,
             hpnicfmplsInterfaceLabelMinOut,
             hpnicfmplsInterfaceLabelMaxOut,
             hpnicfmplsInterfaceTotalBandwidth,
             hpnicfmplsInterfaceAvailableBandwidth,
             hpnicfmplsInterfaceLabelParticipationType,
             hpnicfmplsInterfaceConfStorageType
          }
             
   STATUS  current
   DESCRIPTION
          "Collection of objects needed for MPLS interface
           configuration and performance information."
   ::= { hpnicfmplsLsrGroups 1 }

hpnicfmplsInSegmentGroup  OBJECT-GROUP
             OBJECTS { hpnicfmplsInSegmentNPop,
             hpnicfmplsInSegmentAddrFamily,
             hpnicfmplsInSegmentXCIndex,
             hpnicfmplsInSegmentOctets,
             hpnicfmplsInSegmentDiscards,
             hpnicfmplsInSegmentOwner,
             hpnicfmplsInSegmentRowStatus,
             hpnicfmplsInSegmentStorageType,
             hpnicfmplsInSegmentTrafficParamPtr
          }
   STATUS  current
   DESCRIPTION
          "Collection of objects needed to implement an in-
           segment."
   ::= { hpnicfmplsLsrGroups 2 }

hpnicfmplsOutSegmentGroup  OBJECT-GROUP
   OBJECTS { hpnicfmplsOutSegmentIndexNext,
             hpnicfmplsOutSegmentIfIndex,
             hpnicfmplsOutSegmentPushTopLabel,
             hpnicfmplsOutSegmentTopLabel,
             hpnicfmplsOutSegmentNextHopIpAddrType,
             hpnicfmplsOutSegmentNextHopIpv4Addr,
             hpnicfmplsOutSegmentNextHopIpv6Addr,
             hpnicfmplsOutSegmentXCIndex,
             hpnicfmplsOutSegmentOwner,
             hpnicfmplsOutSegmentOctets,
             hpnicfmplsOutSegmentDiscards,
             hpnicfmplsOutSegmentErrors,
             hpnicfmplsOutSegmentRowStatus,
             hpnicfmplsOutSegmentStorageType,
             hpnicfmplsOutSegmentTrafficParamPtr
          }
   STATUS  current
   DESCRIPTION
          "Collection of objects needed to implement an out-
           segment."
   ::= { hpnicfmplsLsrGroups 3 }

hpnicfmplsXCGroup  OBJECT-GROUP
   OBJECTS { hpnicfmplsXCIndexNext,
             hpnicfmplsXCLabelStackIndex,
             hpnicfmplsXCOwner,
             hpnicfmplsXCAdminStatus,
             hpnicfmplsXCOperStatus,
             hpnicfmplsXCRowStatus,
             hpnicfmplsXCTrapEnable,
             hpnicfmplsXCStorageType
          }
   STATUS  current
   DESCRIPTION
          "Collection of objects needed to implement a
           cross-connect entry."
   ::= { hpnicfmplsLsrGroups 4 }

hpnicfmplsXCOptionalGroup  OBJECT-GROUP
   OBJECTS { hpnicfmplsXCLspId }
   STATUS  current
   DESCRIPTION
          "Collection of optional objects for implementing 
           a cross-connect entry."
   ::= { hpnicfmplsLsrGroups 5 }

hpnicfmplsPerfGroup OBJECT-GROUP
   OBJECTS { hpnicfmplsInSegmentOctets,
             hpnicfmplsInSegmentPackets,
             hpnicfmplsInSegmentErrors,
             hpnicfmplsInSegmentDiscards,
             hpnicfmplsOutSegmentOctets,
             hpnicfmplsOutSegmentPackets,
             hpnicfmplsOutSegmentDiscards,
             hpnicfmplsInterfaceInLabelsUsed,
             hpnicfmplsInterfaceFailedLabelLookup,
             hpnicfmplsInterfaceOutFragments,
             hpnicfmplsInterfaceOutLabelsUsed
          }
   
   STATUS  current
   DESCRIPTION
          "Collection of objects providing performance
           information
        about an LSR."
   ::= { hpnicfmplsLsrGroups 6 }

hpnicfmplsHCInSegmentPerfGroup OBJECT-GROUP
   OBJECTS { hpnicfmplsInSegmentHCOctets }
   STATUS  current
   DESCRIPTION
          "Object(s) providing performance information
           specific to out-segments for which the object
           hpnicfmplsInterfaceInOctets wraps around too quickly."
   ::= { hpnicfmplsLsrGroups 7 }

hpnicfmplsHCOutSegmentPerfGroup OBJECT-GROUP
   OBJECTS { hpnicfmplsOutSegmentHCOctets }
   STATUS  current
   DESCRIPTION
          "Object(s) providing performance information
           specific to out-segments for which the object
           hpnicfmplsInterfaceOutOctets wraps around too
           quickly."
   ::= { hpnicfmplsLsrGroups 8 }
   
hpnicfmplsTrafficParamGroup OBJECT-GROUP
   OBJECTS { hpnicfmplsTrafficParamIndexNext,
             hpnicfmplsTrafficParamMaxRate,
             hpnicfmplsTrafficParamMeanRate,
             hpnicfmplsTrafficParamMaxBurstSize,
             hpnicfmplsTrafficParamRowStatus,
             hpnicfmplsTrafficParamStorageType
          }
   STATUS  current
   DESCRIPTION
          "Object(s) required for supporting QoS resource
           reservation."
   ::= { hpnicfmplsLsrGroups 9 }

hpnicfmplsXCIsPersistentGroup OBJECT-GROUP
   OBJECTS { hpnicfmplsXCIsPersistent }
   STATUS  current
   DESCRIPTION
          "Objects needed to support persistent cross-
           connects."
   ::= { hpnicfmplsLsrGroups 10 }

hpnicfmplsXCIsNotPersistentGroup OBJECT-GROUP
   OBJECTS { hpnicfmplsXCIsPersistent }
   STATUS  current
   DESCRIPTION
          "Objects needed to support non-persistent cross-
           connects."
   ::= { hpnicfmplsLsrGroups 11 }
   
hpnicfmplsLabelStackGroup OBJECT-GROUP
   OBJECTS { hpnicfmplsLabelStackLabel,
             hpnicfmplsLabelStackRowStatus,
             hpnicfmplsLabelStackStorageType,
             hpnicfmplsMaxLabelStackDepth,
             hpnicfmplsLabelStackIndexNext }
   STATUS current
   DESCRIPTION
          "Objects needed to support label stacking."
      ::= { hpnicfmplsLsrGroups 12 }
      
hpnicfmplsSegmentDiscontinuityGroup OBJECT-GROUP
   OBJECTS { hpnicfmplsInSegmentPerfDiscontinuityTime,
             hpnicfmplsOutSegmentPerfDiscontinuityTime
          }
   
   STATUS  current
   DESCRIPTION
       " A collection of objects providing information
        specific to segment discontinuities.."
   ::= { hpnicfmplsLsrGroups 13 }
      

hpnicfmplsLsrNotificationGroup NOTIFICATION-GROUP
   NOTIFICATIONS { hpnicfmplsXCUp,
                   hpnicfmplsXCDown }
   STATUS  current
   DESCRIPTION
          "Set of notifications implemented in this module.
           None is mandatory."
   ::= { hpnicfmplsLsrGroups 14 }

-- End of MPLS-LSR-MIB
END
