-- =============================================================================
-- Copyright (c) 2010-2014 Hewlett-Packard Development Company, L.P.
--
-- Description:
--   The file defines a MIB to provide AP object information such as
--   performance statistic and notification events.
-- Reference:
-- Version: V3.0
-- History:
--   V1.0 2006-05-10 Initial version, created by shiyang (Richard)
--   V1.1 2007-02-01 modified by xingjichen(Daniel)
--        Changed DESCRIPTION of hpnicfDot11APRxStatisTable,
--        hpnicfDot11APTxStatisTable,hpnicfDot11APMtRadioFailTrap,
--        hpnicfDot11APMtRadioFailRecoverTrap.
--   V1.2 2007-04-27 modified by shiyang(Richard)
--        Add new nodes of hpnicfDot11APChannelChgMode and hpnicfDot11APChgWorkMode.
--        Split hpnicfDot11APObjectTable table into hpnicfDot11APObjectStatusTable
--        and hpnicfDot11APObjectTable.
--        Rename hpnicfDot11APRadioRelationTable as hpnicfDot11APRadioTable.
--        Rename hpnicfDot11APBSSRelationTable as hpnicfDot11APBSSTable.
--   V1.3 2007-06-19 modified by Banasree
--        Add new table of hpnicfDot11APIfTable for hpnicfDot11APObjectGroup.
--        Add new table of hpnicfDot11APAssocStatisTable for hpnicfDot11APStatisGroup.
--        Add new node of hpnicfDot11CurrAPName, hpnicfDot11CurrAPModelName,
--        hpnicfDot11CurrAPImageName, hpnicfDot11CurrAPSoftwareVersion,
--        hpnicfDot11CurrAPIPNetMask, hpnicfDot11CurrRadioModeSupport for
--        hpnicfDot11APObjectTable.
--        Add new node of hpnicfDot11Channel, hpnicfDot11TxPowerLevel,
--        hpnicfDot11APRadioIfIndex, hpnicfDot11AntennaGain for hpnicfDot11APRadioTable.
--        Add new node of hpnicfDot11APManufacturer, hpnicfDot11APCPUType,
--        hpnicfDot11APCPUClockSpeed, hpnicfDot11APMemoryType, hpnicfDot11APMemorySize,
--        hpnicfDot11APFlashType, hpnicfDot11APFlashSize for hpnicfDot11APModelTable
--        Add hpnicfDot11APReset node to the hpnicfDot11APObjectStatusTable.
--        Add hpnicfDot11RxFrameErrorRatio to the hpnicfDot11APRxStatisTable.
--        Add_hpnicfDot11TxFrameRetryRatio to the hpnicfDot11APTxStatisTable.
--   V1.4 2007-12-21 modified by wanghao (Kumar)
--        Add hpnicfDot11BSSRxStatisTable, hpnicfDot11BSSTxStatisTable,
--        hpnicfDot11BSSAssocStatisTable for BSS statistics.
--        Add hpnicfDot11APCpuUsage to hpnicfDot11APObjectStatusTable.
--        Add hpnicfDot11MaxBandwidth to hpnicfDot11APRadioTable.
--        Add hpnicfDot11RxPhyErrorCnt, hpnicfDot11RxMICErrorCnt,
--        hpnicfDot11RxDataFrameBytes to hpnicfDot11APRxStatisTable.
--        Add hpnicfDot11TxDataFrameCnt, hpnicfDot11TxDataFrameBytes to
--        hpnicfDot11APTxStatisTable.
--        Add hpnicfDot11ApStationExDeAuthenSum, hpnicfDot11ApStationCurAssocSum to
--        hpnicfDot11APAssocStatisTable.
--   V1.5 2008-02-25 modified by wanghao (Kumar)
--        Add hpnicfDot11ResourceUseRatio to hpnicfDot11APRadioTable.
--   V1.6 2008-07-09 modified by ChangHuifeng
--        Add hpnicfDot11APConnectionType to hpnicfDot11APObjectStatusTable.
--   V1.7 2008-11-07 modified by Wang Lu and Li Yugang
--        Add hpnicfDot11APLinkStatisTable and hpnicfDot11RadioAssocStatisTable.
--        Add hpnicfDot11CurrIfNumber to hpnicfDot11APObjectTable.
--        Add hpnicfDot11RadioModeSupport, hpnicfDot11TxPowerLevel2 and
--        hpnicfDot11PowerMgmtStatus to hpnicfDot11APRadioTable.
--        Add hpnicfDot11SSID to hpnicfDot11APBSSTable.
--        Add hpnicfDot11APIfSpeed, hpnicfDot11APIfInDataRate and
--        hpnicfDot11APIfOutDataRate to hpnicfDot11APIfTable
--        Add hpnicfDot11RadioRxAverSnr to hpnicfDot11APRxStatisTable.
--        Add hpnicfDot11APMtTimeSynFail, hpnicfDot11APMtChlIntfDetected,
--        hpnicfDot11APMtIntfAPDetected, hpnicfDot11APMtIntfStaDetected,
--        hpnicfDot11APMtIPChange, hpnicfDot11APFlashWriteFailure,
--        hpnicfDot11APSysReboot, hpnicfDot11APMtAvailChlTooLow and
--        hpnicfDot11APImgDwldSuccess to hpnicfDot11APMtTraps.
--        Add hpnicfDot11APIntfDevMACAddress and hpnicfDot11APMtTrapOldIPAddr to
--        hpnicfDot11APMtTrapVarObjects.
--        Add hpnicfDot11ChannelSwitchTimes to hpnicfDot11APRadioTable.
--        Add hpnicfDot11RxPayloadBytes, hpnicfDot11RxTrafficSpeed to
--        hpnicfDot11APRxStatisTable.
--        Add hpnicfDot11TxMSDUCnt, hpnicfDot11TxDiscardMSDUCnt,
--        hpnicfDot11RetryMSDUCnt, hpnicfDot11TxPayloadBytes,
--        hpnicfDot11TxTrafficSpeed to hpnicfDot11APTxStatisTable.
--        Add hpnicfDot11ApStaCurAuthSuccSum, hpnicfDot11AllStationUpSumTime,
--        hpnicfDot11ApStationAssocReqSum to hpnicfDot11APAssocStatisTable.
--        Add hpnicfDot11BSSRxFrameErrorRatio, hpnicfDot11BSSRxPayloadBytes to
--        hpnicfDot11BSSRxStatisTable.
--        Add hpnicfDot11BSSTxPayloadBytes to hpnicfDot11BSSTxStatisTable.
--        Add hpnicfDot11BSSStationAssocReqSum to hpnicfDot11BSSAssocStatisTable.
--        Add new tables hpnicfDot11RadioMngFrameStatisTable,
--        hpnicfDot11APAuthFailStatisTable, hpnicfDot11APAssocFailStatisTable,
--        hpnicfDot11APReassocStatisTable, hpnicfDot11APUserAuthStatisTable,
--        hpnicfDot11APDeauthStatisTable, hpnicfDot11APDeassocStatisTable to
--        hpnicfDot11APStatisGroup.
--   V1.8 2009-04-17 modified by WangChunsheng
--        Add hpnicfDot11AntennaType to hpnicfDot11APRadioTable.
--   V1.9 2009-05-07 modified by Li Yugang, Wang Shaojie, Jin Yi
--        Add hpnicfDot11CurrAPElementID to hpnicfDot11APObjectTable.
--        Add hpnicfDot11DiversitySelectionRx, hpnicfDot11MaxTxPwrLvl,
--        hpnicfDot11PwrAttRange, hpnicfDot11AvgRxSignalStrength,
--        hpnicfDot11HighestRxSignalStrength, hpnicfDot11LowestRxSignalStrength
--        hpnicfDot11RadioIfUpdownTimes, hpnicfDot11RadioIfLastChange
--        to hpnicfDot11APRadioTable.
--        Add hpnicfDot11CurrSSIDResourceUseRatio to hpnicfDot11APBSSTable.
--        Add new table hpnicfDot11APSSIDObjectTable, hpnicfDot11APSysInfoTable
--        to hpnicfDot11APObjectGroup.
--        Add hpnicfDot11TxErrFrameRatio, hpnicfDot11TxFrameRate
--        to hpnicfDot11APTxStatisTable.
--        Add hpnicfDot11BSSRxUniFrameCnt, hpnicfDot11BSSRxNonUniFrameCnt,
--        hpnicfDot11BSSRxAuthenFrameCnt to hpnicfDot11BSSRxStatisTable.
--        Add hpnicfDot11BSSTxRetryCnt, hpnicfDot11BSSTxUniFrameCnt,
--        hpnicfDot11BSSTxNonUniFrameCnt, hpnicfDot11BSSTxAuthenFrameCnt
--        to hpnicfDot11BSSTxStatisTable.
--        Add new table hpnicfDot11APAssocFailStatis2Table, hpnicfDot11APIfStatisTable
--        to hpnicfDot11APStatisGroup.
--        Add hpnicfDot11APInterfDetectedTrap,
--        hpnicfDot11APInterfClearTrap, hpnicfDot11StaInterfDetectedTrap,
--        hpnicfDot11StaInterfClearTrap, hpnicfDot11OtherDevIntDetectedTrap,
--        hpnicfDot11OtherDevIntClearTrap, hpnicfDot11APModuleTroubleTrap,
--        hpnicfDot11APModuleTroubleClearTrap, hpnicfDot11APRadioDownTrap,
--        hpnicfDot11APRadioDownRecovTrap, hpnicfDot11APStaFullTrap,
--        hpnicfDot11APStaFullRecoverTrap, hpnicfDot11DFSFreeCntBelowThrRecov,
--        hpnicfDot11APCpuUsageHigh, hpnicfDot11APCpuUsageHighRecover,
--        hpnicfDot11APMemUsageHigh, hpnicfDot11APMemUsageHighRecover
--        to hpnicfDot11APMtTraps.
--        Add hpnicfDot11CurrInterfDetectedNum, hpnicfDot11StaFullReason,
--        hpnicfDot11StaLimitNumber, hpnicfDot11APRadioDownReason,
--        hpnicfDot11InterfMacList to hpnicfDot11APMtTrapVarObjects.
--        Add hpnicfDot11APLastImgDownloadTime to hpnicfDot11APObjectStatusTable.
--   V2.0 2009-07-29 modified by Heziqi
--        Add new node hpnicfDot11CurrAPMode for hpnicfDot11APObjectTable.
--        Add new node hpnicfDot11APEssVlanId and hpnicfDot11APBSSResourceUseRatio
--        for hpnicfDot11APBSSTable.
--        Add new node hpnicfDot11APTrapUserCnt and hpnicfDot11APTrapUserThreshold
--        for hpnicfDot11APMtTrapVarObjects.
--        Add hpnicfDot11APUserCntOverFlow for hpnicfDot11APMtNotifyGroup.
--        Add new node hpnicfDot11TxDiscardFrameRatio, hpnicfDot11TxFrameRate,
--        hpnicfDot11TxMgtFrameCnt and hpnicfDot11TxCtrlFrameCnt
--        for hpnicfDot11APTxStatisTable.
--        Add new node hpnicfDot11APIPv6Address for hpnicfDot11APObjectStatusTable.
--        Add new node hpnicfDot11CurrAPIPv6Address for hpnicfDot11APObjectTable.
--        Add hpnicfDot11RadioMngFrmStatisTable.
--   V2.1 2009-08-07 modified by wang shaojie, Jin Yi
--        Add hpnicfDot11APIfInBrdcastPkts, hpnicfDot11APIfOutBrdcastPkts,
--        hpnicfDot11APIfInMulcastPkts, hpnicfDot11APIfOutMulcastPkts,
--        hpnicfDot11APIfInPayloadOctets, hpnicfDot11APIfOutPayloadOctets to
--        hpnicfDot11APIfStatisTable.
--        Add new node hpnicfDot11APLastRegisterTime to hpnicfDot11APObjectStatusTable
--        Add new node hpnicfDot11TxMACErrCnt, hpnicfDot11TxErrFrameCnt to
--        hpnicfDot11APTxStatisTable.
--        Add new variable bindings hpnicfDot11APMtChanlChgCount to
--        hpnicfDot11APMtRdoChanlChgTrap.
--   V2.2 2009-12-01 modified by Wang Shaojie, duyanbing
--        Add new table hpnicfDot11APIdleListTable to hpnicfDot11APObjectGroup.
--        Add new table hpnicfDot11APPacketSizeStatisTable,
--        hpnicfDot11APPacketRateStatisTable, hpnicfDot11APPacketMCSRateStatisTable to
--        hpnicfDot11APStatisGroup.
--        Add new node hpnicfDot11RxUcastDataFrameCnt, hpnicfDot11RxNUcastDataFrameCnt
--        to hpnicfDot11APRxStatisTable.
--        Add new node hpnicfDot11TxUcastDataFrameCnt, hpnicfDot11TxNUcastDataFrameCnt
--        to hpnicfDot11APTxStatisTable.
--        Add new node hpnicfDot11CurrAPSSIDNumber to hpnicfDot11APObjectTable.
--        Add new node hpnicfDot11AllStationUpSumTimeTicks to
--        hpnicfDot11APAssocStatisTable
--        Add new node hpnicfDot11RxTotalDiscardFrameCnt to hpnicfDot11APRxStatisTable.
--        Added hpnicfDot11APMtTrapSwitch.
--        2010-02-23 modified by Wang Shaojie
--        Add hpnicfDot11APMtDetectedIntfAP, hpnicfDot11APMtDetectedIntfSTA,
--        hpnicfDot11APMtDetectedIntfOtherDev to hpnicfDot11APMtTraps.
--        Add hpnicfDot11APMtFormerApVersion, hpnicfDot11APMtAPID, hpnicfDot11APMtRadioID
--        hpnicfDot11APMtChannel, hpnicfDot11APMtInterfMacAdd to
--        hpnicfDot11APMtTrapVarObjects.
--        2010-03-15 modified by Deng Gaoliang
--        Add hpnicfDot11APAssocFailStatis3Table
--        Add hpnicfDot11APFlashSizeInBytes
--        Remove hpnicfDot11APMtTrapSwitch
--        2010-05-31 modified by LiuChen, Wang Chunsheng, Wang Shaojie
--        Add new table hpnicfDot11APSysInfoByAPIDTable.
--        Add new node hpnicfDot11CurrAPManufacturer, hpnicfDot11CurrAPMemorySize,
--        hpnicfDot11CurrAPMemSizeInBytes, hpnicfDot11CurrAPFlashSize,
--        hpnicfDot11CurrAPFlashSizeInBytes to hpnicfDot11APObjectTable.
--        Add new table hpnicfDot11APUserSecAuthStatisTable to hpnicfDot11APStatisGroup.
--        Add new table hpnicfDot11APUserInfoStatisTable to hpnicfDot11APStatisGroup.
--        2010-08-05 modified by LiuChen, Yinjunjie
--        Add new node hpnicfDot11CurrAPReleasedVersion to hpnicfDot11APObjectTable.
--        Add new node hpnicfDot11BSSStationCurAuthSum to hpnicfDot11BSSAssocStatisTable.
--        Add new node hpnicfDot11APMtAdjChannel.
--        Add hpnicfDot11DetcAdjChlIntfAP, hpnicfDot11DetcAdjChlIntfAPClear
--        to hpnicfDot11APMtTraps.
--        2010-08-05 modified by Yinjunjie
--        Add new table hpnicfDot11APReassocStatis2Table
--        2010-09-16 Change names from hpnicfDot11APIfLastChange and
--        hpnicfDot11APIfLastChange2 to hpnicfDot11APIfStatusKeepTime and
--        hpnicfDot11APIfStatusKeepTime2 by shuaixiaojuan
--   V2.3 2010-10-11 modified by Wuxiaopeng
--        Add new node hpnicfDot11APIfInDataOctets2, hpnicfDot11APIfOutDataOctets2,
--        to hpnicfDot11APIfStatisByAPIDTable.
--        Add new node hpnicfDot11APMacAddress2 to hpnicfDot11APSysInfoByAPIDTable.
--        Modify node hpnicfDot11APChgWorkMode.
--   V2.4 2011-07-13 modified by Yu Bo
--        Add new node hpnicfDot11RxTotalIPCheckErrPacketCnt to hpnicfDot11APRxStatisTable
--        Add new node hpnicfDot11APConfigPortalStaNum to hpnicfDot11APSSIDObjectTable
--        2011-08-08 modified by Donglaqi
--        Add new node hpnicfDot11AllUserOnlineTime to hpnicfDot11APUserSecAuthStatisTable
--        2011-08-10 modified by limingjin
--        Add new node hpnicfDot11RadioModeSupport2 to hpnicfDot11APRadioTable
--        Add new node hpnicfDot11CurrRadioModeSupport2 to hpnicfDot11APObjectTable
--   V2.5 2011-09-27 modified by Limingjin
--        Add hpnicfDot11TrafficTable
--        2011-09-28 modified by Li Honghao & jiaolibin
--        Add new table hpnicfDot11APEchoStatisTable
--        Add hpnicfDot11APEchoAvgDelay, hpnicfDot11APEchoRequestCnt,
--        hpnicfDot11APEchoRespLossCnt to hpnicfDot11APEchoStatisTable
--        Add hpnicfDot11APMtFirstTrapTime to hpnicfDot11APMtTrapVarObjects and
--        varialbe bindings hpnicfDot11APMtFirstTrapTime for
--        hpnicfDot11APInterfClearTrap, hpnicfDot11StaInterfDetectedTrap,
--        hpnicfDot11StaInterfClearTrap, hpnicfDot11OtherDevIntDetectedTrap,
--        hpnicfDot11OtherDevIntClearTrap, hpnicfDot11APRadioDownTrap ,
--        hpnicfDot11APRadioDownRecovTrap, hpnicfDot11APStaFullTrap,
--        hpnicfDot11APStaFullRecoverTrap, hpnicfDot11APMtDetectedIntfAP,
--        hpnicfDot11DetcAdjChlIntfAP, hpnicfDot11DetcAdjChlIntfAPClear,
--        hpnicfDot11APMtDetectedIntfSTA
--   V2.6 2012-05-08 modified by Lihonghao
--        Add new table hpnicfDot11APUserSecAuthTypeStatisTable
--        Add hpnicfDot11APPortalOnlineUserNum, hpnicfDot11APAuthFreeOnlineUserNum,
--        hpnicfDot11APAssocAuthOnlineUserNum, hpnicfDot11APMacAuthOnlineUserNum,
--        hpnicfDot11APAllPortalUserOnlineTime, hpnicfDot11APAllAuthFreeUserOnlineTime,
--        hpnicfDot11APAllAssocAuthUserOnlineTime, hpnicfDot11APAllMacAuthUserOnlineTime,
--        hpnicfDot11APPortalUserLostCnntCnt, hpnicfDot11APAuthFreeUserLostCnntCnt,
--        hpnicfDot11APAssocAuthUserLostCnntCnt, hpnicfDot11APMacAuthUserLostCnntCnt,
--        hpnicfDot11APPortalAuthReqCnt, hpnicfDot11APAssocAuthReqCnt,
--        hpnicfDot11APMacAuthReqCnt, hpnicfDot11APPortalAuthSucCnt,
--        hpnicfDot11APAssocAuthSucCnt, hpnicfDot11APMacAuthSucCnt,
--        hpnicfDot11APPortalAuthReqFailCnt, hpnicfDot11APAssocAuthReqFailCnt,
--        hpnicfDot11APMacAuthReqFailCnt to hpnicfDot11APUserSecAuthTypeStatisTable
--    2012-04-25 modified by Wang Shaojie
--        Add new table hpnicfDot11RadioRxStatis64Table, hpnicfDot11RadioTxStatis64Table,
--        hpnicfDot11BSSRxStatis64Table, hpnicfDot11BSSTxStatis64Table to
--        hpnicfDot11APStatisGroup.
--    2012-08-12 modified by Zhang Congcong & Chen Zhao liang & Li Xin
--        Add new node   hpnicfDot11APMtTrapAPMacAddress to hpnicfDot11APMtTrapVarObjects
--        Add new object hpnicfDot11APMtTrapAPMacAddress to hpnicfDot11APMtWorkModeChgTrap
--        Add new object hpnicfDot11APMtTrapAPMacAddress to hpnicfDot11APFlashWriteFailure
--        Add new object hpnicfDot11APMtTrapAPMacAddress to hpnicfDot11APMtDetectedIntfAP
--        Add new object hpnicfDot11APMtTrapAPMacAddress to hpnicfDot11APInterfClearTrap
--        Add new object hpnicfDot11APMtTrapAPMacAddress to hpnicfDot11APMtDetectedIntfSTA
--        Add new object hpnicfDot11APMtTrapAPMacAddress to hpnicfDot11StaInterfClearTrap
--        Add new object hpnicfDot11APMtTrapAPMacAddress to hpnicfDot11APMtDetectedIntfOtherDev
--        Add new object hpnicfDot11APMtTrapAPMacAddress to hpnicfDot11OtherDevIntClearTrap
--        Add new object hpnicfDot11APMtTrapAPMacAddress to hpnicfDot11APModuleTroubleTrap
--        Add new object hpnicfDot11APMtTrapAPMacAddress to hpnicfDot11APModuleTroubleClearTrap
--        Add new object hpnicfDot11APMtTrapAPMacAddress to hpnicfDot11APRadioDownTrap
--        Add new object hpnicfDot11APMtTrapAPMacAddress to hpnicfDot11APRadioDownRecovTrap
--        Add new object hpnicfDot11APMtTrapAPMacAddress to hpnicfDot11APStaFullTrap
--        Add new object hpnicfDot11APMtTrapAPMacAddress to hpnicfDot11APStaFullRecoverTrap
--        Add new object hpnicfDot11APMtTrapAPMacAddress to hpnicfDot11APMtAvailChlTooLow
--        Add new object hpnicfDot11APMtTrapAPMacAddress to hpnicfDot11DFSFreeCntBelowThrRecov
--        Add new object hpnicfDot11APMtTrapAPMacAddress to hpnicfDot11APMtRdoChanlChgTrap
--   V2.7 2013-01-16 modified by Peng Nao
--        Add new object hpnicfDot11APMtTrapAPMacAddress to hpnicfDot11APCpuUsageHigh
--        Add new object hpnicfDot11APMtTrapAPMacAddress to hpnicfDot11APCpuUsageHighRecover
--        Add new object hpnicfDot11APMtTrapAPMacAddress to hpnicfDot11APMemUsageHigh
--        Add new object hpnicfDot11APMtTrapAPMacAddress to hpnicfDot11APMemUsageHighRecover
--   V2.8 2013-07-01 modified by LiuYanjie
--        Add new table hpnicfDot11APPacketMCSRateStatis2Table to hpnicfDot11APStatisGroup.
--        2013-07-08 modified by Chen Guoxi
--        Add new node  hpnicfDot11ApStationReassocReqSum      to hpnicfDot11APAssocStatisEntry
--        Add new node  hpnicfDot11ApStationReassocFailSum     to hpnicfDot11APAssocStatisEntry
--   V2.9 2013-09-02 Added hpnicfDot11OperStatusCM to hpnicfDot11APRadioTable by Zhang Siyu
--        2013-09-13 Added hpnicfDot11APIfAdminStatus,hpnicfDot11APIfOperStatusCM and
--        hpnicfDot11APACAssociateStatusCM by duyanbing
--   V3.0 2014-02-10 modified by weixiangxiang
--        Add new object hpnicfDot11APResetCM to hpnicfDot11APObjectStatusTable
--        Add new object hpnicfDot11CurrAPCPUTypeCM to hpnicfDot11APObjectTable
--        Add new object hpnicfDot11CurrAPMemoryTypeCM to hpnicfDot11APObjectTable
--        Add new object hpnicfDot11CurrAPBSSIDNumberCM to hpnicfDot11APObjectTable
--        Add new object hpnicfDot11APIfTypeCM to hpnicfDot11APIfTable
--        Add new object hpnicfDot11RxSignalStrengthPacketCntCM to hpnicfDot11APRxStatisTable
--        Add new object hpnicfDot11APAssocFailStatisRSSILowCntCM to hpnicfDot11APAssocFailStatis3Table
--        Add new object hpnicfDot11APUserLoginNameCM to hpnicfDot11APUserInfoStatisTable
--        Add new object hpnicfDot11APUserAuthTypeCM to hpnicfDot11APUserInfoStatisTable
--        Add new object hpnicfDot11APUserTxPacketCntCM to hpnicfDot11APUserInfoStatisTable
--        Add new object hpnicfDot11APUserTxBytesCM to hpnicfDot11APUserInfoStatisTable
--        Add new object hpnicfDot11APUserRxPacketCntCM to hpnicfDot11APUserInfoStatisTable
--        Add new object hpnicfDot11APUserRxBytesCM to hpnicfDot11APUserInfoStatisTable
--        Add new table hpnicfDot11APUserSecAuthStatisCMTable to hpnicfDot11APStatisGroup
--        Add new object hpnicfDot11APAutoAuthOnlineUserNumCM to hpnicfDot11APUserSecAuthTypeStatisTable
--        Add new object hpnicfDot11APAllAutoAuthOnlineTimeCM to hpnicfDot11APUserSecAuthTypeStatisTable
--        Add new object hpnicfDot11APAutoAuthUserLostCnntCntCM to hpnicfDot11APUserSecAuthTypeStatisTable
--        Add new object hpnicfDot11APAutoAuthReqCntCM to hpnicfDot11APUserSecAuthTypeStatisTable
--        Add new object hpnicfDot11APAutoAuthSucCntCM to hpnicfDot11APUserSecAuthTypeStatisTable
--        Add new object hpnicfDot11APAutoAuthReqFailCntCM to hpnicfDot11APUserSecAuthTypeStatisTable
--        Modify object hpnicfDot11APPortalOnlineUserNum from hpnicfDot11APUserSecAuthTypeStatisTable
--        Modify object hpnicfDot11APAssocAuthOnlineUserNum from hpnicfDot11APUserSecAuthTypeStatisTable
--        Add hpnicfDot11RxDataFrameCntCM to hpnicfDot11APRxStatisTable
--        Add hpnicfDot11Rx64DataFrameBytesCM to hpnicfDot11RadioRxStatis64Table
-- =============================================================================
HPN-ICF-DOT11-APMT-MIB DEFINITIONS ::= BEGIN

IMPORTS
        MODULE-IDENTITY,
        OBJECT-TYPE,
        NOTIFICATION-TYPE,
        Integer32,
        Counter32,
        IpAddress,
        Unsigned32,
        TimeTicks,
        Counter64,
        Gauge32
    FROM SNMPv2-SMI
        MacAddress,
        TruthValue,
        DateAndTime
    FROM SNMPv2-TC
        hpnicfDot11,
        HpnicfDot11ObjectIDType,
        HpnicfDot11MACModeType,
        HpnicfDot11RadioScopeType,
        HpnicfDot11NotifyReasonType,
        HpnicfDot11ChannelScopeType,
        HpnicfDot11ServicePolicyIDType,
        HpnicfDot11RFModeType,
        HpnicfDot11TxPwrLevelScopeType,
        HpnicfDot11RadioElementIndex,
        hpnicfDot11APElementIndex,
        HpnicfDot11SSIDStringType
    FROM HPN-ICF-DOT11-REF-MIB;

hpnicfDot11APMT MODULE-IDENTITY
    LAST-UPDATED "201205071800Z"        -- May 07, 2012 at 18:00 GMT
    ORGANIZATION
        ""
    CONTACT-INFO
        ""
    DESCRIPTION
        "This MIB provides AP information which includes AP current object
        information, AP statistic data.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable STA invocation
        of the distribution system services.
        (Wireless clients attempt to connect to
        access points.)

        Basic Rate
        A data rate that is mandatory for client
        devices to support in order for them to achieve
        successful association."

    REVISION "201205071800Z"        -- May 07, 2012 at 18:00 GMT
    DESCRIPTION
        "Modified to add new tables."

    REVISION "201010111800Z"        -- Oct 11, 2010 at 18:00 GMT
    DESCRIPTION
        "Modified to add new nodes."
    REVISION "201009151200Z"        -- Sep 15, 2010 at 12:00 GMT
    DESCRIPTION
        "Modified to add new table."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new tables and new nodes."
    REVISION "200811071000Z"        -- Nov 07, 2008 at 10:00 GMT
    DESCRIPTION
        "Modified to add new tables and new nodes."
    REVISION "200807091800Z"        -- July 09, 2008 at 18:00 GMT
    DESCRIPTION
        "Modified to add new nodes."
    REVISION "200802251800Z"        -- Feb 25, 2008 at 18:00 GMT
    DESCRIPTION
        "Modified to add new nodes."
    REVISION "200712211800Z"        -- Dec 21, 2007 at 18:00 GMT
    DESCRIPTION
        "Modified to add new tables and new nodes."
    REVISION "200706191800Z"        -- June 19, 2007 at 18:00 GMT
    DESCRIPTION
        "Modified for new requirements and fix some issue."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { hpnicfDot11 2 }

-- *****************************************************************************
-- *  Major sections
-- *****************************************************************************
--  AP Object Group
--  DEFINED AS "The group to provide the basic information for APs.
--  In order to support fit and fat AP, it uses tables to keep
--  information. For fat AP, if it is needful, it could add more
--  tables to keep information."
hpnicfDot11APObjectGroup OBJECT IDENTIFIER   ::= { hpnicfDot11APMT 1 }

--  AP Object Group has the following children:
--  hpnicfDot11APObjectStatusTable           ::= { hpnicfDot11APObjectGroup 1 }
--  hpnicfDot11APObjectTable                 ::= { hpnicfDot11APObjectGroup 2 }
--  hpnicfDot11APRadioTable                  ::= { hpnicfDot11APObjectGroup 3 }
--  hpnicfDot11APBSSTable                    ::= { hpnicfDot11APObjectGroup 4 }
--  hpnicfDot11APModelTable                  ::= { hpnicfDot11APObjectGroup 5 }
--  hpnicfDot11APIfTable                     ::= { hpnicfDot11APObjectGroup 6 }
--  hpnicfDot11APSSIDObjectTable             ::= { hpnicfDot11APObjectGroup 7 }
--  hpnicfDot11APSysInfoTable                ::= { hpnicfDot11APObjectGroup 8 }
--  hpnicfDot11APIdleListTable               ::= { hpnicfDot11APObjectGroup 9 }
--  hpnicfDot11APSysInfoByAPIDTable          ::= { hpnicfDot11APObjectGroup 10 }

--  AP Statistic Group
--  DEFINED AS "The group to provide the statistic information of Rx
--  and Tx for AP."
hpnicfDot11APStatisGroup OBJECT IDENTIFIER   ::= { hpnicfDot11APMT 2 }

--  AP Statistic Group has the following children:
--  hpnicfDot11APRxStatisTable               ::= { hpnicfDot11APStatisGroup 1 }
--  hpnicfDot11APTxStatisTable               ::= { hpnicfDot11APStatisGroup 2 }
--  hpnicfDot11APAssocStatisTable            ::= { hpnicfDot11APStatisGroup 3 }
--  hpnicfDot11BSSRxStatisTable              ::= { hpnicfDot11APStatisGroup 4 }
--  hpnicfDot11BSSTxStatisTable              ::= { hpnicfDot11APStatisGroup 5 }
--  hpnicfDot11BSSAssocStatisTable           ::= { hpnicfDot11APStatisGroup 6 }
--  hpnicfDot11APLinkStatisTable             ::= { hpnicfDot11APStatisGroup 7 }
--  hpnicfDot11RadioAssocStatisTable         ::= { hpnicfDot11APStatisGroup 8 }
--  hpnicfDot11RadioMngFrameStatisTable      ::= { hpnicfDot11APStatisGroup 9 }
--  hpnicfDot11APAuthFailStatisTable         ::= { hpnicfDot11APStatisGroup 10 }
--  hpnicfDot11APAssocFailStatisTable        ::= { hpnicfDot11APStatisGroup 11 }
--  hpnicfDot11APReassocStatisTable          ::= { hpnicfDot11APStatisGroup 12 }
--  hpnicfDot11APUserAuthStatisTable         ::= { hpnicfDot11APStatisGroup 13 }
--  hpnicfDot11APDeauthStatisTable           ::= { hpnicfDot11APStatisGroup 14 }
--  hpnicfDot11APDeassocStatisTable          ::= { hpnicfDot11APStatisGroup 15 }
--  hpnicfDot11APAssocFailStatis2Table       ::= { hpnicfDot11APStatisGroup 16 }
--  hpnicfDot11APIfStatisTable               ::= { hpnicfDot11APStatisGroup 17 }
--  hpnicfDot11RadioMngFrmStatisTable        ::= { hpnicfDot11APStatisGroup 18 }
--  hpnicfDot11APPacketSizeStatisTable       ::= { hpnicfDot11APStatisGroup 19 }
--  hpnicfDot11APPacketRateStatisTable       ::= { hpnicfDot11APStatisGroup 20 }
--  hpnicfDot11APPacketMCSRateStatisTable    ::= { hpnicfDot11APStatisGroup 21 }
--  hpnicfDot11APAssocFailStatis3Table       ::= { hpnicfDot11APStatisGroup 22 }
--  hpnicfDot11APIfStatisByAPIDTable         ::= { hpnicfDot11APStatisGroup 23 }
--  hpnicfDot11APUserSecAuthStatisTable      ::= { hpnicfDot11APStatisGroup 24 }
--  hpnicfDot11APUserInfoStatisTable         ::= { hpnicfDot11APStatisGroup 25 }
--  hpnicfDot11APReassocStatis2Table         ::= { hpnicfDot11APStatisGroup 26 }
--  hpnicfDot11TrafficTable                  ::= { hpnicfDot11APStatisGroup 27 }
--  hpnicfDot11APEchoStatisTable             ::= { hpnicfDot11APStatisGroup 28 }
--  hpnicfDot11APUserSecAuthTypeStatisTable  ::= { hpnicfDot11APStatisGroup 29 }
--  hpnicfDot11RadioRxStatis64Table          ::= { hpnicfDot11APStatisGroup 30 }
--  hpnicfDot11RadioTxStatis64Table          ::= { hpnicfDot11APStatisGroup 31 }
--  hpnicfDot11BSSRxStatis64Table            ::= { hpnicfDot11APStatisGroup 32 }
--  hpnicfDot11BSSTxStatis64Table            ::= { hpnicfDot11APStatisGroup 33 }
--  hpnicfDot11APPacketMCSRateStatis2Table   ::= { hpnicfDot11APStatisGroup 34 }
--  hpnicfDot11APUserSecAuthStatisCMTable    ::= { hpnicfDot11APStatisGroup 35 }

--  AP Event Notification
--  DEFINED AS " The group to provide AP management notification."
hpnicfDot11APMtNotifyGroup OBJECT IDENTIFIER ::= { hpnicfDot11APMT 3 }

-- *****************************************************************************
-- *  hpnicfDot11APObjectStatusTable Definition
-- *****************************************************************************
hpnicfDot11APObjectStatusTable OBJECT-TYPE
    SYNTAX      SEQUENCE OF HpnicfDot11APObjectStatusEntry
    MAX-ACCESS  not-accessible
    STATUS      current
    DESCRIPTION
        "The table will provide the general information about APs in
        different status."
    ::= { hpnicfDot11APObjectGroup 1 }

hpnicfDot11APObjectStatusEntry OBJECT-TYPE
    SYNTAX      HpnicfDot11APObjectStatusEntry
    MAX-ACCESS  not-accessible
    STATUS      current
    DESCRIPTION
        "Each entry contains the general information of an AP."
    INDEX
        {
            hpnicfDot11APID
        }
    ::= { hpnicfDot11APObjectStatusTable 1 }

HpnicfDot11APObjectStatusEntry ::= SEQUENCE
    {
        hpnicfDot11APID                  HpnicfDot11ObjectIDType,
        hpnicfDot11APIPAddress           IpAddress,
        hpnicfDot11APMacAddress          MacAddress,
        hpnicfDot11APOperationStatus     INTEGER,
        hpnicfDot11APTemplateNameOfAP    OCTET STRING,
        hpnicfDot11APReset               TruthValue,
        hpnicfDot11APCpuUsage            Integer32,
        hpnicfDot11APConnectionType      INTEGER,
        hpnicfDot11APLastImgDownloadTime DateAndTime,
        hpnicfDot11APIPv6Address         OCTET STRING,
        hpnicfDot11APLastRegisterTime    DateAndTime,
        hpnicfDot11APResetCM             INTEGER
    }

hpnicfDot11APID OBJECT-TYPE
    SYNTAX      HpnicfDot11ObjectIDType
    MAX-ACCESS  accessible-for-notify
    STATUS      current
    DESCRIPTION
        "To uniquely identify each AP, and relation-ship between hpnicfDot11APID
        and AP device will be static."
    ::= { hpnicfDot11APObjectStatusEntry 1 }

hpnicfDot11APIPAddress OBJECT-TYPE
    SYNTAX      IpAddress
    MAX-ACCESS  read-only
    STATUS      current
    DESCRIPTION
        "Represents the IP address of an AP."
    ::= { hpnicfDot11APObjectStatusEntry 2 }

hpnicfDot11APMacAddress OBJECT-TYPE
    SYNTAX      MacAddress
    MAX-ACCESS  read-only
    STATUS      current
    DESCRIPTION
        "Represents the MAC address of an AP."
    ::= { hpnicfDot11APObjectStatusEntry 3 }

hpnicfDot11APOperationStatus OBJECT-TYPE
    SYNTAX      INTEGER
        {
            join(1),
            joinConfirm(2),
            download(3),
            config(4),
            run(5)
        }
    MAX-ACCESS  read-only
    STATUS      current
    DESCRIPTION
        "Represents operational status of AP.
        The following values are supported:
        join         - AP is joining to AC.
        joinConfirm  - AC confirm whether permit AP to join.
        download     - AP is downloading software from AC.
        config       - AP and AC exchange configuration before AP
        - provide WLAN service.
        run          - The WLAN service is ready."
    ::= { hpnicfDot11APObjectStatusEntry 4 }

hpnicfDot11APTemplateNameOfAP OBJECT-TYPE
    SYNTAX      OCTET STRING
    MAX-ACCESS  read-only
    STATUS      current
    DESCRIPTION
        "Represents the name of current AP template configured for AP."
    ::= { hpnicfDot11APObjectStatusEntry 5 }

hpnicfDot11APReset OBJECT-TYPE
    SYNTAX      TruthValue
    MAX-ACCESS  read-write
    STATUS      current
    DESCRIPTION
        "When read the value from the node
        2: Represents the AP can not be reseted.
        1: Represents the AP can be reseted.
        When write the value to the node
        1: Represents reseting the AP. Other values are not supported"
    ::= { hpnicfDot11APObjectStatusEntry 6 }

hpnicfDot11APCpuUsage OBJECT-TYPE
    SYNTAX      Integer32(0..100)
    UNITS       "onepercent"
    MAX-ACCESS  read-only
    STATUS      current
    DESCRIPTION
        "Represents the current CPU usage for AP."
    ::= { hpnicfDot11APObjectStatusEntry 7 }

hpnicfDot11APConnectionType OBJECT-TYPE
    SYNTAX      INTEGER
        {
            master(1),
            slave(2),
            notAvailable(3)
        }
    MAX-ACCESS  read-only
    STATUS      current
    DESCRIPTION
        "Represents the current connection type."
    ::= { hpnicfDot11APObjectStatusEntry 8 }

hpnicfDot11APLastImgDownloadTime OBJECT-TYPE
    SYNTAX      DateAndTime
    MAX-ACCESS  read-only
    STATUS      current
    DESCRIPTION
        "Represents the time at which the device last downloaded image."
    ::= { hpnicfDot11APObjectStatusEntry 9 }

hpnicfDot11APIPv6Address OBJECT-TYPE
    SYNTAX      OCTET STRING
    MAX-ACCESS  read-only
    STATUS      current
    DESCRIPTION
        "Represents the IPv6 address of AP."
    ::= { hpnicfDot11APObjectStatusEntry 10 }

hpnicfDot11APLastRegisterTime OBJECT-TYPE
    SYNTAX      DateAndTime
    MAX-ACCESS  read-only
    STATUS      current
    DESCRIPTION
        "Represents the time at which the device last registered with AC."
    ::= { hpnicfDot11APObjectStatusEntry 11 }

hpnicfDot11APResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP. Other values are not supported."
    ::= { hpnicfDot11APObjectStatusEntry 12 }

-- *****************************************************************************
-- *  End of HpnicfDot11APObjectStatusTable Definition
-- *****************************************************************************

-- *****************************************************************************
-- *  hpnicfDot11APObjectTable Definition
-- *****************************************************************************
hpnicfDot11APObjectTable OBJECT-TYPE
    SYNTAX      SEQUENCE OF HpnicfDot11APObjectEntry
    MAX-ACCESS  not-accessible
    STATUS      current
    DESCRIPTION
        "The table will provide information for APs in the running status."
    ::= { hpnicfDot11APObjectGroup 2 }

hpnicfDot11APObjectEntry OBJECT-TYPE
    SYNTAX      HpnicfDot11APObjectEntry
    MAX-ACCESS  not-accessible
    STATUS      current
    DESCRIPTION
        "Each entry contains information of an AP in run status."
    INDEX
        {
            hpnicfDot11APObjID
        }
    ::= { hpnicfDot11APObjectTable 1 }

HpnicfDot11APObjectEntry ::= SEQUENCE
    {
        hpnicfDot11APObjID                    HpnicfDot11ObjectIDType,
        hpnicfDot11CurrAPIPAddress            IpAddress,
        hpnicfDot11CurrAPMacAddress           MacAddress,
        hpnicfDot11CurrACPortIndex            Integer32,
        hpnicfDot11CurrAPMACMode              HpnicfDot11MACModeType,
        hpnicfDot11CurrAPTemplateName         OCTET STRING,
        hpnicfDot11CurrAPStationAssocCount    Integer32,
        hpnicfDot11CurrAPName                 OCTET STRING,
        hpnicfDot11CurrAPModelName            OCTET STRING,
        hpnicfDot11CurrAPImageName            OCTET STRING,
        hpnicfDot11CurrAPSoftwareVersion      OCTET STRING,
        hpnicfDot11CurrAPIPNetMask            IpAddress,
        hpnicfDot11CurrRadioModeSupport       Integer32,
        hpnicfDot11CurrIfNumber               Integer32,
        hpnicfDot11CurrAPElementID            Integer32,
        hpnicfDot11CurrAPMode                 INTEGER,
        hpnicfDot11CurrAPIPv6Address          OCTET STRING,
        hpnicfDot11CurrAPSSIDNumber           Integer32,
        hpnicfDot11CurrAPManufacturer         OCTET STRING,
        hpnicfDot11CurrAPMemorySize           Integer32,
        hpnicfDot11CurrAPMemSizeInBytes       Integer32,
        hpnicfDot11CurrAPFlashSize            Integer32,
        hpnicfDot11CurrAPFlashSizeInBytes     Integer32,
        hpnicfDot11CurrAPReleasedVersion      OCTET STRING,
        hpnicfDot11CurrRadioModeSupport2      Integer32,
        hpnicfDot11CurrAPCPUTypeCM            OCTET STRING,
        hpnicfDot11CurrAPMemoryTypeCM         OCTET STRING,
        hpnicfDot11CurrAPBSSIDNumberCM        Integer32
    }

hpnicfDot11APObjID OBJECT-TYPE
    SYNTAX      HpnicfDot11ObjectIDType
    MAX-ACCESS  not-accessible
    STATUS      current
    DESCRIPTION
        "To uniquely identify each AP, and relation-ship between hpnicfDot11APObjID
        and AP device will be static."
    ::= { hpnicfDot11APObjectEntry 1 }

hpnicfDot11CurrAPIPAddress OBJECT-TYPE
    SYNTAX      IpAddress
    MAX-ACCESS  read-only
    STATUS      current
    DESCRIPTION
        "Represents the IP address of an AP."
    ::= { hpnicfDot11APObjectEntry 2 }

hpnicfDot11CurrAPMacAddress OBJECT-TYPE
    SYNTAX      MacAddress
    MAX-ACCESS  read-only
    STATUS      current
    DESCRIPTION
        "Represents the MAC address of an AP."
    ::= { hpnicfDot11APObjectEntry 3 }

hpnicfDot11CurrACPortIndex OBJECT-TYPE
    SYNTAX      Integer32
    MAX-ACCESS  read-only
    STATUS      current
    DESCRIPTION
        "Represents the port on the AC, by which the traffic of this AP comes
        through. NMS could refer it to access information kept in the
        MIB-2."
    ::= { hpnicfDot11APObjectEntry 4 }

hpnicfDot11CurrAPMACMode OBJECT-TYPE
    SYNTAX      HpnicfDot11MACModeType
    MAX-ACCESS  read-only
    STATUS      current
    DESCRIPTION
        "Represents what MAC mode defined in the CAPWAP is applied.
        For fat AP, the value will be fatap."
    ::= { hpnicfDot11APObjectEntry 5 }

hpnicfDot11CurrAPTemplateName OBJECT-TYPE
    SYNTAX      OCTET STRING
    MAX-ACCESS  read-only
    STATUS      current
    DESCRIPTION
        "Represents the name of current AP template."
    ::= { hpnicfDot11APObjectEntry 6 }

hpnicfDot11CurrAPStationAssocCount OBJECT-TYPE
    SYNTAX      Integer32
    MAX-ACCESS  read-only
    STATUS      current
    DESCRIPTION
        "Represents the total number of stations which are associating
        to AP."
    ::= { hpnicfDot11APObjectEntry 7 }

hpnicfDot11CurrAPName OBJECT-TYPE
    SYNTAX      OCTET STRING
    MAX-ACCESS  read-only
    STATUS      current
    DESCRIPTION
        "Represents the name of AP."
    ::= { hpnicfDot11APObjectEntry 8 }

hpnicfDot11CurrAPModelName OBJECT-TYPE
    SYNTAX      OCTET STRING
    MAX-ACCESS  read-only
    STATUS      current
    DESCRIPTION
        "Represents index of WTP model,with it to get AP model information."
    ::= { hpnicfDot11APObjectEntry 9 }

hpnicfDot11CurrAPImageName OBJECT-TYPE
    SYNTAX      OCTET STRING
    MAX-ACCESS  read-only
    STATUS      current
    DESCRIPTION
        "Represents the image file name of AP."
    ::= { hpnicfDot11APObjectEntry 10 }

hpnicfDot11CurrAPSoftwareVersion OBJECT-TYPE
    SYNTAX      OCTET STRING
    MAX-ACCESS  read-only
    STATUS      current
    DESCRIPTION
        "Represents the software version of AP."
    ::= { hpnicfDot11APObjectEntry 11 }

hpnicfDot11CurrAPIPNetMask OBJECT-TYPE
    SYNTAX      IpAddress
    MAX-ACCESS  read-only
    STATUS      current
    DESCRIPTION
        "Represents the IP netmask of AP."
    ::= { hpnicfDot11APObjectEntry 12 }

hpnicfDot11CurrRadioModeSupport OBJECT-TYPE
    SYNTAX      Integer32
    MAX-ACCESS  read-only
    STATUS      current
    DESCRIPTION
        "Represents which radio type supported by the AP.
        The WLAN system support the following possible radio type.
        dot11a(1),
        dot11b(2),
        dot11g(4),
        dot11n(8)
        For a AP,it could support multiple radio types at
        the same time.So the value of object could combine multiple value
        of radio type above.
        For example:
        For one AP which support both b and g mode radio, when getting the value
        from the node, the value is 6(2 + 4)."
    ::= { hpnicfDot11APObjectEntry 13 }

hpnicfDot11CurrIfNumber OBJECT-TYPE
    SYNTAX      Integer32
    MAX-ACCESS  read-only
    STATUS      current
    DESCRIPTION
        "Represents number of interface of the AP."
    ::= { hpnicfDot11APObjectEntry 14 }

hpnicfDot11CurrAPElementID OBJECT-TYPE
    SYNTAX      Integer32
    MAX-ACCESS  read-only
    STATUS      current
    DESCRIPTION
    "Represents the AP element ID."
    ::= { hpnicfDot11APObjectEntry 15 }

hpnicfDot11CurrAPMode OBJECT-TYPE
    SYNTAX      INTEGER
        {
            bridge(1),
            route(2)
        }
    MAX-ACCESS  read-only
    STATUS      current
    DESCRIPTION
        "Represents the forward mode of the AP."
    ::= { hpnicfDot11APObjectEntry 16 }

hpnicfDot11CurrAPIPv6Address OBJECT-TYPE
    SYNTAX      OCTET STRING
    MAX-ACCESS  read-only
    STATUS      current
    DESCRIPTION
        "Represents the IPv6 address of AP."
    ::= { hpnicfDot11APObjectEntry 17 }

hpnicfDot11CurrAPSSIDNumber OBJECT-TYPE
    SYNTAX      Integer32
    MAX-ACCESS  read-only
    STATUS      current
    DESCRIPTION
        "Represents the number of SSID configured on AP."
    ::= { hpnicfDot11APObjectEntry 18 }

hpnicfDot11CurrAPManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { hpnicfDot11APObjectEntry 19 }

hpnicfDot11CurrAPMemorySize OBJECT-TYPE
    SYNTAX      Integer32
    UNITS       "kbytes"
    MAX-ACCESS  read-only
    STATUS      current
    DESCRIPTION
        "Represents the size of AP memory."
    ::= { hpnicfDot11APObjectEntry 20 }

hpnicfDot11CurrAPMemSizeInBytes OBJECT-TYPE
    SYNTAX      Integer32
    UNITS       "bytes"
    MAX-ACCESS  read-only
    STATUS      current
    DESCRIPTION
        "Represents the size of AP memory."
    ::= { hpnicfDot11APObjectEntry 21 }

hpnicfDot11CurrAPFlashSize OBJECT-TYPE
    SYNTAX      Integer32
    UNITS       "Kbytes"
    MAX-ACCESS  read-only
    STATUS      current
    DESCRIPTION
        "Represents the size of AP flash."
    ::= { hpnicfDot11APObjectEntry 22 }

hpnicfDot11CurrAPFlashSizeInBytes OBJECT-TYPE
    SYNTAX      Integer32
    UNITS       "bytes"
    MAX-ACCESS  read-only
    STATUS      current
    DESCRIPTION
        "This object represents the size of AP flash."
    ::= { hpnicfDot11APObjectEntry 23 }

hpnicfDot11CurrAPReleasedVersion OBJECT-TYPE
    SYNTAX      OCTET STRING
    MAX-ACCESS  read-only
    STATUS      current
    DESCRIPTION
        "Represents the released version of AP."
    ::= { hpnicfDot11APObjectEntry 24 }

hpnicfDot11CurrRadioModeSupport2 OBJECT-TYPE
    SYNTAX      Integer32
    MAX-ACCESS  read-only
    STATUS      current
    DESCRIPTION
        "Represents which radio type supported by the AP.
        The WLAN system support the following possible radio type.
        dot11a(1),
        dot11b(2),
        dot11g(4),
        dot11an(8),
        dot11gn(16)
        For a AP,it could support multiple radio types at
        the same time.So the value of object could combine multiple value
        of radio type above.
        For example:
        For one AP which support both b and g mode radio, when getting the value
        from the node, the value is 6(2 + 4)."
    ::= { hpnicfDot11APObjectEntry 25 }

hpnicfDot11CurrAPCPUTypeCM OBJECT-TYPE
    SYNTAX      OCTET STRING
    MAX-ACCESS  read-only
    STATUS      current
    DESCRIPTION
        "Represents the CPU type of AP."
    ::= { hpnicfDot11APObjectEntry 26 }

hpnicfDot11CurrAPMemoryTypeCM OBJECT-TYPE
    SYNTAX      OCTET STRING
    MAX-ACCESS  read-only
    STATUS      current
    DESCRIPTION
        "Represents the memory card type of AP."
    ::= { hpnicfDot11APObjectEntry 27 }

hpnicfDot11CurrAPBSSIDNumberCM OBJECT-TYPE
    SYNTAX      Integer32
    MAX-ACCESS  read-only
    STATUS      current
    DESCRIPTION
        "Represents the number of BSSID configured on AP."
    ::= { hpnicfDot11APObjectEntry 28 }

-- *****************************************************************************
-- *  End of hpnicfDot11APObjectTable Definition
-- *****************************************************************************

-- *****************************************************************************
-- *  hpnicfDot11APRadioTable Definition
-- *****************************************************************************
hpnicfDot11APRadioTable OBJECT-TYPE
    SYNTAX      SEQUENCE OF HpnicfDot11APRadioEntry
    MAX-ACCESS  not-accessible
    STATUS      current
    DESCRIPTION
        "The table will describe the radio information of AP. The AP here will
        be in running status."
    ::= { hpnicfDot11APObjectGroup 3 }

hpnicfDot11APRadioEntry OBJECT-TYPE
    SYNTAX      HpnicfDot11APRadioEntry
    MAX-ACCESS  not-accessible
    STATUS      current
    DESCRIPTION
        "Each entry contains the information of each radio of a specific AP."
    INDEX
        {
            hpnicfDot11CurAPID,
            hpnicfDot11RadioID
        }
    ::= { hpnicfDot11APRadioTable 1 }

HpnicfDot11APRadioEntry ::= SEQUENCE
    {
        hpnicfDot11CurAPID            OCTET STRING,
        hpnicfDot11RadioID            Integer32,
        hpnicfDot11AdminStatus        TruthValue,
        hpnicfDot11OperStatus         TruthValue,
        hpnicfDot11Channel            HpnicfDot11ChannelScopeType,
        hpnicfDot11TxPowerLevel       HpnicfDot11TxPwrLevelScopeType,
        hpnicfDot11APRadioIfIndex     Integer32,
        hpnicfDot11AntennaGain        Integer32,
        hpnicfDot11MaxBandwidth       Integer32,
        hpnicfDot11ResourceUseRatio   Integer32,
        hpnicfDot11RadioModeSupport   Unsigned32,
        hpnicfDot11TxPowerLevel2      Integer32,
        hpnicfDot11PowerMgmtStatus    TruthValue,
        hpnicfDot11ChannelSwitchTimes Counter32,
        hpnicfDot11AntennaType        OCTET STRING,
        hpnicfDot11DiversitySelectionRx     TruthValue,
        hpnicfDot11MaxTxPwrLvl              OCTET STRING,
        hpnicfDot11PwrAttRange              Integer32,
        hpnicfDot11AvgRxSignalStrength      Integer32,
        hpnicfDot11HighestRxSignalStrength  Integer32,
        hpnicfDot11LowestRxSignalStrength   Integer32,
        hpnicfDot11RadioIfUpdownTimes       Counter32,
        hpnicfDot11RadioIfLastChange        TimeTicks,
        hpnicfDot11RadioModeSupport2        Unsigned32,
        hpnicfDot11OperStatusCM             INTEGER
    }

hpnicfDot11CurAPID OBJECT-TYPE
    SYNTAX      OCTET STRING(SIZE(0..64))
    MAX-ACCESS  not-accessible
    STATUS      current
    DESCRIPTION
        "To uniquely identify a AP in running status."
    ::= { hpnicfDot11APRadioEntry 1 }

hpnicfDot11RadioID OBJECT-TYPE
    SYNTAX      Integer32(0..2147483647)
    MAX-ACCESS  accessible-for-notify
    STATUS      current
    DESCRIPTION
        "Represents each radio."
    ::= { hpnicfDot11APRadioEntry 2 }

hpnicfDot11AdminStatus OBJECT-TYPE
    SYNTAX      TruthValue
    MAX-ACCESS  read-only
    STATUS      current
    DESCRIPTION
        "Represents the administrator status of radio."
    ::= { hpnicfDot11APRadioEntry 3 }

hpnicfDot11OperStatus OBJECT-TYPE
    SYNTAX      TruthValue
    MAX-ACCESS  read-only
    STATUS      current
    DESCRIPTION
        "Represents the operational status of radio."
    ::= { hpnicfDot11APRadioEntry 4 }

hpnicfDot11Channel OBJECT-TYPE
    SYNTAX      HpnicfDot11ChannelScopeType
    MAX-ACCESS  read-only
    STATUS      current
    DESCRIPTION
        "Represents the current channel allocation for radio."
    ::= { hpnicfDot11APRadioEntry 5 }

hpnicfDot11TxPowerLevel OBJECT-TYPE
    SYNTAX      HpnicfDot11TxPwrLevelScopeType
    UNITS       "dbm"
    MAX-ACCESS  read-only
    STATUS      current
    DESCRIPTION
        "Represents the current transmit power level for radio."
    ::= { hpnicfDot11APRadioEntry 6 }

hpnicfDot11APRadioIfIndex OBJECT-TYPE
    SYNTAX      Integer32
    MAX-ACCESS  read-only
    STATUS      current
    DESCRIPTION
        "Represents the interface index for the radio."
    ::= { hpnicfDot11APRadioEntry 7 }

hpnicfDot11AntennaGain OBJECT-TYPE
    SYNTAX      Integer32
    UNITS       "dBi"
    MAX-ACCESS  read-only
    STATUS      current
    DESCRIPTION
        "Represents the current gain for antenna."
    ::= { hpnicfDot11APRadioEntry 8 }

hpnicfDot11MaxBandwidth OBJECT-TYPE
    SYNTAX      Integer32
    UNITS       "Mbps"
    MAX-ACCESS  read-only
    STATUS      current
    DESCRIPTION
        "Represents the maximum bandwidth for the radio."
    ::= { hpnicfDot11APRadioEntry 9 }

hpnicfDot11ResourceUseRatio OBJECT-TYPE
    SYNTAX      Integer32
    UNITS       "onepercent"
    MAX-ACCESS  read-only
    STATUS      current
    DESCRIPTION
        "Represents the ratio of radio resource usage."
    ::= { hpnicfDot11APRadioEntry 10 }

hpnicfDot11RadioModeSupport OBJECT-TYPE
    SYNTAX      Unsigned32
    MAX-ACCESS  read-only
    STATUS      current
    DESCRIPTION
        "Represents radio type supported by the radio.
        The WLAN system supports the following possible radio type:
        dot11a(1),
        dot11b(2),
        dot11g(4),
        dot11gn(16),
        dot11an(32).
        For the radio, it could support multiple radio types at
        the same time.  So the value of this object could combine multiple
        values of radio type above.
        For example:
        For one radio which supports both dot11b and dot11g mode, when get
        value from the object, the value is 5(1 + 4)."
    ::= { hpnicfDot11APRadioEntry 11 }

hpnicfDot11TxPowerLevel2 OBJECT-TYPE
    SYNTAX      Integer32(1..8)
    MAX-ACCESS  read-only
    STATUS      current
    DESCRIPTION
        "The TxPowerLevel N currently being used to transmit data."
    ::= { hpnicfDot11APRadioEntry 12 }

hpnicfDot11PowerMgmtStatus OBJECT-TYPE
    SYNTAX      TruthValue
    MAX-ACCESS  read-only
    STATUS      current
    DESCRIPTION
        "Represents status of power management of the radio."
    ::= { hpnicfDot11APRadioEntry 13 }

hpnicfDot11ChannelSwitchTimes OBJECT-TYPE
    SYNTAX      Counter32
    MAX-ACCESS  read-only
    STATUS      current
    DESCRIPTION
        "Represents the channel switch times."
    ::= { hpnicfDot11APRadioEntry 14 }

hpnicfDot11AntennaType OBJECT-TYPE
    SYNTAX      OCTET STRING
    MAX-ACCESS  read-only
    STATUS      current
    DESCRIPTION
        "Represents type of the antenna which radio used."
    ::= { hpnicfDot11APRadioEntry 15 }

hpnicfDot11DiversitySelectionRx OBJECT-TYPE
    SYNTAX      TruthValue
    MAX-ACCESS  read-only
    STATUS      current
    DESCRIPTION
        "Represents the diversity selection received."
    ::= { hpnicfDot11APRadioEntry 16 }

hpnicfDot11MaxTxPwrLvl OBJECT-TYPE
    SYNTAX      OCTET STRING
    MAX-ACCESS  read-only
    STATUS      current
    DESCRIPTION
        "Represents the maximum transmit power."
    ::= { hpnicfDot11APRadioEntry 17 }

hpnicfDot11PwrAttRange OBJECT-TYPE
    SYNTAX      Integer32
    MAX-ACCESS  read-only
    STATUS      current
    DESCRIPTION
        "Represents the range of power attenuation."
    ::= { hpnicfDot11APRadioEntry 18 }

hpnicfDot11AvgRxSignalStrength OBJECT-TYPE
    SYNTAX      Integer32
    UNITS       "dBm"
    MAX-ACCESS  read-only
    STATUS      current
    DESCRIPTION
        "Represents the average received signal strength."
    ::= { hpnicfDot11APRadioEntry 19 }

hpnicfDot11HighestRxSignalStrength OBJECT-TYPE
    SYNTAX      Integer32
    UNITS       "dBm"
    MAX-ACCESS  read-only
    STATUS      current
    DESCRIPTION
        "Represents the highest received signal strength."
    ::= { hpnicfDot11APRadioEntry 20 }

hpnicfDot11LowestRxSignalStrength OBJECT-TYPE
    SYNTAX      Integer32
    UNITS       "dBm"
    MAX-ACCESS  read-only
    STATUS      current
    DESCRIPTION
        "Represents the lowest received signal strength."
    ::= { hpnicfDot11APRadioEntry 21 }

hpnicfDot11RadioIfUpdownTimes OBJECT-TYPE
    SYNTAX      Counter32
    MAX-ACCESS  read-only
    STATUS      current
    DESCRIPTION
        "Represents the up/down times on radio interface."
    ::= { hpnicfDot11APRadioEntry 22 }

hpnicfDot11RadioIfLastChange OBJECT-TYPE
    SYNTAX      TimeTicks
    MAX-ACCESS  read-only
    STATUS      current
    DESCRIPTION
        "Represents time at last change that occurred on radio interface."
    ::= { hpnicfDot11APRadioEntry 23 }

hpnicfDot11RadioModeSupport2 OBJECT-TYPE
    SYNTAX      Unsigned32
    MAX-ACCESS  read-only
    STATUS      current
    DESCRIPTION
        "Represents radio type supported by the radio.
        The WLAN system supports the following possible radio type:
        dot11a(1),
        dot11b(2),
        dot11g(4),
        dot11an(8),
        dot11gn(16).
        For the radio, it could support multiple radio types at
        the same time.  So the value of this object could combine multiple
        values of radio type above.
        For example:
        For one radio which supports both dot11b and dot11g mode, when get
        value from the object, the value is 5(1 + 4)."
    ::= { hpnicfDot11APRadioEntry 24 }

hpnicfDot11OperStatusCM OBJECT-TYPE
    SYNTAX      INTEGER
        {
            up(1),
            down(2),
            testing(3),
            admindown(4)
        }
    MAX-ACCESS  read-only
    STATUS      current
    DESCRIPTION
        "Represents the operational status of radio."
    ::= { hpnicfDot11APRadioEntry 25 }
-- *****************************************************************************
-- *  End of hpnicfDot11APRadioTable Definition
-- *****************************************************************************

-- *****************************************************************************
-- *  hpnicfDot11APBSSTable Definition
-- *****************************************************************************
hpnicfDot11APBSSTable OBJECT-TYPE
    SYNTAX      SEQUENCE OF HpnicfDot11APBSSEntry
    MAX-ACCESS  not-accessible
    STATUS      current
    DESCRIPTION
        "After AP connect to AC and get AP template configuration,
        it will create BSS data structure for each radio.
        The table will describe BSS information of AP and service
        policy as per BSS."
    ::= { hpnicfDot11APObjectGroup 4 }

hpnicfDot11APBSSEntry OBJECT-TYPE
    SYNTAX      HpnicfDot11APBSSEntry
    MAX-ACCESS  not-accessible
    STATUS      current
    DESCRIPTION
        "Each entry contains information of each BSS for specific radio."
    INDEX
        {
            hpnicfDot11CurAPID,
            hpnicfDot11RadioID,
            hpnicfDot11WlanID
        }
    ::= { hpnicfDot11APBSSTable 1 }

HpnicfDot11APBSSEntry ::= SEQUENCE
    {
        hpnicfDot11WlanID             Integer32,
        hpnicfDot11BSSID              MacAddress,
        hpnicfDot11CurrSvcPolicyID    HpnicfDot11ServicePolicyIDType,
        hpnicfDot11SSID               OCTET STRING,
        hpnicfDot11CurrSSIDResourceUseRatio             Integer32,
        hpnicfDot11APEssVlanId                          Integer32
    }

hpnicfDot11WlanID OBJECT-TYPE
    SYNTAX      Integer32(0..2147483647)
    MAX-ACCESS  not-accessible
    STATUS      current
    DESCRIPTION
        "Represents ID of a specific ESS."
    ::= { hpnicfDot11APBSSEntry 1 }

hpnicfDot11BSSID OBJECT-TYPE
    SYNTAX      MacAddress
    MAX-ACCESS  read-only
    STATUS      current
    DESCRIPTION
        "As MAC Address format, it is to identify BSS."
    ::= { hpnicfDot11APBSSEntry 2 }

hpnicfDot11CurrSvcPolicyID OBJECT-TYPE
    SYNTAX      HpnicfDot11ServicePolicyIDType
    MAX-ACCESS  read-only
    STATUS      current
    DESCRIPTION
        "Represents the ID of each service policy used by the AP."
    ::= { hpnicfDot11APBSSEntry 3 }

hpnicfDot11SSID OBJECT-TYPE
    SYNTAX      OCTET STRING
    MAX-ACCESS  read-only
    STATUS      current
    DESCRIPTION
        "This object represents the SSID corresponding to this BSS."
    ::= { hpnicfDot11APBSSEntry 4 }

hpnicfDot11CurrSSIDResourceUseRatio OBJECT-TYPE
    SYNTAX      Integer32
    MAX-ACCESS  read-only
    STATUS      current
    DESCRIPTION
        "Represents the ratio of resource usage of curr SSID"
    ::= { hpnicfDot11APBSSEntry 5 }

hpnicfDot11APEssVlanId OBJECT-TYPE
    SYNTAX      Integer32
    MAX-ACCESS  read-only
    STATUS      current
    DESCRIPTION
        "This object represents the VlanID of the interface ESS
        corresponding to this BSS."
    ::= { hpnicfDot11APBSSEntry 6 }
-- *****************************************************************************
-- *  End of hpnicfDot11APBSSTable Definition
-- *****************************************************************************

-- *****************************************************************************
-- *  hpnicfDot11APModelTable Definition
-- *****************************************************************************
hpnicfDot11APModelTable OBJECT-TYPE
    SYNTAX      SEQUENCE OF HpnicfDot11APModelEntry
    MAX-ACCESS  not-accessible
    STATUS      current
    DESCRIPTION
        "The table defines the capability information for a specific
        kind of AP."
    ::= { hpnicfDot11APObjectGroup 5 }

hpnicfDot11APModelEntry OBJECT-TYPE
    SYNTAX      HpnicfDot11APModelEntry
    MAX-ACCESS  not-accessible
    STATUS      current
    DESCRIPTION
        "Each entry contains capability information for a specific kind
        of AP."
    INDEX
        {
            IMPLIED hpnicfDot11APModelAlias
        }
    ::= { hpnicfDot11APModelTable 1 }

HpnicfDot11APModelEntry ::= SEQUENCE
    {
        hpnicfDot11APModelAlias         OCTET STRING,
        hpnicfDot11APModelName          OCTET STRING,
        hpnicfDot11RadioNumSupport      HpnicfDot11RadioScopeType,
        hpnicfDot11StationNumSupport    Integer32,
        hpnicfDot11MACModeSupport       HpnicfDot11MACModeType,
        hpnicfDot11APManufacturer       OCTET STRING,
        hpnicfDot11APCPUType            OCTET STRING,
        hpnicfDot11APCPUClockSpeed      Unsigned32,
        hpnicfDot11APMemoryType         OCTET STRING,
        hpnicfDot11APMemorySize         Unsigned32,
        hpnicfDot11APFlashType          OCTET STRING,
        hpnicfDot11APFlashSize          Unsigned32,
        hpnicfDot11APMemSize            Gauge32,
        hpnicfDot11APFlashSizeInBytes   Unsigned32
    }

hpnicfDot11APModelAlias OBJECT-TYPE
    SYNTAX      OCTET STRING(SIZE(0..127))
    MAX-ACCESS  not-accessible
    STATUS      current
    DESCRIPTION
        "Represents alias of AP model name."
    ::= { hpnicfDot11APModelEntry 1 }

hpnicfDot11APModelName OBJECT-TYPE
    SYNTAX      OCTET STRING
    MAX-ACCESS  read-only
    STATUS      current
    DESCRIPTION
        "Represents AP model name(like WA2100)."
    ::= { hpnicfDot11APModelEntry 2 }

hpnicfDot11RadioNumSupport OBJECT-TYPE
    SYNTAX      HpnicfDot11RadioScopeType
    MAX-ACCESS  read-only
    STATUS      current
    DESCRIPTION
        "Represents how many radios the specific AP model
        could support."
    ::= { hpnicfDot11APModelEntry 3 }

hpnicfDot11StationNumSupport OBJECT-TYPE
    SYNTAX      Integer32
    MAX-ACCESS  read-only
    STATUS      current
    DESCRIPTION
        "Represents how many station could be supported by a specific
        AP model."
    ::= { hpnicfDot11APModelEntry 4 }

hpnicfDot11MACModeSupport OBJECT-TYPE
    SYNTAX      HpnicfDot11MACModeType
    MAX-ACCESS  read-only
    STATUS      current
    DESCRIPTION
        "Represents the MAC mode type could be supported by a specific
        AP model."
    DEFVAL      { split }
    ::= { hpnicfDot11APModelEntry 5 }

hpnicfDot11APManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { hpnicfDot11APModelEntry 6 }

hpnicfDot11APCPUType OBJECT-TYPE
    SYNTAX      OCTET STRING
    MAX-ACCESS  read-only
    STATUS      current
    DESCRIPTION
        "Represents the CPU type of AP"
    ::= { hpnicfDot11APModelEntry 7 }

hpnicfDot11APCPUClockSpeed OBJECT-TYPE
    SYNTAX      Unsigned32
    UNITS       "Hz"
    MAX-ACCESS  read-only
    STATUS      current
    DESCRIPTION
        "Represents the clock speed of CPU."
    ::= { hpnicfDot11APModelEntry 8 }

hpnicfDot11APMemoryType OBJECT-TYPE
    SYNTAX      OCTET STRING
    MAX-ACCESS  read-only
    STATUS      current
    DESCRIPTION
        "Represents the memory card type of AP"
    ::= { hpnicfDot11APModelEntry 9 }

hpnicfDot11APMemorySize OBJECT-TYPE
    SYNTAX      Unsigned32
    UNITS       "kbytes"
    MAX-ACCESS  read-only
    STATUS      current
    DESCRIPTION
        "Represents the size of AP memory card."
    ::= { hpnicfDot11APModelEntry 20 }

hpnicfDot11APFlashType OBJECT-TYPE
    SYNTAX      OCTET STRING
    MAX-ACCESS  read-only
    STATUS      current
    DESCRIPTION
        "Represents the flash card type of AP"
    ::= { hpnicfDot11APModelEntry 11 }

hpnicfDot11APFlashSize OBJECT-TYPE
    SYNTAX      Unsigned32
    UNITS       "kbytes"
    MAX-ACCESS  read-only
    STATUS      current
    DESCRIPTION
        "Represents the size of AP flash card."
    ::= { hpnicfDot11APModelEntry 12 }

hpnicfDot11APMemSize OBJECT-TYPE
    SYNTAX      Gauge32
    UNITS       "bytes"
    MAX-ACCESS  read-only
    STATUS      current
    DESCRIPTION
        "Represents the size of AP memory card."
    ::= { hpnicfDot11APModelEntry 13 }

hpnicfDot11APFlashSizeInBytes OBJECT-TYPE
    SYNTAX      Unsigned32
    UNITS       "bytes"
    MAX-ACCESS  read-only
    STATUS      current
    DESCRIPTION
        "This object represents the size of AP flash card in bytes."
    ::= { hpnicfDot11APModelEntry 14 }

-- *****************************************************************************
-- *  End of hpnicfDot11APModelTable Definition
-- *****************************************************************************

-- *****************************************************************************
-- *  hpnicfDot11APIfTable Definition
-- *****************************************************************************
hpnicfDot11APIfTable OBJECT-TYPE
    SYNTAX      SEQUENCE OF HpnicfDot11APIfEntry
    MAX-ACCESS  not-accessible
    STATUS      current
    DESCRIPTION
        "This table represents the AP interface informations."
    ::= { hpnicfDot11APObjectGroup 6 }

hpnicfDot11APIfEntry OBJECT-TYPE
    SYNTAX      HpnicfDot11APIfEntry
    MAX-ACCESS  not-accessible
    STATUS      current
    DESCRIPTION
        "Each entry of the table will provide data for the interface of AP."
    INDEX
        {
            hpnicfDot11APObjID,
            hpnicfDot11APIfIndex
        }
    ::= { hpnicfDot11APIfTable 1 }

HpnicfDot11APIfEntry ::= SEQUENCE
    {
        hpnicfDot11APIfIndex         Integer32,
        hpnicfDot11APIfDescr         OCTET STRING,
        hpnicfDot11APIfType          Integer32,
        hpnicfDot11APIfMtu           Integer32,
        hpnicfDot11APIfPHYAddress    OCTET STRING,
        hpnicfDot11APIfSpeed         Integer32,
        hpnicfDot11APIfInDataRate    Integer32,
        hpnicfDot11APIfOutDataRate   Integer32,
        hpnicfDot11APIfSpeedKbps     Gauge32,
        hpnicfDot11APIfTypeCM        Integer32
    }

hpnicfDot11APIfIndex OBJECT-TYPE
    SYNTAX      Integer32
    MAX-ACCESS  not-accessible
    STATUS      current
    DESCRIPTION
        "Represents the index for a interface."
    ::= { hpnicfDot11APIfEntry 1 }

hpnicfDot11APIfDescr OBJECT-TYPE
    SYNTAX      OCTET STRING
    MAX-ACCESS  read-only
    STATUS      current
    DESCRIPTION
        "Represents the interface description for a interface."
    ::= { hpnicfDot11APIfEntry 2 }

hpnicfDot11APIfType OBJECT-TYPE
    SYNTAX      Integer32
    MAX-ACCESS  read-only
    STATUS      current
    DESCRIPTION
        "Represents the interface type for a interface."
    ::= { hpnicfDot11APIfEntry 3 }

hpnicfDot11APIfMtu OBJECT-TYPE
    SYNTAX      Integer32
    MAX-ACCESS  read-write
    STATUS      current
    DESCRIPTION
        "Represents size of the largest datagram which can
        be sent/received on the interface, specified in octets."
    ::= { hpnicfDot11APIfEntry 4 }

hpnicfDot11APIfPHYAddress OBJECT-TYPE
    SYNTAX      OCTET STRING
    MAX-ACCESS  read-only
    STATUS      current
    DESCRIPTION
        "Represents the PHY address of interface."
    ::= { hpnicfDot11APIfEntry 5 }

hpnicfDot11APIfSpeed OBJECT-TYPE
    SYNTAX      Integer32
    UNITS       "Mbps"
    MAX-ACCESS  read-only
    STATUS      current
    DESCRIPTION
        "Represents maximum bandwidth of this interface."
    ::= { hpnicfDot11APIfEntry 6 }

hpnicfDot11APIfInDataRate OBJECT-TYPE
    SYNTAX      Integer32
    UNITS       "Kbps"
    MAX-ACCESS  read-only
    STATUS      current
    DESCRIPTION
        "Represents the average input data rate of this interface in
        latest 300 seconds."
    ::= { hpnicfDot11APIfEntry 7 }

hpnicfDot11APIfOutDataRate OBJECT-TYPE
    SYNTAX      Integer32
    UNITS       "Kbps"
    MAX-ACCESS  read-only
    STATUS      current
    DESCRIPTION
        "Represents the average output data rate of this interface in
        latest 300 seconds."
    ::= { hpnicfDot11APIfEntry 8 }

hpnicfDot11APIfSpeedKbps OBJECT-TYPE
    SYNTAX      Gauge32
    UNITS       "kbps"
    MAX-ACCESS  read-only
    STATUS      current
    DESCRIPTION
        "Represents maximum bandwidth of this interface."
    ::= { hpnicfDot11APIfEntry 9 }

hpnicfDot11APIfTypeCM OBJECT-TYPE
    SYNTAX      Integer32
    MAX-ACCESS  read-only
    STATUS      current
    DESCRIPTION
        "Represents the interface type."
    ::= { hpnicfDot11APIfEntry 10 }

-- *****************************************************************************
-- *  End of hpnicfDot11APIfTable Definition
-- *****************************************************************************

-- *****************************************************************************
-- *  hpnicfDot11APSSIDObjectTable Definition
-- *****************************************************************************
hpnicfDot11APSSIDObjectTable OBJECT-TYPE
    SYNTAX      SEQUENCE OF HpnicfDot11APSSIDObjectEntry
    MAX-ACCESS  not-accessible
    STATUS      current
    DESCRIPTION
        "This table provides BSSID number configuration information
         based on SSID."
    ::= { hpnicfDot11APObjectGroup 7 }

hpnicfDot11APSSIDObjectEntry OBJECT-TYPE
    SYNTAX      HpnicfDot11APSSIDObjectEntry
    MAX-ACCESS  not-accessible
    STATUS      current
    DESCRIPTION
        "Each entry provides BSSID number configuration information
         of a SSID."
    INDEX
        {
            hpnicfDot11APConfigSPID
        }
    ::= { hpnicfDot11APSSIDObjectTable 1 }

HpnicfDot11APSSIDObjectEntry ::= SEQUENCE
    {
        hpnicfDot11APConfigSPID              HpnicfDot11ServicePolicyIDType,
        hpnicfDot11APConfigSSIDName          HpnicfDot11SSIDStringType,
        hpnicfDot11APConfigBSSIDNum          Integer32,
        hpnicfDot11APConfigPortalStaNum      Integer32
    }

hpnicfDot11APConfigSPID OBJECT-TYPE
    SYNTAX      HpnicfDot11ServicePolicyIDType
    MAX-ACCESS  not-accessible
    STATUS      current
    DESCRIPTION
        "Represents the service policy ID."
    ::= { hpnicfDot11APSSIDObjectEntry 1 }

hpnicfDot11APConfigSSIDName OBJECT-TYPE
    SYNTAX      HpnicfDot11SSIDStringType
    MAX-ACCESS  read-only
    STATUS      current
    DESCRIPTION
        "Represents the SSID name of this service policy."
    ::= { hpnicfDot11APSSIDObjectEntry 2 }

hpnicfDot11APConfigBSSIDNum OBJECT-TYPE
    SYNTAX      Integer32
    MAX-ACCESS  read-only
    STATUS      current
    DESCRIPTION
        "Represents the number of BSSID that be configured
         with current SSID."
    ::= { hpnicfDot11APSSIDObjectEntry 3 }

hpnicfDot11APConfigPortalStaNum OBJECT-TYPE
    SYNTAX      Integer32
    MAX-ACCESS  read-only
    STATUS      current
    DESCRIPTION
        "Represents the total number of associated protal
        stations with current SSID."
    ::= { hpnicfDot11APSSIDObjectEntry 4 }

-- *****************************************************************************
-- *  End of hpnicfDot11APSSIDObjectTable Definition
-- *****************************************************************************

-- *****************************************************************************
-- *  hpnicfDot11APSysInfoTable Definition
-- *****************************************************************************
hpnicfDot11APSysInfoTable OBJECT-TYPE
    SYNTAX      SEQUENCE OF HpnicfDot11APSysInfoEntry
    MAX-ACCESS  not-accessible
    STATUS      current
    DESCRIPTION
        "The table provides the system information of the AP."
    ::= { hpnicfDot11APObjectGroup 8 }

hpnicfDot11APSysInfoEntry OBJECT-TYPE
    SYNTAX      HpnicfDot11APSysInfoEntry
    MAX-ACCESS  not-accessible
    STATUS      current
    DESCRIPTION
        "Each entry provides system information of an AP."
    INDEX
        {
            hpnicfDot11APElementIndex
        }
    ::= { hpnicfDot11APSysInfoTable 1 }

HpnicfDot11APSysInfoEntry ::= SEQUENCE
    {
        hpnicfDot11APSysUpTime           TimeTicks,
        hpnicfDot11APCPURTUsage          Integer32,
        hpnicfDot11APCPUAvgUsage         Integer32,
        hpnicfDot11APMemRTUsage          Integer32,
        hpnicfDot11APMemAvgUsage         Integer32,
        hpnicfDot11APIPAddressGateway    IpAddress,
        hpnicfDot11APACAssociateStatus   INTEGER,
        hpnicfDot11APManuBuildInfo       OCTET STRING,
        hpnicfDot11APFlashFreeSize       Unsigned32,
        hpnicfDot11APTemperature         Integer32
    }

hpnicfDot11APSysUpTime OBJECT-TYPE
    SYNTAX      TimeTicks
    MAX-ACCESS  read-only
    STATUS      current
    DESCRIPTION
        "Represents how long AP has been powered on."
    ::= { hpnicfDot11APSysInfoEntry 1 }

hpnicfDot11APCPURTUsage OBJECT-TYPE
    SYNTAX      Integer32(0..100)
    UNITS       "onepercent"
    MAX-ACCESS  read-only
    STATUS      current
    DESCRIPTION
        "Represents the CPU real time usage for AP."
    ::= { hpnicfDot11APSysInfoEntry 2 }

hpnicfDot11APCPUAvgUsage OBJECT-TYPE
    SYNTAX      Integer32(0..100)
    UNITS       "onepercent"
    MAX-ACCESS  read-only
    STATUS      current
    DESCRIPTION
        "Represents the CPU average usage for AP."
    ::= { hpnicfDot11APSysInfoEntry 3 }

hpnicfDot11APMemRTUsage OBJECT-TYPE
    SYNTAX      Integer32(0..100)
    UNITS       "onepercent"
    MAX-ACCESS  read-only
    STATUS      current
    DESCRIPTION
        "Represents the memory real time usage for AP."
    ::= { hpnicfDot11APSysInfoEntry 4 }

hpnicfDot11APMemAvgUsage OBJECT-TYPE
    SYNTAX      Integer32(0..100)
    UNITS       "onepercent"
    MAX-ACCESS  read-only
    STATUS      current
    DESCRIPTION
        "Represents the average memory usage for AP."
    ::= { hpnicfDot11APSysInfoEntry 5 }

hpnicfDot11APIPAddressGateway OBJECT-TYPE
    SYNTAX      IpAddress
    MAX-ACCESS  read-only
    STATUS      current
    DESCRIPTION
        "Represents the IP address gateway for AP."
    ::= { hpnicfDot11APSysInfoEntry 6 }

hpnicfDot11APACAssociateStatus OBJECT-TYPE
    SYNTAX      INTEGER
        {
            associated(1),
            deassociated(2),
            downloadingImage(3)
        }
    MAX-ACCESS  read-only
    STATUS      current
    DESCRIPTION
        "Represents associate status of AP and AC."
    ::= { hpnicfDot11APSysInfoEntry 7 }

hpnicfDot11APManuBuildInfo OBJECT-TYPE
    SYNTAX      OCTET STRING(SIZE(0..255))
    MAX-ACCESS  read-only
    STATUS      current
    DESCRIPTION
        "Represents the device version information for AP."
    ::= { hpnicfDot11APSysInfoEntry 8 }

hpnicfDot11APFlashFreeSize OBJECT-TYPE
    SYNTAX      Unsigned32
    UNITS       "bytes"
    MAX-ACCESS  read-only
    STATUS      current
    DESCRIPTION
        "Represents the free size of AP flash card."
    ::= { hpnicfDot11APSysInfoEntry 9 }

hpnicfDot11APTemperature OBJECT-TYPE
    SYNTAX      Integer32
    MAX-ACCESS  read-only
    STATUS      current
    DESCRIPTION
        "Represents the device temperature information for AP."
    ::= { hpnicfDot11APSysInfoEntry 10 }

-- *****************************************************************************
-- *  End of hpnicfDot11APSysInfoTable Definition
-- *****************************************************************************

-- *****************************************************************************
-- *  hpnicfDot11APIdleListTable Definition
-- *****************************************************************************
hpnicfDot11APIdleListTable OBJECT-TYPE
    SYNTAX      SEQUENCE OF HpnicfDot11APIdleListEntry
    MAX-ACCESS  not-accessible
    STATUS      current
    DESCRIPTION
        "This table provides the list of idle AP."
    ::= { hpnicfDot11APObjectGroup 9 }

hpnicfDot11APIdleListEntry OBJECT-TYPE
    SYNTAX      HpnicfDot11APIdleListEntry
    MAX-ACCESS  not-accessible
    STATUS      current
    DESCRIPTION
        "Each entry provides information of a idle AP."
    INDEX
        {
            hpnicfDot11APIdleTemplateName
        }
    ::= { hpnicfDot11APIdleListTable 1 }

HpnicfDot11APIdleListEntry ::= SEQUENCE
    {
        hpnicfDot11APIdleTemplateName OCTET STRING,
        hpnicfDot11APIdleSerialID     OCTET STRING
    }

hpnicfDot11APIdleTemplateName OBJECT-TYPE
    SYNTAX      OCTET STRING(SIZE(0..127))
    MAX-ACCESS  not-accessible
    STATUS      current
    DESCRIPTION
        "Represents the name of idle AP template."
    ::= { hpnicfDot11APIdleListEntry 1 }

hpnicfDot11APIdleSerialID    OBJECT-TYPE
    SYNTAX      OCTET STRING
    MAX-ACCESS  read-only
    STATUS      current
    DESCRIPTION
        "Represents AP serial ID."
    ::= { hpnicfDot11APIdleListEntry 2 }

-- *****************************************************************************
-- *  End of hpnicfDot11APIdleListTable Definition
-- *****************************************************************************

-- *****************************************************************************
-- *  hpnicfDot11APSysInfoByAPIDTable Definition
-- *****************************************************************************
hpnicfDot11APSysInfoByAPIDTable OBJECT-TYPE
    SYNTAX      SEQUENCE OF HpnicfDot11APSysInfoByAPIDEntry
    MAX-ACCESS  not-accessible
    STATUS      current
    DESCRIPTION
        "The table provides the system information of the AP."
    ::= { hpnicfDot11APObjectGroup 10 }

hpnicfDot11APSysInfoByAPIDEntry OBJECT-TYPE
    SYNTAX      HpnicfDot11APSysInfoByAPIDEntry
    MAX-ACCESS  not-accessible
    STATUS      current
    DESCRIPTION
        "Each entry provides system information of an AP."
    INDEX
        {
            hpnicfDot11APObjID
        }
    ::= { hpnicfDot11APSysInfoByAPIDTable 1 }

HpnicfDot11APSysInfoByAPIDEntry ::= SEQUENCE
    {
        hpnicfDot11APSysUpTime2           TimeTicks,
        hpnicfDot11APCPURTUsage2          Integer32,
        hpnicfDot11APCPUAvgUsage2         Integer32,
        hpnicfDot11APMemRTUsage2          Integer32,
        hpnicfDot11APMemAvgUsage2         Integer32,
        hpnicfDot11APIPAddressGateway2    IpAddress,
        hpnicfDot11APACAssociateStatus2   INTEGER,
        hpnicfDot11APManuBuildInfo2       OCTET STRING,
        hpnicfDot11APFlashFreeSize2       Unsigned32,
        hpnicfDot11APTemperature2         Integer32,
        hpnicfDot11APMacAddress2          MacAddress,
        hpnicfDot11APACAssociateStatusCM  INTEGER
    }

hpnicfDot11APSysUpTime2 OBJECT-TYPE
    SYNTAX      TimeTicks
    MAX-ACCESS  read-only
    STATUS      current
    DESCRIPTION
        "Represents how long AP has been powered on."
    ::= { hpnicfDot11APSysInfoByAPIDEntry 1 }

hpnicfDot11APCPURTUsage2 OBJECT-TYPE
    SYNTAX      Integer32(0..100)
    UNITS       "onepercent"
    MAX-ACCESS  read-only
    STATUS      current
    DESCRIPTION
        "Represents the CPU real time usage for AP."
    ::= { hpnicfDot11APSysInfoByAPIDEntry 2 }

hpnicfDot11APCPUAvgUsage2 OBJECT-TYPE
    SYNTAX      Integer32(0..100)
    UNITS       "onepercent"
    MAX-ACCESS  read-only
    STATUS      current
    DESCRIPTION
        "Represents the CPU average usage for AP."
    ::= { hpnicfDot11APSysInfoByAPIDEntry 3 }

hpnicfDot11APMemRTUsage2 OBJECT-TYPE
    SYNTAX      Integer32(0..100)
    UNITS       "onepercent"
    MAX-ACCESS  read-only
    STATUS      current
    DESCRIPTION
        "Represents the memory real time usage for AP."
    ::= { hpnicfDot11APSysInfoByAPIDEntry 4 }

hpnicfDot11APMemAvgUsage2 OBJECT-TYPE
    SYNTAX      Integer32(0..100)
    UNITS       "onepercent"
    MAX-ACCESS  read-only
    STATUS      current
    DESCRIPTION
        "Represents the average memory usage for AP."
    ::= { hpnicfDot11APSysInfoByAPIDEntry 5 }

hpnicfDot11APIPAddressGateway2 OBJECT-TYPE
    SYNTAX      IpAddress
    MAX-ACCESS  read-only
    STATUS      current
    DESCRIPTION
        "Represents the IP address gateway for AP."
    ::= { hpnicfDot11APSysInfoByAPIDEntry 6 }

hpnicfDot11APACAssociateStatus2 OBJECT-TYPE
    SYNTAX      INTEGER
        {
            associated(1),
            deassociated(2),
            downloadingImage(3)
        }
    MAX-ACCESS  read-only
    STATUS      current
    DESCRIPTION
        "Represents associate status of AP and AC."
    ::= { hpnicfDot11APSysInfoByAPIDEntry 7 }

hpnicfDot11APManuBuildInfo2 OBJECT-TYPE
    SYNTAX      OCTET STRING(SIZE(0..255))
    MAX-ACCESS  read-only
    STATUS      current
    DESCRIPTION
        "Represents the device version information for AP."
    ::= { hpnicfDot11APSysInfoByAPIDEntry 8 }

hpnicfDot11APFlashFreeSize2 OBJECT-TYPE
    SYNTAX      Unsigned32
    UNITS       "bytes"
    MAX-ACCESS  read-only
    STATUS      current
    DESCRIPTION
        "Represents the free size of AP flash card."
    ::= { hpnicfDot11APSysInfoByAPIDEntry 9 }

hpnicfDot11APTemperature2 OBJECT-TYPE
    SYNTAX      Integer32
    MAX-ACCESS  read-only
    STATUS      current
    DESCRIPTION
        "Represents the device temperature information for AP."
    ::= { hpnicfDot11APSysInfoByAPIDEntry 10 }

hpnicfDot11APMacAddress2 OBJECT-TYPE
    SYNTAX      MacAddress
    MAX-ACCESS  read-only
    STATUS      current
    DESCRIPTION
        "Represents the MAC address of AP."
    ::= { hpnicfDot11APSysInfoByAPIDEntry 11 }

hpnicfDot11APACAssociateStatusCM OBJECT-TYPE
    SYNTAX      INTEGER
        {
            deassociated(0),
            associated(1)
        }
    MAX-ACCESS  read-only
    STATUS      current
    DESCRIPTION
        "Represents associate status of AP and AC."
    ::= { hpnicfDot11APSysInfoByAPIDEntry 12 }

-- *****************************************************************************
-- *  End of hpnicfDot11APSysInfoByAPIDTable Definition
-- *****************************************************************************

-- *****************************************************************************
-- *  hpnicfDot11APRxStatisTable Definition
-- *****************************************************************************
hpnicfDot11APRxStatisTable OBJECT-TYPE
    SYNTAX      SEQUENCE OF HpnicfDot11APRxStatisEntry
    MAX-ACCESS  not-accessible
    STATUS      current
    DESCRIPTION
        "The table will provide the receiving statistic for a specific
        radio of AP."
    ::= { hpnicfDot11APStatisGroup 1 }

hpnicfDot11APRxStatisEntry OBJECT-TYPE
    SYNTAX      HpnicfDot11APRxStatisEntry
    MAX-ACCESS  not-accessible
    STATUS      current
    DESCRIPTION
        "Each entry of the table will provide the statistic data for
        each radio of a specific AP."
    INDEX
        {
            hpnicfDot11CurAPID,
            hpnicfDot11RadioID
        }
    ::= { hpnicfDot11APRxStatisTable 1 }

HpnicfDot11APRxStatisEntry ::= SEQUENCE
    {
        hpnicfDot11RxFrameDupCnt          Counter32,
        hpnicfDot11RxFrameCnt             Counter32,
        hpnicfDot11RxUcastFrameCnt        Counter32,
        hpnicfDot11RxBcastFrameCnt        Counter32,
        hpnicfDot11RxMcastFrameCnt        Counter32,
        hpnicfDot11RxDiscardFrameCnt      Counter32,
        hpnicfDot11RxFragCnt              Counter32,
        hpnicfDot11RxFcsErrCnt            Counter32,
        hpnicfDot11RxFrameBytes           Counter32,
        hpnicfDot11RxUcastFrameBytes      Counter32,
        hpnicfDot11RxBcastFrameBytes      Counter32,
        hpnicfDot11RxMcastFrameBytes      Counter32,
        hpnicfDot11RxDiscardFrameBytes    Counter32,
        hpnicfDot11RxMgmtFrameCnt         Counter32,
        hpnicfDot11RxCtrlFrameCnt         Counter32,
        hpnicfDot11RxDataFrameCnt         Counter32,
        hpnicfDot11RxDecryptErrorCnt      Counter32,
        hpnicfDot11RxAuthenFrameCnt       Counter32,
        hpnicfDot11RxAssociateFrameCnt    Counter32,
        hpnicfDot11RxFrameErrorRatio      Integer32,
        hpnicfDot11RxPhyErrorCnt          Counter32,
        hpnicfDot11RxMICErrorCnt          Counter32,
        hpnicfDot11RxDataFrameBytes       Counter32,
        hpnicfDot11RadioRxAverSnr         Integer32,
        hpnicfDot11RxPayloadBytes         Counter32,
        hpnicfDot11RxTrafficSpeed         Integer32,
        hpnicfDot11RxUcastDataFrameCnt    Counter64,
        hpnicfDot11RxNUcastDataFrameCnt   Counter64,
        hpnicfDot11RxTotalDiscardFrameCnt Counter64,
        hpnicfDot11RxTotalIPCheckErrPacketCnt    Counter64,
        hpnicfDot11RxSignalStrengthPacketCntCM   OCTET STRING,
        hpnicfDot11RxDataFrameCntCM              Counter32
    }

hpnicfDot11RxFrameDupCnt OBJECT-TYPE
    SYNTAX      Counter32
    MAX-ACCESS  read-only
    STATUS      current
    DESCRIPTION
        "Represents the number of duplicate frames reception."
    ::= { hpnicfDot11APRxStatisEntry 1 }

hpnicfDot11RxFrameCnt OBJECT-TYPE
    SYNTAX      Counter32
    MAX-ACCESS  read-only
    STATUS      current
    DESCRIPTION
        "Represents the number of frames reception."
    ::= { hpnicfDot11APRxStatisEntry 2 }

hpnicfDot11RxUcastFrameCnt OBJECT-TYPE
    SYNTAX      Counter32
    MAX-ACCESS  read-only
    STATUS      current
    DESCRIPTION
        "Represents the number of unicast frames reception."
    ::= { hpnicfDot11APRxStatisEntry 3 }

hpnicfDot11RxBcastFrameCnt OBJECT-TYPE
    SYNTAX      Counter32
    MAX-ACCESS  read-only
    STATUS      current
    DESCRIPTION
        "Represents the number of broadcast frames reception."
    ::= { hpnicfDot11APRxStatisEntry 4 }

hpnicfDot11RxMcastFrameCnt OBJECT-TYPE
    SYNTAX      Counter32
    MAX-ACCESS  read-only
    STATUS      current
    DESCRIPTION
        "Represents the number of multicast frames reception."
    ::= { hpnicfDot11APRxStatisEntry 5 }

hpnicfDot11RxDiscardFrameCnt OBJECT-TYPE
    SYNTAX      Counter32
    MAX-ACCESS  read-only
    STATUS      current
    DESCRIPTION
        "Represents the number of frames discarded by AP."
    ::= { hpnicfDot11APRxStatisEntry 6 }

hpnicfDot11RxFragCnt OBJECT-TYPE
    SYNTAX      Counter32
    MAX-ACCESS  read-only
    STATUS      current
    DESCRIPTION
        "Represents the number of frame fragments reception."
    ::= { hpnicfDot11APRxStatisEntry 7 }

hpnicfDot11RxFcsErrCnt OBJECT-TYPE
    SYNTAX      Counter32
    MAX-ACCESS  read-only
    STATUS      current
    DESCRIPTION
        "Represents the number of FCS error frames reception."
    ::= { hpnicfDot11APRxStatisEntry 8 }

hpnicfDot11RxFrameBytes OBJECT-TYPE
    SYNTAX      Counter32
    MAX-ACCESS  read-only
    STATUS      current
    DESCRIPTION
        "Represents the bytes of frames reception."
    ::= { hpnicfDot11APRxStatisEntry 9 }

hpnicfDot11RxUcastFrameBytes OBJECT-TYPE
    SYNTAX      Counter32
    MAX-ACCESS  read-only
    STATUS      current
    DESCRIPTION
        "Represents the bytes of unicast frames reception."
    ::= { hpnicfDot11APRxStatisEntry 10 }

hpnicfDot11RxBcastFrameBytes OBJECT-TYPE
    SYNTAX      Counter32
    MAX-ACCESS  read-only
    STATUS      current
    DESCRIPTION
        "Represents the bytes of broadcast frames reception."
    ::= { hpnicfDot11APRxStatisEntry 11 }

hpnicfDot11RxMcastFrameBytes OBJECT-TYPE
    SYNTAX      Counter32
    MAX-ACCESS  read-only
    STATUS      current
    DESCRIPTION
        "Represents the bytes of multicast frames reception."
    ::= { hpnicfDot11APRxStatisEntry 12 }

hpnicfDot11RxDiscardFrameBytes OBJECT-TYPE
    SYNTAX      Counter32
    MAX-ACCESS  read-only
    STATUS      current
    DESCRIPTION
        "Represents the bytes of frames discarded by AP."
    ::= { hpnicfDot11APRxStatisEntry 13 }

hpnicfDot11RxMgmtFrameCnt OBJECT-TYPE
    SYNTAX      Counter32
    MAX-ACCESS  read-only
    STATUS      current
    DESCRIPTION
        "Represents the number of management frames reception."
    ::= { hpnicfDot11APRxStatisEntry 14 }

hpnicfDot11RxCtrlFrameCnt OBJECT-TYPE
    SYNTAX      Counter32
    MAX-ACCESS  read-only
    STATUS      current
    DESCRIPTION
        "Represents the number of control frames reception."
    ::= { hpnicfDot11APRxStatisEntry 15 }

hpnicfDot11RxDataFrameCnt OBJECT-TYPE
    SYNTAX      Counter32
    MAX-ACCESS  read-only
    STATUS      current
    DESCRIPTION
        "Represents the number of data frames reception."
    ::= { hpnicfDot11APRxStatisEntry 16 }

hpnicfDot11RxDecryptErrorCnt OBJECT-TYPE
    SYNTAX      Counter32
    MAX-ACCESS  read-only
    STATUS      current
    DESCRIPTION
        "Represents the number of decryption error."
    ::= { hpnicfDot11APRxStatisEntry 17 }

hpnicfDot11RxAuthenFrameCnt OBJECT-TYPE
    SYNTAX      Counter32
    MAX-ACCESS  read-only
    STATUS      current
    DESCRIPTION
        "Represents the number of authentication frame reception."
    ::= { hpnicfDot11APRxStatisEntry 18 }

hpnicfDot11RxAssociateFrameCnt OBJECT-TYPE
    SYNTAX      Counter32
    MAX-ACCESS  read-only
    STATUS      current
    DESCRIPTION
        "Represents the number of associate frame reception."
    ::= { hpnicfDot11APRxStatisEntry 19 }

hpnicfDot11RxFrameErrorRatio OBJECT-TYPE
    SYNTAX      Integer32
    UNITS       "onepercent"
    MAX-ACCESS  read-only
    STATUS      current
    DESCRIPTION
        "Represents the ratio of error frame."
    ::= { hpnicfDot11APRxStatisEntry 20 }

hpnicfDot11RxPhyErrorCnt OBJECT-TYPE
    SYNTAX      Counter32
    MAX-ACCESS  read-only
    STATUS      current
    DESCRIPTION
        "Represents the number of physical reception error."
    ::= { hpnicfDot11APRxStatisEntry 21 }

hpnicfDot11RxMICErrorCnt OBJECT-TYPE
    SYNTAX      Counter32
    MAX-ACCESS  read-only
    STATUS      current
    DESCRIPTION
        "Represents the number of MIC verification error."
    ::= { hpnicfDot11APRxStatisEntry 22 }

hpnicfDot11RxDataFrameBytes OBJECT-TYPE
    SYNTAX      Counter32
    MAX-ACCESS  read-only
    STATUS      current
    DESCRIPTION
        "Represents the bytes of data frames reception."
    ::= { hpnicfDot11APRxStatisEntry 23 }

hpnicfDot11RadioRxAverSnr OBJECT-TYPE
    SYNTAX      Integer32
    MAX-ACCESS  read-only
    STATUS      current
    DESCRIPTION
        "Represents the average signal noise rate of this radio."
    ::= { hpnicfDot11APRxStatisEntry 24 }

hpnicfDot11RxPayloadBytes OBJECT-TYPE
    SYNTAX      Counter32
    MAX-ACCESS  read-only
    STATUS      current
    DESCRIPTION
        "Represents the payload bytes of data frames reception."
    ::= { hpnicfDot11APRxStatisEntry 25 }

hpnicfDot11RxTrafficSpeed OBJECT-TYPE
    SYNTAX      Integer32
    UNITS       "byte/s"
    MAX-ACCESS  read-only
    STATUS      current
    DESCRIPTION
        "Represents the bytes of frames reception per second."
    ::= { hpnicfDot11APRxStatisEntry 26 }

hpnicfDot11RxUcastDataFrameCnt OBJECT-TYPE
    SYNTAX      Counter64
    MAX-ACCESS  read-only
    STATUS      current
    DESCRIPTION
        "Represents the number of unicast data frames reception."
    ::= { hpnicfDot11APRxStatisEntry 27 }

hpnicfDot11RxNUcastDataFrameCnt OBJECT-TYPE
    SYNTAX      Counter64
    MAX-ACCESS  read-only
    STATUS      current
    DESCRIPTION
        "Represents the number of non-unicast data frames reception."
    ::= { hpnicfDot11APRxStatisEntry 28 }

hpnicfDot11RxTotalDiscardFrameCnt OBJECT-TYPE
    SYNTAX      Counter64
    MAX-ACCESS  read-only
    STATUS      current
    DESCRIPTION
        "Represents the number of total frames discarded by radio."
    ::= { hpnicfDot11APRxStatisEntry 29 }

hpnicfDot11RxTotalIPCheckErrPacketCnt OBJECT-TYPE
    SYNTAX      Counter64
    MAX-ACCESS  read-only
    STATUS      current
    DESCRIPTION
        "Represents the total number of IP checksum error packets
        received through the current radio."
    ::= { hpnicfDot11APRxStatisEntry 30 }

hpnicfDot11RxSignalStrengthPacketCntCM OBJECT-TYPE
    SYNTAX      OCTET STRING
    MAX-ACCESS  read-only
    STATUS      current
    DESCRIPTION
        "Represents the count of received packets according to signal strength."
    ::= { hpnicfDot11APRxStatisEntry 31 }

hpnicfDot11RxDataFrameCntCM OBJECT-TYPE
    SYNTAX      Counter32
    MAX-ACCESS  read-only
    STATUS      current
    DESCRIPTION
        "Represents the number of received data frames, excluding retransmitted
        frames."
    ::= { hpnicfDot11APRxStatisEntry 32 }

-- *****************************************************************************
-- *  End of hpnicfDot11APRxStatisTable Definition
-- *****************************************************************************

-- *****************************************************************************
-- *  hpnicfDot11APTxStatisTable Definition
-- *****************************************************************************
hpnicfDot11APTxStatisTable OBJECT-TYPE
    SYNTAX      SEQUENCE OF HpnicfDot11APTxStatisEntry
    MAX-ACCESS  not-accessible
    STATUS      current
    DESCRIPTION
        "The table will provide the transmission statistic for a
        specific radio of AP."
    ::= { hpnicfDot11APStatisGroup 2 }

hpnicfDot11APTxStatisEntry OBJECT-TYPE
    SYNTAX      HpnicfDot11APTxStatisEntry
    MAX-ACCESS  not-accessible
    STATUS      current
    DESCRIPTION
        "Each entry of the table will provide the statistic data for
        each radio of a specific AP."
    INDEX
        {
            hpnicfDot11CurAPID,
            hpnicfDot11RadioID
        }
    ::= { hpnicfDot11APTxStatisTable 1 }

HpnicfDot11APTxStatisEntry ::= SEQUENCE
    {
        hpnicfDot11TxFragCnt              Counter32,
        hpnicfDot11FailedCnt              Counter32,
        hpnicfDot11RetryCnt               Counter32,
        hpnicfDot11MultiRetryCnt          Counter32,
        hpnicfDot11RtsSuccessCnt          Counter32,
        hpnicfDot11RtsFailCnt             Counter32,
        hpnicfDot11AckFailCnt             Counter32,
        hpnicfDot11TxFrameCnt             Counter32,
        hpnicfDot11TxUcastFrameCnt        Counter32,
        hpnicfDot11TxBcastFrameCnt        Counter32,
        hpnicfDot11TxMcastFrameCnt        Counter32,
        hpnicfDot11TxDiscardFrameCnt      Counter32,
        hpnicfDot11TxFrameBytes           Counter32,
        hpnicfDot11TxUcastFrameBytes      Counter32,
        hpnicfDot11TxBcastFrameBytes      Counter32,
        hpnicfDot11TxMcastFrameBytes      Counter32,
        hpnicfDot11TxDiscardFrameBytes    Counter32,
        hpnicfDot11TxAuthenFrameCnt       Counter32,
        hpnicfDot11TxAssociateFrameCnt    Counter32,
        hpnicfDot11TxFrameRetryRatio      Integer32,
        hpnicfDot11TxDataFrameCnt         Counter32,
        hpnicfDot11TxDataFrameBytes       Counter32,
        hpnicfDot11TxMSDUCnt              Counter32,
        hpnicfDot11TxDiscardMSDUCnt       Counter32,
        hpnicfDot11RetryMSDUCnt           Counter32,
        hpnicfDot11TxPayloadBytes         Counter32,
        hpnicfDot11TxTrafficSpeed         Integer32,
        hpnicfDot11TxErrFrameRatio        Integer32,
        hpnicfDot11TxFrameRate            Integer32,
        hpnicfDot11TxMgtFrameCnt          Counter32,
        hpnicfDot11TxCtrlFrameCnt         Counter32,
        hpnicfDot11TxMACErrCnt            Counter32,
        hpnicfDot11TxErrFrameCnt          Counter32,
        hpnicfDot11TxUcastDataFrameCnt    Counter64,
        hpnicfDot11TxNUcastDataFrameCnt   Counter64
    }

hpnicfDot11TxFragCnt OBJECT-TYPE
    SYNTAX      Counter32
    MAX-ACCESS  read-only
    STATUS      current
    DESCRIPTION
        "Represents the number of fragmented frames transmission."
    ::= { hpnicfDot11APTxStatisEntry 1 }

hpnicfDot11FailedCnt OBJECT-TYPE
    SYNTAX      Counter32
    MAX-ACCESS  read-only
    STATUS      current
    DESCRIPTION
        "Represents the number of transmission failures."
    ::= { hpnicfDot11APTxStatisEntry 2 }

hpnicfDot11RetryCnt OBJECT-TYPE
    SYNTAX      Counter32
    MAX-ACCESS  read-only
    STATUS      current
    DESCRIPTION
        "Represents the number of transmit retries."
    ::= { hpnicfDot11APTxStatisEntry 3 }

hpnicfDot11MultiRetryCnt OBJECT-TYPE
    SYNTAX      Counter32
    MAX-ACCESS  read-only
    STATUS      current
    DESCRIPTION
        "Represents the number of transmits that required more than
        one retry."
    ::= { hpnicfDot11APTxStatisEntry 4 }

hpnicfDot11RtsSuccessCnt OBJECT-TYPE
    SYNTAX      Counter32
    MAX-ACCESS  read-only
    STATUS      current
    DESCRIPTION
        "Represents the number of successful RTS (Request to send)
        transmission."
    ::= { hpnicfDot11APTxStatisEntry 5 }

hpnicfDot11RtsFailCnt OBJECT-TYPE
    SYNTAX      Counter32
    MAX-ACCESS  read-only
    STATUS      current
    DESCRIPTION
        "Represents the number of RTS transmission failures."
    ::= { hpnicfDot11APTxStatisEntry 6 }

hpnicfDot11AckFailCnt OBJECT-TYPE
    SYNTAX      Counter32
    MAX-ACCESS  read-only
    STATUS      current
    DESCRIPTION
        "Represents the number of acknowledgement failures."
    ::= { hpnicfDot11APTxStatisEntry 7 }

hpnicfDot11TxFrameCnt OBJECT-TYPE
    SYNTAX      Counter32
    MAX-ACCESS  read-only
    STATUS      current
    DESCRIPTION
        "Represents the total number of frames transmission."
    ::= { hpnicfDot11APTxStatisEntry 8 }

hpnicfDot11TxUcastFrameCnt OBJECT-TYPE
    SYNTAX      Counter32
    MAX-ACCESS  read-only
    STATUS      current
    DESCRIPTION
        "Represents the number of unicast frames transmission."
    ::= { hpnicfDot11APTxStatisEntry 9 }

hpnicfDot11TxBcastFrameCnt OBJECT-TYPE
    SYNTAX      Counter32
    MAX-ACCESS  read-only
    STATUS      current
    DESCRIPTION
        "Represents the number of broadcast frames transmission."
    ::= { hpnicfDot11APTxStatisEntry 10 }

hpnicfDot11TxMcastFrameCnt OBJECT-TYPE
    SYNTAX      Counter32
    MAX-ACCESS  read-only
    STATUS      current
    DESCRIPTION
        "Represents the number of multicast frames transmission."
    ::= { hpnicfDot11APTxStatisEntry 11 }

hpnicfDot11TxDiscardFrameCnt OBJECT-TYPE
    SYNTAX      Counter32
    MAX-ACCESS  read-only
    STATUS      current
    DESCRIPTION
        "Represents the number of frames discarded by AP."
    ::= { hpnicfDot11APTxStatisEntry 12 }

hpnicfDot11TxFrameBytes OBJECT-TYPE
    SYNTAX      Counter32
    MAX-ACCESS  read-only
    STATUS      current
    DESCRIPTION
        "Represents the total bytes of frames transmission."
    ::= { hpnicfDot11APTxStatisEntry 13 }

hpnicfDot11TxUcastFrameBytes OBJECT-TYPE
    SYNTAX      Counter32
    MAX-ACCESS  read-only
    STATUS      current
    DESCRIPTION
        "Represents the bytes of unicast frames transmission."
    ::= { hpnicfDot11APTxStatisEntry 14 }

hpnicfDot11TxBcastFrameBytes OBJECT-TYPE
    SYNTAX      Counter32
    MAX-ACCESS  read-only
    STATUS      current
    DESCRIPTION
        "Represents the bytes of broadcast frames transmission."
    ::= { hpnicfDot11APTxStatisEntry 15 }

hpnicfDot11TxMcastFrameBytes OBJECT-TYPE
    SYNTAX      Counter32
    MAX-ACCESS  read-only
    STATUS      current
    DESCRIPTION
        "Represents the bytes of multicast frames transmission."
    ::= { hpnicfDot11APTxStatisEntry 16 }

hpnicfDot11TxDiscardFrameBytes OBJECT-TYPE
    SYNTAX      Counter32
    MAX-ACCESS  read-only
    STATUS      current
    DESCRIPTION
        "Represents the bytes of multicast frames transmission."
    ::= { hpnicfDot11APTxStatisEntry 17 }

hpnicfDot11TxAuthenFrameCnt OBJECT-TYPE
    SYNTAX      Counter32
    MAX-ACCESS  read-only
    STATUS      current
    DESCRIPTION
        "Represents the number of authentication frame transmission."
    ::= { hpnicfDot11APTxStatisEntry 18 }

hpnicfDot11TxAssociateFrameCnt OBJECT-TYPE
    SYNTAX      Counter32
    MAX-ACCESS  read-only
    STATUS      current
    DESCRIPTION
        "Represents the number of associate frame transmission."
    ::= { hpnicfDot11APTxStatisEntry 19 }

hpnicfDot11TxFrameRetryRatio OBJECT-TYPE
    SYNTAX      Integer32
    UNITS       "onepercent"
    MAX-ACCESS  read-only
    STATUS      current
    DESCRIPTION
        "Represents the ratio of retry frame."
    ::= { hpnicfDot11APTxStatisEntry 20 }

hpnicfDot11TxDataFrameCnt OBJECT-TYPE
    SYNTAX      Counter32
    MAX-ACCESS  read-only
    STATUS      current
    DESCRIPTION
        "Represents the number of data frame transmission."
    ::= { hpnicfDot11APTxStatisEntry 21 }

hpnicfDot11TxDataFrameBytes OBJECT-TYPE
    SYNTAX      Counter32
    MAX-ACCESS  read-only
    STATUS      current
    DESCRIPTION
        "Represents the bytes of data frame transmission."
    ::= { hpnicfDot11APTxStatisEntry 22 }

hpnicfDot11TxMSDUCnt OBJECT-TYPE
    SYNTAX      Counter32
    MAX-ACCESS  read-only
    STATUS      current
    DESCRIPTION
        "Represents the total number of MSDU transmission."
    ::= { hpnicfDot11APTxStatisEntry 23 }

hpnicfDot11TxDiscardMSDUCnt OBJECT-TYPE
    SYNTAX      Counter32
    MAX-ACCESS  read-only
    STATUS      current
    DESCRIPTION
        "Represents the number of discarded MSDU transmission."
    ::= { hpnicfDot11APTxStatisEntry 24 }

hpnicfDot11RetryMSDUCnt OBJECT-TYPE
    SYNTAX      Counter32
    MAX-ACCESS  read-only
    STATUS      current
    DESCRIPTION
        "Represents the number of retransfer MSDU."
    ::= { hpnicfDot11APTxStatisEntry 25 }

hpnicfDot11TxPayloadBytes OBJECT-TYPE
    SYNTAX      Counter32
    MAX-ACCESS  read-only
    STATUS      current
    DESCRIPTION
        "Represents the payload bytes of data frames transmission."
    ::= { hpnicfDot11APTxStatisEntry 26 }

hpnicfDot11TxTrafficSpeed OBJECT-TYPE
    SYNTAX      Integer32
    UNITS       "byte/s"
    MAX-ACCESS  read-only
    STATUS      current
    DESCRIPTION
        "Represents the bytes of frames transmission per second."
    ::= { hpnicfDot11APTxStatisEntry 27 }

hpnicfDot11TxErrFrameRatio OBJECT-TYPE
    SYNTAX      Integer32
    UNITS       "onepercent"
    MAX-ACCESS  read-only
    STATUS      current
    DESCRIPTION
        "Represents the ratio of error frame."
    ::= { hpnicfDot11APTxStatisEntry 28 }

hpnicfDot11TxFrameRate OBJECT-TYPE
    SYNTAX      Integer32
    MAX-ACCESS  read-only
    STATUS      current
    DESCRIPTION
        "Represents the count of frames transmission per second."
    ::= { hpnicfDot11APTxStatisEntry 29 }

hpnicfDot11TxMgtFrameCnt OBJECT-TYPE
    SYNTAX      Counter32
    MAX-ACCESS  read-only
    STATUS      current
    DESCRIPTION
        "Represents the number of transmitted management frames."
    ::= { hpnicfDot11APTxStatisEntry 30 }

hpnicfDot11TxCtrlFrameCnt OBJECT-TYPE
    SYNTAX      Counter32
    MAX-ACCESS  read-only
    STATUS      current
    DESCRIPTION
        "Represents the number of transmission control frames."
    ::= { hpnicfDot11APTxStatisEntry 31 }
hpnicfDot11TxMACErrCnt OBJECT-TYPE
    SYNTAX      Counter32
    MAX-ACCESS  read-only
    STATUS      current
    DESCRIPTION
        "Represents the count of MAC error frame."
    ::= { hpnicfDot11APTxStatisEntry 32 }

hpnicfDot11TxErrFrameCnt OBJECT-TYPE
    SYNTAX      Counter32
    MAX-ACCESS  read-only
    STATUS      current
    DESCRIPTION
        "Represents the count of error frame."
    ::= { hpnicfDot11APTxStatisEntry 33 }

hpnicfDot11TxUcastDataFrameCnt OBJECT-TYPE
    SYNTAX      Counter64
    MAX-ACCESS  read-only
    STATUS      current
    DESCRIPTION
        "Represents the number of unicast data frames transmission."
    ::= { hpnicfDot11APTxStatisEntry 34 }

hpnicfDot11TxNUcastDataFrameCnt OBJECT-TYPE
    SYNTAX      Counter64
    MAX-ACCESS  read-only
    STATUS      current
    DESCRIPTION
        "Represents the number of non-unicast data frames transmission."
    ::= { hpnicfDot11APTxStatisEntry 35 }

-- *****************************************************************************
-- *  End of hpnicfDot11APTxStatisTable Definition
-- *****************************************************************************

-- *****************************************************************************
-- *  hpnicfDot11APAssocStatisTable Definition
-- *****************************************************************************
hpnicfDot11APAssocStatisTable OBJECT-TYPE
    SYNTAX      SEQUENCE OF HpnicfDot11APAssocStatisEntry
    MAX-ACCESS  not-accessible
    STATUS      current
    DESCRIPTION
        "The table will provide the station association statistic for AP."
    ::= { hpnicfDot11APStatisGroup 3 }

hpnicfDot11APAssocStatisEntry OBJECT-TYPE
    SYNTAX      HpnicfDot11APAssocStatisEntry
    MAX-ACCESS  not-accessible
    STATUS      current
    DESCRIPTION
        "Each entry of the table will provide the statistic data of station
        association for AP."
    INDEX
        {
            hpnicfDot11CurAPID
        }
    ::= { hpnicfDot11APAssocStatisTable 1 }

HpnicfDot11APAssocStatisEntry ::= SEQUENCE
    {
        hpnicfDot11ApStationAssocSum          Counter32,
        hpnicfDot11ApStationAssocFailSum      Counter32,
        hpnicfDot11ApStationReassocSum        Counter32,
        hpnicfDot11ApStationAssocRejectSum    Counter32,
        hpnicfDot11ApStationExDeAuthenSum     Counter32,
        hpnicfDot11ApStationCurAssocSum       Integer32,
        hpnicfDot11ApStaCurAuthSuccSum        Integer32,
        hpnicfDot11AllStationUpSumTime        Counter32,
        hpnicfDot11ApStationAssocReqSum       Counter32,
        hpnicfDot11AllStationUpSumTimeTicks   TimeTicks,
        hpnicfDot11ApStationReassocReqSum     Counter32,
        hpnicfDot11ApStationReassocFailSum    Counter32
    }

hpnicfDot11ApStationAssocSum OBJECT-TYPE
    SYNTAX      Counter32
    MAX-ACCESS  read-only
    STATUS      current
    DESCRIPTION
        "Represents the total number of station association
        with this AP."
    ::= { hpnicfDot11APAssocStatisEntry 1 }

hpnicfDot11ApStationAssocFailSum OBJECT-TYPE
    SYNTAX      Counter32
    MAX-ACCESS  read-only
    STATUS      current
    DESCRIPTION
        "Represents the total number of station
        association failure with this AP."
    ::= { hpnicfDot11APAssocStatisEntry 2 }

hpnicfDot11ApStationReassocSum OBJECT-TYPE
    SYNTAX      Counter32
    MAX-ACCESS  read-only
    STATUS      current
    DESCRIPTION
        "Represents the total number of station reassociation with this AP."
    ::= { hpnicfDot11APAssocStatisEntry 3 }

hpnicfDot11ApStationAssocRejectSum OBJECT-TYPE
    SYNTAX      Counter32
    MAX-ACCESS  read-only
    STATUS      current
    DESCRIPTION
        "Represents the total number of station association rejected
        on account of resource limit with this AP."
    ::= { hpnicfDot11APAssocStatisEntry 4 }

hpnicfDot11ApStationExDeAuthenSum OBJECT-TYPE
    SYNTAX      Counter32
    MAX-ACCESS  read-only
    STATUS      current
    DESCRIPTION
        "Represents the total number of exceptional station deauthentication
        (Without sending a deauthentication to AP) with this AP."
    ::= { hpnicfDot11APAssocStatisEntry 5 }

hpnicfDot11ApStationCurAssocSum OBJECT-TYPE
    SYNTAX      Integer32
    MAX-ACCESS  read-only
    STATUS      current
    DESCRIPTION
        "Represents the total number of current associated stations
        with this AP."
    ::= { hpnicfDot11APAssocStatisEntry 6 }

hpnicfDot11ApStaCurAuthSuccSum OBJECT-TYPE
    SYNTAX      Integer32
    MAX-ACCESS  read-only
    STATUS      current
    DESCRIPTION
        "Represents the successful number of station authentication
        with this AP."
    ::= { hpnicfDot11APAssocStatisEntry 7 }

hpnicfDot11AllStationUpSumTime OBJECT-TYPE
    SYNTAX      Counter32
    UNITS       "minute"
    MAX-ACCESS  read-only
    STATUS      current
    DESCRIPTION
        "Represents the sum of duration of all stations which associate with
         this AP."
    ::= { hpnicfDot11APAssocStatisEntry 8 }

hpnicfDot11ApStationAssocReqSum OBJECT-TYPE
    SYNTAX      Counter32
    MAX-ACCESS  read-only
    STATUS      current
    DESCRIPTION
        "Represents the number of station association request with this AP."
    ::= { hpnicfDot11APAssocStatisEntry 9 }

hpnicfDot11AllStationUpSumTimeTicks OBJECT-TYPE
    SYNTAX      TimeTicks
    MAX-ACCESS  read-only
    STATUS      current
    DESCRIPTION
        "Represents the sum of duration of all stations which associate with
         this AP."
    ::= { hpnicfDot11APAssocStatisEntry 10 }

hpnicfDot11ApStationReassocReqSum OBJECT-TYPE
    SYNTAX      Counter32
    MAX-ACCESS  read-only
    STATUS      current
    DESCRIPTION
        "Represents the total number of station reassociation request
        with this AP."
    ::= { hpnicfDot11APAssocStatisEntry 11 }

hpnicfDot11ApStationReassocFailSum OBJECT-TYPE
    SYNTAX      Counter32
    MAX-ACCESS  read-only
    STATUS      current
    DESCRIPTION
        "Represents the total number of station reassociation failure
        with this AP."
    ::= { hpnicfDot11APAssocStatisEntry 12 }
-- *****************************************************************************
-- *  End of hpnicfDot11APAssocStatisTable Definition
-- *****************************************************************************

-- *****************************************************************************
-- *  hpnicfDot11BSSRxStatisTable Definition
-- *****************************************************************************
hpnicfDot11BSSRxStatisTable OBJECT-TYPE
    SYNTAX      SEQUENCE OF HpnicfDot11BSSRxStatisEntry
    MAX-ACCESS  not-accessible
    STATUS      current
    DESCRIPTION
        "The table will provide the reception statistic for a
        specific BSS on a radio."
    ::= { hpnicfDot11APStatisGroup 4 }

hpnicfDot11BSSRxStatisEntry OBJECT-TYPE
    SYNTAX      HpnicfDot11BSSRxStatisEntry
    MAX-ACCESS  not-accessible
    STATUS      current
    DESCRIPTION
        "Each entry of the table will provide the statistic data for
        each BSS on a specific radio."
    INDEX
        {
            hpnicfDot11CurAPID,
            hpnicfDot11RadioID,
            hpnicfDot11WlanID
        }
    ::= { hpnicfDot11BSSRxStatisTable 1 }

HpnicfDot11BSSRxStatisEntry ::= SEQUENCE
    {
        hpnicfDot11BSSRxFrameCnt             Counter32,
        hpnicfDot11BSSRxFrameBytes           Counter32,
        hpnicfDot11BSSRxDataFrameCnt         Counter32,
        hpnicfDot11BSSRxDataFrameBytes       Counter32,
        hpnicfDot11BSSRxAssociateFrameCnt    Counter32,
        hpnicfDot11BSSRxFrameErrorRatio      Integer32,
        hpnicfDot11BSSRxPayloadBytes         Counter32,
        hpnicfDot11BSSRxUniFrameCnt          Counter32,
        hpnicfDot11BSSRxNonUniFrameCnt       Integer32,
        hpnicfDot11BSSRxAuthenFrameCnt       Counter32
    }

hpnicfDot11BSSRxFrameCnt OBJECT-TYPE
    SYNTAX      Counter32
    MAX-ACCESS  read-only
    STATUS      current
    DESCRIPTION
        "Represents the number of frames reception with this BSS."
    ::= { hpnicfDot11BSSRxStatisEntry 1 }

hpnicfDot11BSSRxFrameBytes OBJECT-TYPE
    SYNTAX      Counter32
    MAX-ACCESS  read-only
    STATUS      current
    DESCRIPTION
        "Represents the bytes of frames reception with this BSS."
    ::= { hpnicfDot11BSSRxStatisEntry 2 }

hpnicfDot11BSSRxDataFrameCnt OBJECT-TYPE
    SYNTAX      Counter32
    MAX-ACCESS  read-only
    STATUS      current
    DESCRIPTION
        "Represents the number of data frames reception with this BSS."
    ::= { hpnicfDot11BSSRxStatisEntry 3 }

hpnicfDot11BSSRxDataFrameBytes OBJECT-TYPE
    SYNTAX      Counter32
    MAX-ACCESS  read-only
    STATUS      current
    DESCRIPTION
        "Represents the bytes of data frames reception with this BSS."
    ::= { hpnicfDot11BSSRxStatisEntry 4 }

hpnicfDot11BSSRxAssociateFrameCnt OBJECT-TYPE
    SYNTAX      Counter32
    MAX-ACCESS  read-only
    STATUS      current
    DESCRIPTION
        "Represents the number of associate frames reception with this BSS."
    ::= { hpnicfDot11BSSRxStatisEntry 5 }

hpnicfDot11BSSRxFrameErrorRatio OBJECT-TYPE
    SYNTAX      Integer32
    UNITS       "percent"
    MAX-ACCESS  read-only
    STATUS      current
    DESCRIPTION
        "Represents the ratio of error frames reception with this BSS."
    ::= { hpnicfDot11BSSRxStatisEntry 6 }

hpnicfDot11BSSRxPayloadBytes OBJECT-TYPE
    SYNTAX      Counter32
    MAX-ACCESS  read-only
    STATUS      current
    DESCRIPTION
        "Represents the payload bytes of data frames reception with this BSS."
    ::= { hpnicfDot11BSSRxStatisEntry 7 }

hpnicfDot11BSSRxUniFrameCnt OBJECT-TYPE
    SYNTAX      Counter32
    MAX-ACCESS  read-only
    STATUS      current
    DESCRIPTION
        "Represents the count of unicast frames received."
    ::= { hpnicfDot11BSSRxStatisEntry 8 }

hpnicfDot11BSSRxNonUniFrameCnt  OBJECT-TYPE
    SYNTAX      Integer32
    MAX-ACCESS  read-only
    STATUS      current
    DESCRIPTION
        "Represents the count of non-unicast frames received."
    ::= { hpnicfDot11BSSRxStatisEntry 9 }

hpnicfDot11BSSRxAuthenFrameCnt OBJECT-TYPE
    SYNTAX      Counter32
    MAX-ACCESS  read-only
    STATUS      current
    DESCRIPTION
        "Represents the count of authentication frames received."
    ::= { hpnicfDot11BSSRxStatisEntry 10 }

-- *****************************************************************************
-- *  End of hpnicfDot11BSSRxStatisTable Definition
-- *****************************************************************************

-- *****************************************************************************
-- *  hpnicfDot11BSSTxStatisTable Definition
-- *****************************************************************************
hpnicfDot11BSSTxStatisTable OBJECT-TYPE
    SYNTAX      SEQUENCE OF HpnicfDot11BSSTxStatisEntry
    MAX-ACCESS  not-accessible
    STATUS      current
    DESCRIPTION
        "The table will provide the transmission statistic for a
        specific BSS on a radio."
    ::= { hpnicfDot11APStatisGroup 5 }

hpnicfDot11BSSTxStatisEntry OBJECT-TYPE
    SYNTAX      HpnicfDot11BSSTxStatisEntry
    MAX-ACCESS  not-accessible
    STATUS      current
    DESCRIPTION
        "Each entry of the table will provide the statistic data for
        each BSS on a specific radio."
    INDEX
        {
            hpnicfDot11CurAPID,
            hpnicfDot11RadioID,
            hpnicfDot11WlanID
        }
    ::= { hpnicfDot11BSSTxStatisTable 1 }

HpnicfDot11BSSTxStatisEntry ::= SEQUENCE
    {
        hpnicfDot11BSSTxFrameCnt             Counter32,
        hpnicfDot11BSSTxFrameBytes           Counter32,
        hpnicfDot11BSSTxDataFrameCnt         Counter32,
        hpnicfDot11BSSTxDataFrameBytes       Counter32,
        hpnicfDot11BSSTxAssociateFrameCnt    Counter32,
        hpnicfDot11BSSTxPayloadBytes         Counter32,
        hpnicfDot11BSSTxRetryCnt             Counter32,
        hpnicfDot11BSSTxUniFrameCnt          Counter32,
        hpnicfDot11BSSTxNonUniFrameCnt       Integer32,
        hpnicfDot11BSSTxAuthenFrameCnt       Counter32
    }

hpnicfDot11BSSTxFrameCnt OBJECT-TYPE
    SYNTAX      Counter32
    MAX-ACCESS  read-only
    STATUS      current
    DESCRIPTION
        "Represents the total number of frames transmission with this BSS."
    ::= { hpnicfDot11BSSTxStatisEntry 1 }

hpnicfDot11BSSTxFrameBytes OBJECT-TYPE
    SYNTAX      Counter32
    MAX-ACCESS  read-only
    STATUS      current
    DESCRIPTION
        "Represents the total number of bytes transmission with this BSS."
    ::= { hpnicfDot11BSSTxStatisEntry 2 }

hpnicfDot11BSSTxDataFrameCnt OBJECT-TYPE
    SYNTAX      Counter32
    MAX-ACCESS  read-only
    STATUS      current
    DESCRIPTION
        "Represents the number of data frame transmission with this BSS."
    ::= { hpnicfDot11BSSTxStatisEntry 3 }

hpnicfDot11BSSTxDataFrameBytes OBJECT-TYPE
    SYNTAX      Counter32
    MAX-ACCESS  read-only
    STATUS      current
    DESCRIPTION
        "Represents the bytes of data frame transmission with this BSS."
    ::= { hpnicfDot11BSSTxStatisEntry 4 }

hpnicfDot11BSSTxAssociateFrameCnt OBJECT-TYPE
    SYNTAX      Counter32
    MAX-ACCESS  read-only
    STATUS      current
    DESCRIPTION
        "Represents the number of associate frame transmission with this BSS."
    ::= { hpnicfDot11BSSTxStatisEntry 5 }

hpnicfDot11BSSTxPayloadBytes OBJECT-TYPE
    SYNTAX      Counter32
    MAX-ACCESS  read-only
    STATUS      current
    DESCRIPTION
        "Represents the payload bytes of data frame transmission with this BSS."
    ::= { hpnicfDot11BSSTxStatisEntry 6 }

hpnicfDot11BSSTxRetryCnt   OBJECT-TYPE
    SYNTAX      Counter32
    MAX-ACCESS  read-only
    STATUS      current
    DESCRIPTION
        "Represents the count of bytes retransmitted with this BSS."
    ::= { hpnicfDot11BSSTxStatisEntry 7 }

hpnicfDot11BSSTxUniFrameCnt OBJECT-TYPE
    SYNTAX      Counter32
    MAX-ACCESS  read-only
    STATUS      current
    DESCRIPTION
        "Represents the count of unicast frames transmission with this BSS."
    ::= { hpnicfDot11BSSTxStatisEntry 8 }

hpnicfDot11BSSTxNonUniFrameCnt OBJECT-TYPE
    SYNTAX      Integer32
    MAX-ACCESS  read-only
    STATUS      current
    DESCRIPTION
        "Represents the number of non-unicast frames transmission with this BSS."
    ::= { hpnicfDot11BSSTxStatisEntry 9 }

hpnicfDot11BSSTxAuthenFrameCnt OBJECT-TYPE
    SYNTAX      Counter32
    MAX-ACCESS  read-only
    STATUS      current
    DESCRIPTION
        "Represents the count of authentication frames transmission with this BSS."
    ::= { hpnicfDot11BSSTxStatisEntry 10 }

-- *****************************************************************************
-- *  End of hpnicfDot11BSSTxStatisTable Definition
-- *****************************************************************************

-- *****************************************************************************
-- *  hpnicfDot11BSSAssocStatisTable Definition
-- *****************************************************************************
hpnicfDot11BSSAssocStatisTable OBJECT-TYPE
    SYNTAX      SEQUENCE OF HpnicfDot11BSSAssocStatisEntry
    MAX-ACCESS  not-accessible
    STATUS      current
    DESCRIPTION
        "The table will provide the station association statistic for BSS."
    ::= { hpnicfDot11APStatisGroup 6 }

hpnicfDot11BSSAssocStatisEntry OBJECT-TYPE
    SYNTAX      HpnicfDot11BSSAssocStatisEntry
    MAX-ACCESS  not-accessible
    STATUS      current
    DESCRIPTION
        "Each entry of the table will provide the statistic data of station
        association for BSS."
    INDEX
        {
            hpnicfDot11CurAPID,
            hpnicfDot11RadioID,
            hpnicfDot11WlanID
        }
    ::= { hpnicfDot11BSSAssocStatisTable 1 }

HpnicfDot11BSSAssocStatisEntry ::= SEQUENCE
    {
        hpnicfDot11BSSStationAssocSum          Counter32,
        hpnicfDot11BSSStationAssocFailSum      Counter32,
        hpnicfDot11BSSStationReassocSum        Counter32,
        hpnicfDot11BSSStationAssocRejectSum    Counter32,
        hpnicfDot11BSSStationExDeAssocSum      Counter32,
        hpnicfDot11BSSStationCurAssocSum       Integer32,
        hpnicfDot11BSSStationAssocReqSum       Counter32,
        hpnicfDot11BSSStationCurAuthSum        Integer32
    }

hpnicfDot11BSSStationAssocSum OBJECT-TYPE
    SYNTAX      Counter32
    MAX-ACCESS  read-only
    STATUS      current
    DESCRIPTION
        "Represents the total number of station association
        with this BSS."
    ::= { hpnicfDot11BSSAssocStatisEntry 1 }

hpnicfDot11BSSStationAssocFailSum OBJECT-TYPE
    SYNTAX      Counter32
    MAX-ACCESS  read-only
    STATUS      current
    DESCRIPTION
        "Represents the total number of station
        association failure with this BSS."
    ::= { hpnicfDot11BSSAssocStatisEntry 2 }

hpnicfDot11BSSStationReassocSum OBJECT-TYPE
    SYNTAX      Counter32
    MAX-ACCESS  read-only
    STATUS      current
    DESCRIPTION
        "Represents the total number of station reassociation
        with this BSS."
    ::= { hpnicfDot11BSSAssocStatisEntry 3 }

hpnicfDot11BSSStationAssocRejectSum OBJECT-TYPE
    SYNTAX      Counter32
    MAX-ACCESS  read-only
    STATUS      current
    DESCRIPTION
        "Represents the total number of station association rejected
        on account of resource limit with this BSS."
    ::= { hpnicfDot11BSSAssocStatisEntry 4 }

hpnicfDot11BSSStationExDeAssocSum OBJECT-TYPE
    SYNTAX      Counter32
    MAX-ACCESS  read-only
    STATUS      current
    DESCRIPTION
        "Represents the total number of exceptional station deauthentication
        (Without sending a deauthentication to AP) with this BSS."
    ::= { hpnicfDot11BSSAssocStatisEntry 5 }

hpnicfDot11BSSStationCurAssocSum OBJECT-TYPE
    SYNTAX      Integer32
    MAX-ACCESS  read-only
    STATUS      current
    DESCRIPTION
        "Represents the total number of current associated stations
        with this BSS."
    ::= { hpnicfDot11BSSAssocStatisEntry 6 }

hpnicfDot11BSSStationAssocReqSum OBJECT-TYPE
    SYNTAX      Counter32
    MAX-ACCESS  read-only
    STATUS      current
    DESCRIPTION
        "Represents the total number of station association request with
         this BSS."
    ::= { hpnicfDot11BSSAssocStatisEntry 7 }

hpnicfDot11BSSStationCurAuthSum OBJECT-TYPE
    SYNTAX      Integer32
    MAX-ACCESS  read-only
    STATUS      current
    DESCRIPTION
        "Represents the total number of current associated stations which have
        passed portal or 1x authentication with this BSS."
    ::= { hpnicfDot11BSSAssocStatisEntry 8 }

-- *****************************************************************************
-- *  End of hpnicfDot11BSSAssocStatisTable Definition
-- *****************************************************************************

-- *****************************************************************************
-- *  hpnicfDot11APLinkStatisTable Definition
-- *****************************************************************************
hpnicfDot11APLinkStatisTable OBJECT-TYPE
    SYNTAX      SEQUENCE OF HpnicfDot11APLinkStatisEntry
    MAX-ACCESS  not-accessible
    STATUS      current
    DESCRIPTION
        "The table will provide the link statistic for AP."
    ::= { hpnicfDot11APStatisGroup 7 }

hpnicfDot11APLinkStatisEntry OBJECT-TYPE
    SYNTAX      HpnicfDot11APLinkStatisEntry
    MAX-ACCESS  not-accessible
    STATUS      current
    DESCRIPTION
        "Each entry provides the link statistic of the AP."
    INDEX
        {
            hpnicfDot11CurAPID
        }
    ::= { hpnicfDot11APLinkStatisTable 1 }

HpnicfDot11APLinkStatisEntry ::= SEQUENCE
    {
        hpnicfDot11UpLinkUpDownTimes          Counter32,
        hpnicfDot11DownLinkUpDownTimes        Counter32
    }

hpnicfDot11UpLinkUpDownTimes OBJECT-TYPE
    SYNTAX      Counter32
    MAX-ACCESS  read-only
    STATUS      current
    DESCRIPTION
        "Represents up/down times of uplink interface of the AP."
    ::= { hpnicfDot11APLinkStatisEntry 1 }

hpnicfDot11DownLinkUpDownTimes OBJECT-TYPE
    SYNTAX      Counter32
    MAX-ACCESS  read-only
    STATUS      current
    DESCRIPTION
        "Represents up/down times of downlink interface of the AP."
    ::= { hpnicfDot11APLinkStatisEntry 2 }
-- *****************************************************************************
-- *  End of hpnicfDot11APLinkStatisTable Definition
-- *****************************************************************************

-- *****************************************************************************
-- *  hpnicfDot11RadioAssocStatisTable Definition
-- *****************************************************************************
hpnicfDot11RadioAssocStatisTable OBJECT-TYPE
    SYNTAX      SEQUENCE OF HpnicfDot11RadioAssocStatisEntry
    MAX-ACCESS  not-accessible
    STATUS      current
    DESCRIPTION
        "The table will provide the station association statistic for radio."
    ::= { hpnicfDot11APStatisGroup 8 }

hpnicfDot11RadioAssocStatisEntry OBJECT-TYPE
    SYNTAX      HpnicfDot11RadioAssocStatisEntry
    MAX-ACCESS  not-accessible
    STATUS      current
    DESCRIPTION
        "Each entry of the table will provide the statistic data of station
        association for radio."
    INDEX
        {
            hpnicfDot11CurAPID,
            hpnicfDot11RadioID
        }
    ::= { hpnicfDot11RadioAssocStatisTable 1 }

HpnicfDot11RadioAssocStatisEntry ::= SEQUENCE
    {
        hpnicfDot11RadioStaAssocSum          Counter32,
        hpnicfDot11RadioStaAssocFailSum      Counter32,
        hpnicfDot11RadioStaReassocSum        Counter32,
        hpnicfDot11RadioStaAssocRejectSum    Counter32,
        hpnicfDot11RadioStaExDeAssocSum      Counter32,
        hpnicfDot11RadioStaCurAssocSum       Integer32
    }

hpnicfDot11RadioStaAssocSum OBJECT-TYPE
    SYNTAX      Counter32
    MAX-ACCESS  read-only
    STATUS      current
    DESCRIPTION
        "Represents the total number of station association
        with this radio."
    ::= { hpnicfDot11RadioAssocStatisEntry 1 }

hpnicfDot11RadioStaAssocFailSum OBJECT-TYPE
    SYNTAX      Counter32
    MAX-ACCESS  read-only
    STATUS      current
    DESCRIPTION
        "Represents the total number of station
        association failure with this radio."
    ::= { hpnicfDot11RadioAssocStatisEntry 2 }

hpnicfDot11RadioStaReassocSum OBJECT-TYPE
    SYNTAX      Counter32
    MAX-ACCESS  read-only
    STATUS      current
    DESCRIPTION
        "Represents the total number of station re-association
        with this radio."
    ::= { hpnicfDot11RadioAssocStatisEntry 3 }

hpnicfDot11RadioStaAssocRejectSum OBJECT-TYPE
    SYNTAX      Counter32
    MAX-ACCESS  read-only
    STATUS      current
    DESCRIPTION
        "Represents the total number of station association rejected
        on account of resource limit with this radio."
    ::= { hpnicfDot11RadioAssocStatisEntry 4 }

hpnicfDot11RadioStaExDeAssocSum OBJECT-TYPE
    SYNTAX      Counter32
    MAX-ACCESS  read-only
    STATUS      current
    DESCRIPTION
        "Represents the total number of exceptional station de-authentication
        (Without sending a de-authentication to AP) with this radio."
    ::= { hpnicfDot11RadioAssocStatisEntry 5 }

hpnicfDot11RadioStaCurAssocSum OBJECT-TYPE
    SYNTAX      Integer32
    MAX-ACCESS  read-only
    STATUS      current
    DESCRIPTION
        "Represents the total number of current associated stations
        with this radio."
    ::= { hpnicfDot11RadioAssocStatisEntry 6 }
-- *****************************************************************************
-- *  End of hpnicfDot11RadioAssocStatisTable Definition
-- *****************************************************************************

-- *****************************************************************************
-- *  hpnicfDot11RadioMngFrameStatisTable Definition
-- *****************************************************************************
hpnicfDot11RadioMngFrameStatisTable OBJECT-TYPE
    SYNTAX      SEQUENCE OF HpnicfDot11RadioMngFrameStatisEntry
    MAX-ACCESS  not-accessible
    STATUS      current
    DESCRIPTION
        "The table will provide the management frame statistic for this radio."
    ::= { hpnicfDot11APStatisGroup 9 }

hpnicfDot11RadioMngFrameStatisEntry OBJECT-TYPE
    SYNTAX      HpnicfDot11RadioMngFrameStatisEntry
    MAX-ACCESS  not-accessible
    STATUS      current
    DESCRIPTION
        "Each entry of the table will provide the management
        frame statistic for this radio."
    INDEX
        {
            hpnicfDot11RadioStatisIndex,
            hpnicfDot11MngFrameType
        }
    ::= { hpnicfDot11RadioMngFrameStatisTable 1 }

HpnicfDot11RadioMngFrameStatisEntry ::= SEQUENCE
    {
        hpnicfDot11RadioStatisIndex            HpnicfDot11RadioElementIndex,
        hpnicfDot11MngFrameType                INTEGER,
        hpnicfDot11MngFrameCnt                 Counter32
    }

hpnicfDot11RadioStatisIndex OBJECT-TYPE
    SYNTAX      HpnicfDot11RadioElementIndex
    MAX-ACCESS  not-accessible
    STATUS      current
    DESCRIPTION
        "Represents index of radio."
    ::= { hpnicfDot11RadioMngFrameStatisEntry 1 }

hpnicfDot11MngFrameType   OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { hpnicfDot11RadioMngFrameStatisEntry 2 }

hpnicfDot11MngFrameCnt OBJECT-TYPE
    SYNTAX      Counter32
    MAX-ACCESS  read-only
    STATUS      current
    DESCRIPTION
        "Represents the total number of each type for management frame on this
        radio."
    ::= { hpnicfDot11RadioMngFrameStatisEntry 3 }

-- *****************************************************************************
-- *  End of hpnicfDot11RadioMngFrameStatisTable Definition
-- *****************************************************************************

-- *****************************************************************************
-- *  hpnicfDot11APAuthFailStatisTable Definition
-- *****************************************************************************
hpnicfDot11APAuthFailStatisTable OBJECT-TYPE
    SYNTAX      SEQUENCE OF HpnicfDot11APAuthFailStatisEntry
    MAX-ACCESS  not-accessible
    STATUS      current
    DESCRIPTION
        "The table will provide the authentication failure statistic for this
         AP."
    ::= { hpnicfDot11APStatisGroup 10 }

hpnicfDot11APAuthFailStatisEntry OBJECT-TYPE
    SYNTAX      HpnicfDot11APAuthFailStatisEntry
    MAX-ACCESS  not-accessible
    STATUS      current
    DESCRIPTION
        "Each entry of the table will provide the authentication failure
         statistic for this AP."
    INDEX
        {
            hpnicfDot11CurAPID,
            hpnicfDot11APAuthFailStatisType
        }
    ::= { hpnicfDot11APAuthFailStatisTable 1 }

HpnicfDot11APAuthFailStatisEntry ::= SEQUENCE
    {
        hpnicfDot11APAuthFailStatisType                 INTEGER,
        hpnicfDot11APAuthFailStatisCnt                  Counter32
    }

hpnicfDot11APAuthFailStatisType OBJECT-TYPE
    SYNTAX      INTEGER
        {
            invalidation(1),
            overtime(2),
            rejected(3),
            other(4)
        }
    MAX-ACCESS  not-accessible
    STATUS      current
    DESCRIPTION
        "Represents the type of authentication
        failure with this AP."
    ::= { hpnicfDot11APAuthFailStatisEntry 1 }

hpnicfDot11APAuthFailStatisCnt   OBJECT-TYPE
    SYNTAX      Counter32
    MAX-ACCESS  read-only
    STATUS      current
    DESCRIPTION
        "Represents the total number of each type for authentication
        failure on this AP."
    ::= { hpnicfDot11APAuthFailStatisEntry 2 }

-- *****************************************************************************
-- *  End of hpnicfDot11APAuthFailStatisTable Definition
-- *****************************************************************************

-- *****************************************************************************
-- *  hpnicfDot11APAssocFailStatisTable Definition
-- *****************************************************************************
hpnicfDot11APAssocFailStatisTable OBJECT-TYPE
    SYNTAX      SEQUENCE OF HpnicfDot11APAssocFailStatisEntry
    MAX-ACCESS  not-accessible
    STATUS      current
    DESCRIPTION
        "The table will provide the association failure statistic for
        this AP."
    ::= { hpnicfDot11APStatisGroup 11 }

hpnicfDot11APAssocFailStatisEntry OBJECT-TYPE
    SYNTAX      HpnicfDot11APAssocFailStatisEntry
    MAX-ACCESS  not-accessible
    STATUS      current
    DESCRIPTION
        "Each entry of the table will provide the association failure statistic
         for this AP."
    INDEX
        {
            hpnicfDot11CurAPID,
            hpnicfDot11APAssocFailStatisType
        }
    ::= { hpnicfDot11APAssocFailStatisTable 1 }

HpnicfDot11APAssocFailStatisEntry ::= SEQUENCE
    {
        hpnicfDot11APAssocFailStatisType                 INTEGER,
        hpnicfDot11APAssocFailStatisCnt                  Counter32
    }

hpnicfDot11APAssocFailStatisType OBJECT-TYPE
    SYNTAX      INTEGER
        {
            invalidation(1),
            overtime(2),
            rejected(3),
            other(4)
        }
    MAX-ACCESS  not-accessible
    STATUS      current
    DESCRIPTION
        "Represents the type of association failure
        with this AP."
    ::= { hpnicfDot11APAssocFailStatisEntry 1 }

hpnicfDot11APAssocFailStatisCnt   OBJECT-TYPE
    SYNTAX      Counter32
    MAX-ACCESS  read-only
    STATUS      current
    DESCRIPTION
        "Represents the total number of each type for
        association failure on this AP."
    ::= { hpnicfDot11APAssocFailStatisEntry 2 }

-- *****************************************************************************
-- *  End of hpnicfDot11APAssocFailStatisTable Definition
-- *****************************************************************************

-- *****************************************************************************
-- *  hpnicfDot11APReassocStatisTable Definition
-- *****************************************************************************
hpnicfDot11APReassocStatisTable OBJECT-TYPE
    SYNTAX      SEQUENCE OF HpnicfDot11APReassocStatisEntry
    MAX-ACCESS  not-accessible
    STATUS      current
    DESCRIPTION
        "The table will provide the re-association statistic for this AP."
    ::= { hpnicfDot11APStatisGroup 12 }

hpnicfDot11APReassocStatisEntry OBJECT-TYPE
    SYNTAX      HpnicfDot11APReassocStatisEntry
    MAX-ACCESS  not-accessible
    STATUS      current
    DESCRIPTION
        "Each entry of the table will provide the re-association statistic
        for this AP."
    INDEX
        {
            hpnicfDot11CurAPID,
            hpnicfDot11APReassocStatisType
        }
    ::= { hpnicfDot11APReassocStatisTable 1 }

HpnicfDot11APReassocStatisEntry ::= SEQUENCE
    {
        hpnicfDot11APReassocStatisType                 INTEGER,
        hpnicfDot11APReassocStatisCnt                  Counter32
    }

hpnicfDot11APReassocStatisType OBJECT-TYPE
    SYNTAX      INTEGER
        {
            total(1),
            success(2),
            invalidation(3),
            overtime(4),
            rejected(5),
            other(6)
        }
    MAX-ACCESS  not-accessible
    STATUS      current
    DESCRIPTION
        "Represents the type of re-association with this AP."
    ::= { hpnicfDot11APReassocStatisEntry 1 }

hpnicfDot11APReassocStatisCnt   OBJECT-TYPE
    SYNTAX      Counter32
    MAX-ACCESS  read-only
    STATUS      current
    DESCRIPTION
        "Represents the total number of each type for re-association with
        this AP."
    ::= { hpnicfDot11APReassocStatisEntry 2 }

-- *****************************************************************************
-- *  End of hpnicfDot11APReassocStatisTable Definition
-- *****************************************************************************

-- *****************************************************************************
-- *  hpnicfDot11APUserAuthStatisTable Definition
-- *****************************************************************************
hpnicfDot11APUserAuthStatisTable OBJECT-TYPE
    SYNTAX      SEQUENCE OF HpnicfDot11APUserAuthStatisEntry
    MAX-ACCESS  not-accessible
    STATUS      current
    DESCRIPTION
        "The table will provide the user authentication statistic for this AP."
    ::= { hpnicfDot11APStatisGroup 13 }

hpnicfDot11APUserAuthStatisEntry OBJECT-TYPE
    SYNTAX      HpnicfDot11APUserAuthStatisEntry
    MAX-ACCESS  not-accessible
    STATUS      current
    DESCRIPTION
        "Each entry of the table will provide the user authentication statistic
        for this AP."
    INDEX
        {
            hpnicfDot11CurAPID,
            hpnicfDot11UserAuthStatisType
        }
    ::= { hpnicfDot11APUserAuthStatisTable 1 }

HpnicfDot11APUserAuthStatisEntry ::= SEQUENCE
    {
        hpnicfDot11UserAuthStatisType                 INTEGER,
        hpnicfDot11UserAuthStatisCnt                  Counter32
    }

hpnicfDot11UserAuthStatisType OBJECT-TYPE
    SYNTAX      INTEGER
        {
            total(1),
            success(2),
            keyError(3),
            invalidation(4),
            overtime(5),
            rejected(6),
            other(7)
        }
    MAX-ACCESS  not-accessible
    STATUS      current
    DESCRIPTION
        "Represents the type of user authentication with this AP."
    ::= { hpnicfDot11APUserAuthStatisEntry 1 }

hpnicfDot11UserAuthStatisCnt   OBJECT-TYPE
    SYNTAX      Counter32
    MAX-ACCESS  read-only
    STATUS      current
    DESCRIPTION
        "Represents the total number of each type for user authentication with
        this AP."
    ::= { hpnicfDot11APUserAuthStatisEntry 2 }

-- *****************************************************************************
-- *  End of hpnicfDot11APUserAuthStatisTable Definition
-- *****************************************************************************

-- *****************************************************************************
-- *  hpnicfDot11APDeauthStatisTable Definition
-- *****************************************************************************
hpnicfDot11APDeauthStatisTable OBJECT-TYPE
    SYNTAX      SEQUENCE OF HpnicfDot11APDeauthStatisEntry
    MAX-ACCESS  not-accessible
    STATUS      current
    DESCRIPTION
        "The table will provide the de-authentication statistic for this AP."
    ::= { hpnicfDot11APStatisGroup 14 }

hpnicfDot11APDeauthStatisEntry OBJECT-TYPE
    SYNTAX      HpnicfDot11APDeauthStatisEntry
    MAX-ACCESS  not-accessible
    STATUS      current
    DESCRIPTION
        "Each entry of the table will provide the de-authentication statistic
         for this AP."
    INDEX
        {
            hpnicfDot11CurAPID,
            hpnicfDot11APDeauthStatisType
        }
    ::= { hpnicfDot11APDeauthStatisTable 1 }

HpnicfDot11APDeauthStatisEntry ::= SEQUENCE
    {
        hpnicfDot11APDeauthStatisType                 INTEGER,
        hpnicfDot11APDeauthStatisCnt                  Counter32
    }

hpnicfDot11APDeauthStatisType OBJECT-TYPE
    SYNTAX      INTEGER
        {
            total(1),
            stationLeaving(2),
            shortResource(3),
            exception(4),
            other(5)
        }
    MAX-ACCESS  not-accessible
    STATUS      current
    DESCRIPTION
        "Represents the type of de-authentication for this AP."
    ::= { hpnicfDot11APDeauthStatisEntry 1 }

hpnicfDot11APDeauthStatisCnt   OBJECT-TYPE
    SYNTAX      Counter32
    MAX-ACCESS  read-only
    STATUS      current
    DESCRIPTION
        "Represents the total number of each type for de-authentication
         with this AP."
    ::= { hpnicfDot11APDeauthStatisEntry 2 }

-- *****************************************************************************
-- *  End of hpnicfDot11APDeauthStatisTable Definition
-- *****************************************************************************

-- *****************************************************************************
-- *  hpnicfDot11APDeassocStatisTable Definition
-- *****************************************************************************
hpnicfDot11APDeassocStatisTable OBJECT-TYPE
    SYNTAX      SEQUENCE OF HpnicfDot11APDeassocStatisEntry
    MAX-ACCESS  not-accessible
    STATUS      current
    DESCRIPTION
        "The table will provide the de-association statistic for this AP."
    ::= { hpnicfDot11APStatisGroup 15 }

hpnicfDot11APDeassocStatisEntry OBJECT-TYPE
    SYNTAX      HpnicfDot11APDeassocStatisEntry
    MAX-ACCESS  not-accessible
    STATUS      current
    DESCRIPTION
        "Each entry of the table will provide the de-association statistic
         for this AP."
    INDEX
        {
            hpnicfDot11CurAPID,
            hpnicfDot11APDeassocStatisType
        }
    ::= { hpnicfDot11APDeassocStatisTable 1 }

HpnicfDot11APDeassocStatisEntry ::= SEQUENCE
    {
        hpnicfDot11APDeassocStatisType                 INTEGER,
        hpnicfDot11APDeassocStatisCnt                  Counter32
    }

hpnicfDot11APDeassocStatisType OBJECT-TYPE
    SYNTAX      INTEGER
        {
            total(1),
            stationLeaving(2),
            shortResource(3),
            exception(4),
            other(5)
        }
    MAX-ACCESS  not-accessible
    STATUS      current
    DESCRIPTION
        "Represents the type of de-association with this AP."
    ::= { hpnicfDot11APDeassocStatisEntry 1 }

hpnicfDot11APDeassocStatisCnt   OBJECT-TYPE
    SYNTAX      Counter32
    MAX-ACCESS  read-only
    STATUS      current
    DESCRIPTION
        "Represents the total number of each type for de-association
         with this AP."
    ::= { hpnicfDot11APDeassocStatisEntry 2 }

-- *****************************************************************************
-- *  End of hpnicfDot11APDeassocStatisTable Definition
-- *****************************************************************************
-- *****************************************************************************
-- *  hpnicfDot11APAssocFailStatis2Table Definition
-- *****************************************************************************
hpnicfDot11APAssocFailStatis2Table OBJECT-TYPE
    SYNTAX      SEQUENCE OF HpnicfDot11APAssocFailStatis2Entry
    MAX-ACCESS  not-accessible
    STATUS      current
    DESCRIPTION
        "This table will provide statistic of association fails for each ap."
    ::= { hpnicfDot11APStatisGroup 16 }

hpnicfDot11APAssocFailStatis2Entry OBJECT-TYPE
    SYNTAX      HpnicfDot11APAssocFailStatis2Entry
    MAX-ACCESS  not-accessible
    STATUS      current
    DESCRIPTION
        "Each entry will provide statistic of association fails for this ap."
    INDEX
        {
            hpnicfDot11CurAPID,
            hpnicfDot11APAssocFailStatis2Type
        }
    ::= { hpnicfDot11APAssocFailStatis2Table 1 }

HpnicfDot11APAssocFailStatis2Entry ::= SEQUENCE
    {
        hpnicfDot11APAssocFailStatis2Type                 INTEGER,
        hpnicfDot11APAssocFailStatis2Cnt                  Counter32
    }

hpnicfDot11APAssocFailStatis2Type OBJECT-TYPE
    SYNTAX      INTEGER
        {
            shortResource(1),
            notSupportRateSet(2),
            unknownReasonCode(3),
            other(4)
        }
    MAX-ACCESS  not-accessible
    STATUS      current
    DESCRIPTION
        "Represents the type of association fails for this AP"
    ::= { hpnicfDot11APAssocFailStatis2Entry 1 }

hpnicfDot11APAssocFailStatis2Cnt   OBJECT-TYPE
    SYNTAX      Counter32
    MAX-ACCESS  read-only
    STATUS      current
    DESCRIPTION
        "Represents the total count of association fails for this AP."
    ::= { hpnicfDot11APAssocFailStatis2Entry 2 }

-- *****************************************************************************
-- *  End of hpnicfDot11APAssocFailStatis2Table Definition
-- *****************************************************************************
-- *****************************************************************************
-- *  hpnicfDot11APIfStatisTable Definition
-- *****************************************************************************
hpnicfDot11APIfStatisTable OBJECT-TYPE
    SYNTAX      SEQUENCE OF HpnicfDot11APIfStatisEntry
    MAX-ACCESS  not-accessible
    STATUS      current
    DESCRIPTION
        "The table will provide the statistics on the interface of the AP."
    ::= { hpnicfDot11APStatisGroup 17 }

hpnicfDot11APIfStatisEntry OBJECT-TYPE
    SYNTAX      HpnicfDot11APIfStatisEntry
    MAX-ACCESS  not-accessible
    STATUS      current
    DESCRIPTION
        "Each entry of the table will provide statistics on the interface of the AP."
    INDEX
        {
            hpnicfDot11APElementIndex,
            hpnicfDot11APIfIndex
        }
    ::= { hpnicfDot11APIfStatisTable 1 }

HpnicfDot11APIfStatisEntry ::= SEQUENCE
    {
        hpnicfDot11APIfInPkts              Counter32,
        hpnicfDot11APIfInNormalPkts        Counter32,
        hpnicfDot11APIfInErrorPkts         Counter32,
        hpnicfDot11APIfOutPkts             Counter32,
        hpnicfDot11APIfInOctets            Counter32,
        hpnicfDot11APIfOutOctets           Counter32,
        hpnicfDot11APIfFlowOut             Unsigned32,
        hpnicfDot11APIfFlowIN              Unsigned32,
        hpnicfDot11APIfInUcastPkts         Counter32,
        hpnicfDot11APIfInNUcastPkts        Counter32,
        hpnicfDot11APIfInDiscardPkts       Counter32,
        hpnicfDot11APIfOutUcastPkts        Counter32,
        hpnicfDot11APIfOutNUcastPkts       Counter32,
        hpnicfDot11APIfOutDiscardPkts      Counter32,
        hpnicfDot11APIfOutErrorPkts        Counter32,
        hpnicfDot11APIfUpdownTimes         Counter32,
        hpnicfDot11APIfStatusKeepTime      TimeTicks,
        hpnicfDot11APIfOperStatus          INTEGER,
        hpnicfDot11APIfInBrdcastPkts       Counter64,
        hpnicfDot11APIfOutBrdcastPkts      Counter64,
        hpnicfDot11APIfInMulcastPkts       Counter64,
        hpnicfDot11APIfOutMulcastPkts      Counter64,
        hpnicfDot11APIfInPayloadOctets     Counter64,
        hpnicfDot11APIfOutPayloadOctets    Counter64
    }

hpnicfDot11APIfInPkts OBJECT-TYPE
    SYNTAX      Counter32
    MAX-ACCESS  read-only
    STATUS      current
    DESCRIPTION
        "Represents the total number of packets received
         on the interface."
    ::= { hpnicfDot11APIfStatisEntry 1 }

hpnicfDot11APIfInNormalPkts OBJECT-TYPE
    SYNTAX      Counter32
    MAX-ACCESS  read-only
    STATUS      current
    DESCRIPTION
        "Represents the total number of correct
         packets received on the interface."
    ::= { hpnicfDot11APIfStatisEntry 2 }

hpnicfDot11APIfInErrorPkts OBJECT-TYPE
    SYNTAX      Counter32
    MAX-ACCESS  read-only
    STATUS      current
    DESCRIPTION
        "Represents the total number of error
         packets received on the interface."
    ::= { hpnicfDot11APIfStatisEntry 3 }

hpnicfDot11APIfOutPkts OBJECT-TYPE
    SYNTAX      Counter32
    MAX-ACCESS  read-only
    STATUS      current
    DESCRIPTION
        "Represents the total number of packets
         sent from the interface."
    ::= { hpnicfDot11APIfStatisEntry 4 }

hpnicfDot11APIfInOctets OBJECT-TYPE
    SYNTAX      Counter32
    MAX-ACCESS  read-only
    STATUS      current
    DESCRIPTION
        "Represents the total number of octets
         received on the interface."
    ::= { hpnicfDot11APIfStatisEntry 5 }

hpnicfDot11APIfOutOctets OBJECT-TYPE
    SYNTAX      Counter32
    MAX-ACCESS  read-only
    STATUS      current
    DESCRIPTION
        "Represents the total number of octets
         sent from the interface."
    ::= { hpnicfDot11APIfStatisEntry 6 }

hpnicfDot11APIfFlowOut OBJECT-TYPE
    SYNTAX      Unsigned32
    MAX-ACCESS  read-only
    STATUS      current
    DESCRIPTION
        "Represents the traffic rate (byte/s) on the uplink interface
         during a sampling period."
    ::= { hpnicfDot11APIfStatisEntry 7 }

hpnicfDot11APIfFlowIN OBJECT-TYPE
    SYNTAX      Unsigned32
    MAX-ACCESS  read-only
    STATUS      current
    DESCRIPTION
        "Represents the traffic rate (byte/s) on the downlink interface
         during a sampling period."
    ::= { hpnicfDot11APIfStatisEntry 8 }

hpnicfDot11APIfInUcastPkts OBJECT-TYPE
    SYNTAX      Counter32
    MAX-ACCESS  read-only
    STATUS      current
    DESCRIPTION
        "Represents the number of unicast packets received on the interface."
    ::= { hpnicfDot11APIfStatisEntry 9 }

hpnicfDot11APIfInNUcastPkts OBJECT-TYPE
    SYNTAX      Counter32
    MAX-ACCESS  read-only
    STATUS      current
    DESCRIPTION
        "Represents the number of non-unicast packets received on the wired
         interface."
    ::= { hpnicfDot11APIfStatisEntry 10 }

hpnicfDot11APIfInDiscardPkts OBJECT-TYPE
    SYNTAX      Counter32
    MAX-ACCESS  read-only
    STATUS      current
    DESCRIPTION
        "Represents the number of unicast packets discarded on the interface."
    ::= { hpnicfDot11APIfStatisEntry 11 }

hpnicfDot11APIfOutUcastPkts OBJECT-TYPE
    SYNTAX      Counter32
    MAX-ACCESS  read-only
    STATUS      current
    DESCRIPTION
        "Represents the number of unicast packets send on the interface."
    ::= { hpnicfDot11APIfStatisEntry 12 }

hpnicfDot11APIfOutNUcastPkts OBJECT-TYPE
    SYNTAX      Counter32
    MAX-ACCESS  read-only
    STATUS      current
    DESCRIPTION
        "Represents the number of non-unicast packets send on the interface."
    ::= { hpnicfDot11APIfStatisEntry 13 }

hpnicfDot11APIfOutDiscardPkts OBJECT-TYPE
    SYNTAX      Counter32
    MAX-ACCESS  read-only
    STATUS      current
    DESCRIPTION
        "Represents the number of discarded packets send on the interface."
    ::= { hpnicfDot11APIfStatisEntry 14 }

hpnicfDot11APIfOutErrorPkts OBJECT-TYPE
    SYNTAX      Counter32
    MAX-ACCESS  read-only
    STATUS      current
    DESCRIPTION
        "Represents the number of error packets send on the interface."
    ::= { hpnicfDot11APIfStatisEntry 15 }

hpnicfDot11APIfUpdownTimes OBJECT-TYPE
    SYNTAX      Counter32
    MAX-ACCESS  read-only
    STATUS      current
    DESCRIPTION
        "Represents the up/down times on the interface."
    ::= { hpnicfDot11APIfStatisEntry 16 }

hpnicfDot11APIfStatusKeepTime OBJECT-TYPE
    SYNTAX      TimeTicks
    MAX-ACCESS  read-only
    STATUS      current
    DESCRIPTION
        "Represents the last change time on the interface."
    ::= { hpnicfDot11APIfStatisEntry 17 }

hpnicfDot11APIfOperStatus OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { hpnicfDot11APIfStatisEntry 18 }

hpnicfDot11APIfInBrdcastPkts OBJECT-TYPE
    SYNTAX      Counter64
    MAX-ACCESS  read-only
    STATUS      current
    DESCRIPTION
        "Represents the number of broadcast packets received on the interface."
    ::= { hpnicfDot11APIfStatisEntry 19 }

hpnicfDot11APIfOutBrdcastPkts OBJECT-TYPE
    SYNTAX      Counter64
    MAX-ACCESS  read-only
    STATUS      current
    DESCRIPTION
        "Represents the number of broadcast packets sent on the interface."
    ::= { hpnicfDot11APIfStatisEntry 20 }

hpnicfDot11APIfInMulcastPkts OBJECT-TYPE
    SYNTAX      Counter64
    MAX-ACCESS  read-only
    STATUS      current
    DESCRIPTION
        "Represents the number of multicast packets received on the interface."
    ::= { hpnicfDot11APIfStatisEntry 21 }

hpnicfDot11APIfOutMulcastPkts OBJECT-TYPE
    SYNTAX      Counter64
    MAX-ACCESS  read-only
    STATUS      current
    DESCRIPTION
        "Represents the number of multicast packets sent on the interface."
    ::= { hpnicfDot11APIfStatisEntry 22 }

hpnicfDot11APIfInPayloadOctets OBJECT-TYPE
    SYNTAX      Counter64
    MAX-ACCESS  read-only
    STATUS      current
    DESCRIPTION
        "Represents the number of actual octets received on the interface."
    ::= { hpnicfDot11APIfStatisEntry 23 }

hpnicfDot11APIfOutPayloadOctets OBJECT-TYPE
    SYNTAX      Counter64
    MAX-ACCESS  read-only
    STATUS      current
    DESCRIPTION
        "Represents the number of actual octets sent on the interface."
    ::= { hpnicfDot11APIfStatisEntry 24 }

-- *****************************************************************************
-- *  End of hpnicfDot11APIfStatisTable Definition
-- *****************************************************************************

-- *****************************************************************************
-- *  hpnicfDot11RadioMngFrmStatisTable Definition
-- *****************************************************************************
hpnicfDot11RadioMngFrmStatisTable OBJECT-TYPE
    SYNTAX      SEQUENCE OF HpnicfDot11RadioMngFrmStatisEntry
    MAX-ACCESS  not-accessible
    STATUS      current
    DESCRIPTION
        "The table will provide the management frame statistic of this radio."
    ::= { hpnicfDot11APStatisGroup 18 }

hpnicfDot11RadioMngFrmStatisEntry OBJECT-TYPE
    SYNTAX      HpnicfDot11RadioMngFrmStatisEntry
    MAX-ACCESS  not-accessible
    STATUS      current
    DESCRIPTION
        "Each entry of the table will provide the management
         frame statistic of this radio."
    INDEX
        {
            hpnicfDot11CurAPID,
            hpnicfDot11RadioID,
            hpnicfDot11MngFrmType
        }
    ::= { hpnicfDot11RadioMngFrmStatisTable 1 }

HpnicfDot11RadioMngFrmStatisEntry ::= SEQUENCE
    {
        hpnicfDot11MngFrmType                 INTEGER,
        hpnicfDot11MngFrmCnt                  Counter32
    }

hpnicfDot11MngFrmType  OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { hpnicfDot11RadioMngFrmStatisEntry 1 }

hpnicfDot11MngFrmCnt  OBJECT-TYPE
    SYNTAX      Counter32
    MAX-ACCESS  read-only
    STATUS      current
    DESCRIPTION
        "Represents the total number of each type of management frame on this
         radio."
    ::= { hpnicfDot11RadioMngFrmStatisEntry 2 }
-- *****************************************************************************
-- *  End of hpnicfDot11RadioMngFrmStatisTable Definition
-- *****************************************************************************


-- *****************************************************************************
-- *  hpnicfDot11APPacketSizeStatisTable Definition
-- *****************************************************************************
hpnicfDot11APPacketSizeStatisTable  OBJECT-TYPE
        SYNTAX        SEQUENCE OF HpnicfDot11APPacketSizeStatisEntry
        MAX-ACCESS    not-accessible
        STATUS        current
        DESCRIPTION
                "This table provides packets statistic base on size."
        ::= { hpnicfDot11APStatisGroup 19 }

hpnicfDot11APPacketSizeStatisEntry  OBJECT-TYPE
        SYNTAX        HpnicfDot11APPacketSizeStatisEntry
        MAX-ACCESS    not-accessible
        STATUS        current
        DESCRIPTION
                "Each entry provides packets statistic base on size for each radio
                 of a specific AP."
        INDEX
            {
                hpnicfDot11CurAPID,
                hpnicfDot11RadioID,
                hpnicfDot11APPacketSize
            }
        ::= { hpnicfDot11APPacketSizeStatisTable 1 }

HpnicfDot11APPacketSizeStatisEntry    ::=SEQUENCE
        {
            hpnicfDot11APPacketSize          INTEGER,
            hpnicfDot11APRXPacketSizeCount   Counter64,
            hpnicfDot11APTXPacketSizeCount   Counter64
        }

hpnicfDot11APPacketSize    OBJECT-TYPE
        SYNTAX    INTEGER
            {
                sizeLevel1(1),
                sizeLevel2(2),
                sizeLevel3(3),
                sizeLevel4(4)
            }
        MAX-ACCESS    not-accessible
        STATUS        current
        DESCRIPTION
            "This node represents packet size:
                    sizeLevel1 : size <= 128
                    sizeLevel2 : 128 < size <= 512
                    sizeLevel3 : 512 < size <= 1024
                    sizeLevel4 : size > 1024"
    ::= { hpnicfDot11APPacketSizeStatisEntry 1 }

hpnicfDot11APRXPacketSizeCount    OBJECT-TYPE
        SYNTAX        Counter64
        MAX-ACCESS    read-only
        STATUS        current
        DESCRIPTION
                "Represents the count of packets reception base on frame size."
    ::= { hpnicfDot11APPacketSizeStatisEntry 2 }

hpnicfDot11APTXPacketSizeCount    OBJECT-TYPE
        SYNTAX        Counter64
        MAX-ACCESS    read-only
        STATUS        current
        DESCRIPTION
                "Represents the count of packets transmission base on frame size."
    ::= { hpnicfDot11APPacketSizeStatisEntry 3 }
-- *****************************************************************************
-- *  End of hpnicfDot11APPacketSizeStatisTable Definition
-- *****************************************************************************

-- *****************************************************************************
-- *  hpnicfDot11APPacketRateStatisTable Definition
-- *****************************************************************************
hpnicfDot11APPacketRateStatisTable  OBJECT-TYPE
        SYNTAX        SEQUENCE OF HpnicfDot11APPacketRateStatisEntry
        MAX-ACCESS    not-accessible
        STATUS        current
        DESCRIPTION
                "This table provides packets statistic base on rate."
        ::= { hpnicfDot11APStatisGroup 20 }

hpnicfDot11APPacketRateStatisEntry  OBJECT-TYPE
        SYNTAX        HpnicfDot11APPacketRateStatisEntry
        MAX-ACCESS    not-accessible
        STATUS        current
        DESCRIPTION
                "Each entry provides packets statistic base on rate for each radio
                 of a specific AP."
        INDEX
            {
                hpnicfDot11CurAPID,
                hpnicfDot11RadioID,
                hpnicfDot11APPacketRate
            }
        ::= { hpnicfDot11APPacketRateStatisTable 1 }

HpnicfDot11APPacketRateStatisEntry    ::=SEQUENCE
        {
                hpnicfDot11APPacketRate          Integer32,
                hpnicfDot11APRXPacketRateCount   Counter64,
                hpnicfDot11APTXPacketRateCount   Counter64
        }

hpnicfDot11APPacketRate    OBJECT-TYPE
        SYNTAX        Integer32
        MAX-ACCESS    not-accessible
        STATUS        current
        DESCRIPTION
                "Represents transmit data rate(twice as actual rate)."
    ::= { hpnicfDot11APPacketRateStatisEntry 1 }

hpnicfDot11APRXPacketRateCount    OBJECT-TYPE
        SYNTAX        Counter64
        MAX-ACCESS    read-only
        STATUS        current
        DESCRIPTION
                "Represents the count of packets reception base on transmit data rate."
    ::= { hpnicfDot11APPacketRateStatisEntry 2 }

hpnicfDot11APTXPacketRateCount    OBJECT-TYPE
        SYNTAX        Counter64
        MAX-ACCESS    read-only
        STATUS        current
        DESCRIPTION
                "Represents the count of packets transmission base on transmit data rate."
    ::= { hpnicfDot11APPacketRateStatisEntry 3 }

-- *****************************************************************************
-- *  End of hpnicfDot11APPacketRateStatisTable Definition
-- *****************************************************************************

-- *****************************************************************************
-- *  hpnicfDot11APPacketMCSRateStatisTable Definition
-- *****************************************************************************
hpnicfDot11APPacketMCSRateStatisTable  OBJECT-TYPE
        SYNTAX        SEQUENCE OF HpnicfDot11APPacketMCSRateStatisEntry
        MAX-ACCESS    not-accessible
        STATUS        current
        DESCRIPTION
                "This table provides packets statistic base on MCS rate."
        ::= { hpnicfDot11APStatisGroup 21 }

hpnicfDot11APPacketMCSRateStatisEntry  OBJECT-TYPE
        SYNTAX        HpnicfDot11APPacketMCSRateStatisEntry
        MAX-ACCESS    not-accessible
        STATUS        current
        DESCRIPTION
                "Each entry provides packets statistic base on MCS rate for each radio
                 of a specific AP."
        INDEX
            {
                hpnicfDot11CurAPID,
                hpnicfDot11RadioID,
                hpnicfDot11APPacketMCSRate
            }
        ::= { hpnicfDot11APPacketMCSRateStatisTable 1 }

HpnicfDot11APPacketMCSRateStatisEntry  ::=SEQUENCE
        {
            hpnicfDot11APPacketMCSRate          Integer32,
            hpnicfDot11APRXPacketMCSRateCount   Counter64,
            hpnicfDot11APTXPacketMCSRateCount   Counter64
        }

hpnicfDot11APPacketMCSRate    OBJECT-TYPE
        SYNTAX        Integer32
        MAX-ACCESS    not-accessible
        STATUS        current
        DESCRIPTION
            "Represents transmit data rate(twice as actual rate)."
    ::= { hpnicfDot11APPacketMCSRateStatisEntry 1 }

hpnicfDot11APRXPacketMCSRateCount    OBJECT-TYPE
        SYNTAX        Counter64
        MAX-ACCESS    read-only
        STATUS        current
        DESCRIPTION
            "Represents the count of packets reception base on transmit data rate."
    ::= { hpnicfDot11APPacketMCSRateStatisEntry 2 }

hpnicfDot11APTXPacketMCSRateCount    OBJECT-TYPE
        SYNTAX        Counter64
        MAX-ACCESS    read-only
        STATUS        current
        DESCRIPTION
            "Represents the count of packets transmission base on transmit
             data rate."
    ::= { hpnicfDot11APPacketMCSRateStatisEntry 3 }

-- *****************************************************************************
-- *  End of hpnicfDot11APPacketMcsRateStatisTable Definition
-- *****************************************************************************

-- *****************************************************************************
-- *  hpnicfDot11APAssocFailStatis3Table Definition
-- *****************************************************************************
hpnicfDot11APAssocFailStatis3Table OBJECT-TYPE
    SYNTAX      SEQUENCE OF HpnicfDot11APAssocFailStatis3Entry
    MAX-ACCESS  not-accessible
    STATUS      current
    DESCRIPTION
        "This table will provide statistic of association fails for each AP."
    ::= { hpnicfDot11APStatisGroup 22 }

hpnicfDot11APAssocFailStatis3Entry OBJECT-TYPE
    SYNTAX      HpnicfDot11APAssocFailStatis3Entry
    MAX-ACCESS  not-accessible
    STATUS      current
    DESCRIPTION
        "Each entry will provide statistic of association failure with this AP
         because of different reasons."
    INDEX
        {
            hpnicfDot11CurAPID
       }
    ::= { hpnicfDot11APAssocFailStatis3Table 1 }

HpnicfDot11APAssocFailStatis3Entry ::= SEQUENCE
    {
        hpnicfDot11APAssocFailStatis3SRCnt                 Counter32,
        hpnicfDot11APAssocFailStatis3NSRCnt                Counter32,
        hpnicfDot11APAssocFailStatis3URCCnt                Counter32,
        hpnicfDot11APAssocFailStatis3RFCnt                 Counter32,
        hpnicfDot11APAssocFailStatis3OtherCnt              Counter32,
        hpnicfDot11APAssocFailStatisRSSILowCntCM           Counter32
    }

hpnicfDot11APAssocFailStatis3SRCnt OBJECT-TYPE
    SYNTAX      Counter32
    MAX-ACCESS  read-only
    STATUS      current
    DESCRIPTION
        "This object represents the count of association failure because of
         lack of resource."
    ::= { hpnicfDot11APAssocFailStatis3Entry 1 }

hpnicfDot11APAssocFailStatis3NSRCnt OBJECT-TYPE
    SYNTAX      Counter32
    MAX-ACCESS  read-only
    STATUS      current
    DESCRIPTION
        "This object represents the count of association failure because of
         not support rate set."
    ::= { hpnicfDot11APAssocFailStatis3Entry 2 }

hpnicfDot11APAssocFailStatis3URCCnt OBJECT-TYPE
    SYNTAX      Counter32
    MAX-ACCESS  read-only
    STATUS      current
    DESCRIPTION
        "This object represents the count of association failure because of
         unknown reason code."
    ::= { hpnicfDot11APAssocFailStatis3Entry 3 }

hpnicfDot11APAssocFailStatis3RFCnt OBJECT-TYPE
    SYNTAX      Counter32
    MAX-ACCESS  read-only
    STATUS      current
    DESCRIPTION
        "This object represents the count of association failure because of
         re-associate failed."
    ::= { hpnicfDot11APAssocFailStatis3Entry 4 }

hpnicfDot11APAssocFailStatis3OtherCnt OBJECT-TYPE
    SYNTAX      Counter32
    MAX-ACCESS  read-only
    STATUS      current
    DESCRIPTION
        "This object represents the count of association fails because of
         reason not in 802.11 the protocol."
    ::= { hpnicfDot11APAssocFailStatis3Entry 5 }

hpnicfDot11APAssocFailStatisRSSILowCntCM OBJECT-TYPE
    SYNTAX      Counter32
    MAX-ACCESS  read-only
    STATUS      current
    DESCRIPTION
        "Represents the count of failed associations due to low RSSI."
    ::= { hpnicfDot11APAssocFailStatis3Entry 6 }

-- *****************************************************************************
-- *  End of hpnicfDot11APAssocFailStatis3Table Definition
-- *****************************************************************************

-- *****************************************************************************
-- *  hpnicfDot11APIfStatisByAPIDTable Definition
-- *****************************************************************************
hpnicfDot11APIfStatisByAPIDTable OBJECT-TYPE
    SYNTAX      SEQUENCE OF HpnicfDot11APIfStatisByAPIDEntry
    MAX-ACCESS  not-accessible
    STATUS      current
    DESCRIPTION
        "The table will provide the statistics on the interface of the AP."
    ::= { hpnicfDot11APStatisGroup 23 }

hpnicfDot11APIfStatisByAPIDEntry OBJECT-TYPE
    SYNTAX      HpnicfDot11APIfStatisByAPIDEntry
    MAX-ACCESS  not-accessible
    STATUS      current
    DESCRIPTION
        "Each entry of the table will provide statistics on the interface of the AP."
    INDEX
        {
            hpnicfDot11CurAPID,
            hpnicfDot11APIfIndex
        }
    ::= { hpnicfDot11APIfStatisByAPIDTable 1 }

HpnicfDot11APIfStatisByAPIDEntry ::= SEQUENCE
    {
        hpnicfDot11APIfInPkts2              Counter64,
        hpnicfDot11APIfInNormalPkts2        Counter64,
        hpnicfDot11APIfInErrorPkts2         Counter64,
        hpnicfDot11APIfOutPkts2             Counter64,
        hpnicfDot11APIfInOctets2            Counter64,
        hpnicfDot11APIfOutOctets2           Counter64,
        hpnicfDot11APIfFlowOut2             Unsigned32,
        hpnicfDot11APIfFlowIN2              Unsigned32,
        hpnicfDot11APIfInUcastPkts2         Counter64,
        hpnicfDot11APIfInNUcastPkts2        Counter64,
        hpnicfDot11APIfInDiscardPkts2       Counter64,
        hpnicfDot11APIfOutUcastPkts2        Counter64,
        hpnicfDot11APIfOutNUcastPkts2       Counter64,
        hpnicfDot11APIfOutDiscardPkts2      Counter64,
        hpnicfDot11APIfOutErrorPkts2        Counter64,
        hpnicfDot11APIfUpdownTimes2         Counter32,
        hpnicfDot11APIfStatusKeepTime2      TimeTicks,
        hpnicfDot11APIfOperStatus2          INTEGER,
        hpnicfDot11APIfInBrdcastPkts2       Counter64,
        hpnicfDot11APIfOutBrdcastPkts2      Counter64,
        hpnicfDot11APIfInMulcastPkts2       Counter64,
        hpnicfDot11APIfOutMulcastPkts2      Counter64,
        hpnicfDot11APIfInPayloadOctets2     Counter64,
        hpnicfDot11APIfOutPayloadOctets2    Counter64,
        hpnicfDot11APIfInDataOctets2        Counter64,
        hpnicfDot11APIfOutDataOctets2       Counter64,
        hpnicfDot11APIfAdminStatus          INTEGER,
        hpnicfDot11APIfOperStatusCM         INTEGER
    }

hpnicfDot11APIfInPkts2 OBJECT-TYPE
    SYNTAX      Counter64
    MAX-ACCESS  read-only
    STATUS      current
    DESCRIPTION
        "Represents the total number of packets received
         on the interface."
    ::= { hpnicfDot11APIfStatisByAPIDEntry 1 }

hpnicfDot11APIfInNormalPkts2 OBJECT-TYPE
    SYNTAX      Counter64
    MAX-ACCESS  read-only
    STATUS      current
    DESCRIPTION
        "Represents the total number of correct
         packets received on the interface."
    ::= { hpnicfDot11APIfStatisByAPIDEntry 2 }

hpnicfDot11APIfInErrorPkts2 OBJECT-TYPE
    SYNTAX      Counter64
    MAX-ACCESS  read-only
    STATUS      current
    DESCRIPTION
        "Represents the total number of error
         packets received on the interface."
    ::= { hpnicfDot11APIfStatisByAPIDEntry 3 }

hpnicfDot11APIfOutPkts2 OBJECT-TYPE
    SYNTAX      Counter64
    MAX-ACCESS  read-only
    STATUS      current
    DESCRIPTION
        "Represents the total number of packets
         sent from the interface."
    ::= { hpnicfDot11APIfStatisByAPIDEntry 4 }

hpnicfDot11APIfInOctets2 OBJECT-TYPE
    SYNTAX      Counter64
    MAX-ACCESS  read-only
    STATUS      current
    DESCRIPTION
        "Represents the total number of octets
         received on the interface."
    ::= { hpnicfDot11APIfStatisByAPIDEntry 5 }

hpnicfDot11APIfOutOctets2 OBJECT-TYPE
    SYNTAX      Counter64
    MAX-ACCESS  read-only
    STATUS      current
    DESCRIPTION
        "Represents the total number of octets
         sent from the interface."
    ::= { hpnicfDot11APIfStatisByAPIDEntry 6 }

hpnicfDot11APIfFlowOut2 OBJECT-TYPE
    SYNTAX      Unsigned32
    MAX-ACCESS  read-only
    STATUS      current
    DESCRIPTION
        "Represents the traffic rate (byte/s) on the uplink interface
         during a sampling period."
    ::= { hpnicfDot11APIfStatisByAPIDEntry 7 }

hpnicfDot11APIfFlowIN2 OBJECT-TYPE
    SYNTAX      Unsigned32
    MAX-ACCESS  read-only
    STATUS      current
    DESCRIPTION
        "Represents the traffic rate (byte/s) on the downlink interface
         during a sampling period."
    ::= { hpnicfDot11APIfStatisByAPIDEntry 8 }

hpnicfDot11APIfInUcastPkts2 OBJECT-TYPE
    SYNTAX      Counter64
    MAX-ACCESS  read-only
    STATUS      current
    DESCRIPTION
        "Represents the number of unicast packets received on the interface."
    ::= { hpnicfDot11APIfStatisByAPIDEntry 9 }

hpnicfDot11APIfInNUcastPkts2 OBJECT-TYPE
    SYNTAX      Counter64
    MAX-ACCESS  read-only
    STATUS      current
    DESCRIPTION
        "Represents the number of non-unicast packets received on the wired
         interface."
    ::= { hpnicfDot11APIfStatisByAPIDEntry 10 }

hpnicfDot11APIfInDiscardPkts2 OBJECT-TYPE
    SYNTAX      Counter64
    MAX-ACCESS  read-only
    STATUS      current
    DESCRIPTION
        "Represents the number of unicast packets discarded on the interface."
    ::= { hpnicfDot11APIfStatisByAPIDEntry 11 }

hpnicfDot11APIfOutUcastPkts2 OBJECT-TYPE
    SYNTAX      Counter64
    MAX-ACCESS  read-only
    STATUS      current
    DESCRIPTION
        "Represents the number of unicast packets send on the interface."
    ::= { hpnicfDot11APIfStatisByAPIDEntry 12 }

hpnicfDot11APIfOutNUcastPkts2 OBJECT-TYPE
    SYNTAX      Counter64
    MAX-ACCESS  read-only
    STATUS      current
    DESCRIPTION
        "Represents the number of non-unicast packets send on the interface."
    ::= { hpnicfDot11APIfStatisByAPIDEntry 13 }

hpnicfDot11APIfOutDiscardPkts2 OBJECT-TYPE
    SYNTAX      Counter64
    MAX-ACCESS  read-only
    STATUS      current
    DESCRIPTION
        "Represents the number of discarded packets send on the interface."
    ::= { hpnicfDot11APIfStatisByAPIDEntry 14 }

hpnicfDot11APIfOutErrorPkts2 OBJECT-TYPE
    SYNTAX      Counter64
    MAX-ACCESS  read-only
    STATUS      current
    DESCRIPTION
        "Represents the number of error packets send on the interface."
    ::= { hpnicfDot11APIfStatisByAPIDEntry 15 }

hpnicfDot11APIfUpdownTimes2 OBJECT-TYPE
    SYNTAX      Counter32
    MAX-ACCESS  read-only
    STATUS      current
    DESCRIPTION
        "Represents the up/down times on the interface."
    ::= { hpnicfDot11APIfStatisByAPIDEntry 16 }

hpnicfDot11APIfStatusKeepTime2 OBJECT-TYPE
    SYNTAX      TimeTicks
    MAX-ACCESS  read-only
    STATUS      current
    DESCRIPTION
        "Represents the last change time on the interface."
    ::= { hpnicfDot11APIfStatisByAPIDEntry 17 }

hpnicfDot11APIfOperStatus2 OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { hpnicfDot11APIfStatisByAPIDEntry 18 }

hpnicfDot11APIfInBrdcastPkts2 OBJECT-TYPE
    SYNTAX      Counter64
    MAX-ACCESS  read-only
    STATUS      current
    DESCRIPTION
        "Represents the number of broadcast packets received on the interface."
    ::= { hpnicfDot11APIfStatisByAPIDEntry 19 }

hpnicfDot11APIfOutBrdcastPkts2 OBJECT-TYPE
    SYNTAX      Counter64
    MAX-ACCESS  read-only
    STATUS      current
    DESCRIPTION
        "Represents the number of broadcast packets sent on the interface."
    ::= { hpnicfDot11APIfStatisByAPIDEntry 20 }

hpnicfDot11APIfInMulcastPkts2 OBJECT-TYPE
    SYNTAX      Counter64
    MAX-ACCESS  read-only
    STATUS      current
    DESCRIPTION
        "Represents the number of multicast packets received on the interface."
    ::= { hpnicfDot11APIfStatisByAPIDEntry 21 }

hpnicfDot11APIfOutMulcastPkts2 OBJECT-TYPE
    SYNTAX      Counter64
    MAX-ACCESS  read-only
    STATUS      current
    DESCRIPTION
        "Represents the number of multicast packets sent on the interface."
    ::= { hpnicfDot11APIfStatisByAPIDEntry 22 }

hpnicfDot11APIfInPayloadOctets2 OBJECT-TYPE
    SYNTAX      Counter64
    MAX-ACCESS  read-only
    STATUS      current
    DESCRIPTION
        "Represents the number of actual octets received on the interface."
    ::= { hpnicfDot11APIfStatisByAPIDEntry 23 }

hpnicfDot11APIfOutPayloadOctets2 OBJECT-TYPE
    SYNTAX      Counter64
    MAX-ACCESS  read-only
    STATUS      current
    DESCRIPTION
        "Represents the number of actual octets sent on the interface."
    ::= { hpnicfDot11APIfStatisByAPIDEntry 24 }

hpnicfDot11APIfInDataOctets2 OBJECT-TYPE
    SYNTAX      Counter64
    MAX-ACCESS  read-only
    STATUS      current
    DESCRIPTION
        "Represents the number of actual data octets received on the interface."
    ::= { hpnicfDot11APIfStatisByAPIDEntry 25 }

hpnicfDot11APIfOutDataOctets2 OBJECT-TYPE
    SYNTAX      Counter64
    MAX-ACCESS  read-only
    STATUS      current
    DESCRIPTION
        "Represents the number of actual data octets sent on the interface."
    ::= { hpnicfDot11APIfStatisByAPIDEntry 26 }

hpnicfDot11APIfAdminStatus OBJECT-TYPE
    SYNTAX  INTEGER {
                up(1),       -- ready to forward packets
                down(2),
                testing(3)   -- in a test mode
            }
    MAX-ACCESS  read-write
    STATUS      current
    DESCRIPTION
            "Expected state of the interface.  In testing state the
            interface does not forward any operational packets.  When
             a managed system is initialized, all interfaces start with
            hpnicfDot11APIfAdminStatus in the down state.  As a result
            of either explicit management action or per configuration
            information retained by the managed system,
            hpnicfDot11APIfAdminStatus is then changed to either the up
             or testing state or remains in the down state."
    ::= { hpnicfDot11APIfStatisByAPIDEntry 27 }

hpnicfDot11APIfOperStatusCM OBJECT-TYPE
    SYNTAX  INTEGER {
                       up(1),        -- ready to forward packets
                       down(2),
                       testing(3),   -- in a test mode
                       admindown(4)  -- shutdown by administrator
                    }
    MAX-ACCESS  read-only
    STATUS      current
    DESCRIPTION
        "Operational status of the interface."
    ::= { hpnicfDot11APIfStatisByAPIDEntry 28 }

-- *****************************************************************************
-- *  End of hpnicfDot11APIfStatisTable1 Definition
-- *****************************************************************************

-- *****************************************************************************
-- *  hpnicfDot11APUserSecAuthStatisTable Definition
-- *****************************************************************************
hpnicfDot11APUserSecAuthStatisTable OBJECT-TYPE
    SYNTAX      SEQUENCE OF HpnicfDot11APUserSecAuthStatisEntry
    MAX-ACCESS  not-accessible
    STATUS      current
    DESCRIPTION
        "The table will provide the user authentication statistic for this AP."
    ::= { hpnicfDot11APStatisGroup 24 }

hpnicfDot11APUserSecAuthStatisEntry OBJECT-TYPE
    SYNTAX      HpnicfDot11APUserSecAuthStatisEntry
    MAX-ACCESS  not-accessible
    STATUS      current
    DESCRIPTION
        "Each entry of the table will provide the user authentication statistic
        for this AP."
    INDEX
        {
            hpnicfDot11CurAPID
       }
    ::= { hpnicfDot11APUserSecAuthStatisTable 1 }

HpnicfDot11APUserSecAuthStatisEntry ::= SEQUENCE
    {
        hpnicfDot11APUserAuthCurNumber             Integer32,
        hpnicfDot11APUserConnFailCnt               Counter32,
        hpnicfDot11APUserAuthReqCnt                Counter32,
        hpnicfDot11APUserAuthSuccCnt               Counter32,
        hpnicfDot11APUserAuthFailCnt               Counter32,
        hpnicfDot11AllUserOnlineTime               TimeTicks
    }

hpnicfDot11APUserAuthCurNumber OBJECT-TYPE
    SYNTAX      Integer32
    MAX-ACCESS  read-only
    STATUS      current
    DESCRIPTION
        "Represents the current number of user authenticated with this AP."
    ::= { hpnicfDot11APUserSecAuthStatisEntry 1 }

hpnicfDot11APUserConnFailCnt OBJECT-TYPE
    SYNTAX      Counter32
    MAX-ACCESS  read-only
    STATUS      current
    DESCRIPTION
        "Represents the total number of user disconnected with this AP."
    ::= { hpnicfDot11APUserSecAuthStatisEntry 2 }

hpnicfDot11APUserAuthReqCnt OBJECT-TYPE
    SYNTAX      Counter32
    MAX-ACCESS  read-only
    STATUS      current
    DESCRIPTION
        "Represents the total number of user authentication request with this AP."
    ::= { hpnicfDot11APUserSecAuthStatisEntry 3 }

hpnicfDot11APUserAuthSuccCnt OBJECT-TYPE
    SYNTAX      Counter32
    MAX-ACCESS  read-only
    STATUS      current
    DESCRIPTION
        "Represents the total number of successful authenticated users with this AP."
    ::= { hpnicfDot11APUserSecAuthStatisEntry 4 }

hpnicfDot11APUserAuthFailCnt OBJECT-TYPE
    SYNTAX      Counter32
    MAX-ACCESS  read-only
    STATUS      current
    DESCRIPTION
        "Represents the total number of user authentication failures with this AP."
    ::= { hpnicfDot11APUserSecAuthStatisEntry 5 }

hpnicfDot11AllUserOnlineTime OBJECT-TYPE
    SYNTAX      TimeTicks
    MAX-ACCESS  read-only
    STATUS      current
    DESCRIPTION
        "Represents the online time of all successful authenticated users with this AP."
    ::= { hpnicfDot11APUserSecAuthStatisEntry 6 }

-- *****************************************************************************
-- *  End of hpnicfDot11APUserSecAuthStatisEntry Definition
-- *****************************************************************************

-- *****************************************************************************
-- *  hpnicfDot11APUserInfoStatisTable Definition
-- *****************************************************************************
hpnicfDot11APUserInfoStatisTable OBJECT-TYPE
    SYNTAX      SEQUENCE OF HpnicfDot11APUserInfoStatisEntry
    MAX-ACCESS  not-accessible
    STATUS      current
    DESCRIPTION
        "The table will provide the user information statistic of this AP."
    ::= { hpnicfDot11APStatisGroup 25 }

hpnicfDot11APUserInfoStatisEntry OBJECT-TYPE
    SYNTAX      HpnicfDot11APUserInfoStatisEntry
    MAX-ACCESS  not-accessible
    STATUS      current
    DESCRIPTION
        "Each entry of the table will provide the user information statistic
        of this AP."
    INDEX
        {
            hpnicfDot11CurAPID,
            hpnicfDot11APUserMacAddr
        }
    ::= { hpnicfDot11APUserInfoStatisTable 1 }

HpnicfDot11APUserInfoStatisEntry ::= SEQUENCE
    {
        hpnicfDot11APUserMacAddr                  MacAddress,
        hpnicfDot11APUserIpAddr                   IpAddress,
        hpnicfDot11APUserLoginName                OCTET STRING,
        hpnicfDot11APUserLoginTime                OCTET STRING,
        hpnicfDot11APUserOnlineTime               TimeTicks,
        hpnicfDot11APUserLoginNameCM              OCTET STRING,
        hpnicfDot11APUserAuthTypeCM               INTEGER,
        hpnicfDot11APUserTxPacketCntCM            Counter32,
        hpnicfDot11APUserTxBytesCM                Counter64,
        hpnicfDot11APUserRxPacketCntCM            Counter32,
        hpnicfDot11APUserRxBytesCM                Counter64
    }

hpnicfDot11APUserMacAddr OBJECT-TYPE
    SYNTAX      MacAddress
    MAX-ACCESS  not-accessible
    STATUS      current
    DESCRIPTION
        "Represents the mac address of user logging to this AP."
    ::= { hpnicfDot11APUserInfoStatisEntry 1 }

hpnicfDot11APUserIpAddr OBJECT-TYPE
    SYNTAX      IpAddress
    MAX-ACCESS  read-only
    STATUS      current
    DESCRIPTION
        "Represents the ip address of user logging to this AP."
    ::= { hpnicfDot11APUserInfoStatisEntry 2 }

hpnicfDot11APUserLoginName OBJECT-TYPE
    SYNTAX      OCTET STRING
    MAX-ACCESS  read-only
    STATUS      current
    DESCRIPTION
        "Represents the login name of user logging to this AP."
    ::= { hpnicfDot11APUserInfoStatisEntry 3 }

hpnicfDot11APUserLoginTime OBJECT-TYPE
    SYNTAX      OCTET STRING
    MAX-ACCESS  read-only
    STATUS      current
    DESCRIPTION
        "Represents the login time of user with this AP."
    ::= { hpnicfDot11APUserInfoStatisEntry 4 }

hpnicfDot11APUserOnlineTime OBJECT-TYPE
    SYNTAX      TimeTicks
    MAX-ACCESS  read-only
    STATUS      current
    DESCRIPTION
        "Represents the online time of user with this AP."
    ::= { hpnicfDot11APUserInfoStatisEntry 5 }

hpnicfDot11APUserLoginNameCM OBJECT-TYPE
    SYNTAX      OCTET STRING
    MAX-ACCESS  read-only
    STATUS      current
    DESCRIPTION
        "Represents the login name of dot1x user logging to this AP."
    ::= { hpnicfDot11APUserInfoStatisEntry 6 }

hpnicfDot11APUserAuthTypeCM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { hpnicfDot11APUserInfoStatisEntry 7 }

hpnicfDot11APUserTxPacketCntCM OBJECT-TYPE
    SYNTAX      Counter32
    MAX-ACCESS  read-only
    STATUS      current
    DESCRIPTION
        "Represents the total count of packets sent to online users."
    ::= { hpnicfDot11APUserInfoStatisEntry 8 }

hpnicfDot11APUserTxBytesCM OBJECT-TYPE
    SYNTAX      Counter64
    MAX-ACCESS  read-only
    STATUS      current
    DESCRIPTION
        "Represents the total bytes sent to online users."
    ::= { hpnicfDot11APUserInfoStatisEntry 9 }

hpnicfDot11APUserRxPacketCntCM OBJECT-TYPE
    SYNTAX      Counter32
    MAX-ACCESS  read-only
    STATUS      current
    DESCRIPTION
        "Represents the total count of packets received from online users."
    ::= { hpnicfDot11APUserInfoStatisEntry 10 }

hpnicfDot11APUserRxBytesCM OBJECT-TYPE
    SYNTAX      Counter64
    MAX-ACCESS  read-only
    STATUS      current
    DESCRIPTION
        "Represents the total bytes received from online users."
    ::= { hpnicfDot11APUserInfoStatisEntry 11 }

-- *****************************************************************************
-- *  End of hpnicfDot11APUserInfoStatisTable Definition
-- *****************************************************************************

-- *****************************************************************************
-- *  hpnicfDot11APReassocStatis2Table Definition
-- *****************************************************************************
hpnicfDot11APReassocStatis2Table OBJECT-TYPE
    SYNTAX      SEQUENCE OF HpnicfDot11APReassocStatis2Entry
    MAX-ACCESS  not-accessible
    STATUS      current
    DESCRIPTION
        "This table will provide statistic of reassociation for each AP."
    ::= { hpnicfDot11APStatisGroup 26 }

hpnicfDot11APReassocStatis2Entry OBJECT-TYPE
    SYNTAX      HpnicfDot11APReassocStatis2Entry
    MAX-ACCESS  not-accessible
    STATUS      current
    DESCRIPTION
        "Each entry will provide statistic of reassociation with this AP
         because of different reasons."
    INDEX
        {
            hpnicfDot11CurAPID
        }
    ::= { hpnicfDot11APReassocStatis2Table 1 }

HpnicfDot11APReassocStatis2Entry ::= SEQUENCE
    {
        hpnicfDot11APReassocFailStatis2Cnt                 Counter32
    }

hpnicfDot11APReassocFailStatis2Cnt OBJECT-TYPE
    SYNTAX      Counter32
    MAX-ACCESS  read-only
    STATUS      current
    DESCRIPTION
        "This object represents the count of reassociation failure because of
         lack of resource."
    ::= { hpnicfDot11APReassocStatis2Entry 1 }

-- *****************************************************************************
-- *  End of hpnicfDot11APReassocStatis2Table Definition
-- *****************************************************************************

-- *****************************************************************************
-- *  hpnicfDot11TrafficTable Definition
-- *****************************************************************************
hpnicfDot11TrafficTable OBJECT-TYPE
    SYNTAX      SEQUENCE OF HpnicfDot11TrafficEntry
    MAX-ACCESS  not-accessible
    STATUS      current
    DESCRIPTION
        "The table describes user's traffic based on ssid"
    ::= { hpnicfDot11APStatisGroup 27 }

hpnicfDot11TrafficEntry OBJECT-TYPE
    SYNTAX      HpnicfDot11TrafficEntry
    MAX-ACCESS  not-accessible
    STATUS      current
    DESCRIPTION
        "Each entry contains the traffc information of a ssid."
    INDEX
        {
            hpnicfDot11SSIDIndex
        }
    ::= { hpnicfDot11TrafficTable 1 }

HpnicfDot11TrafficEntry ::= SEQUENCE
    {
        hpnicfDot11SSIDIndex             OCTET STRING,
        hpnicfDot11UpPacketNumber        Counter64,
        hpnicfDot11UpByteNumber          Counter64,
        hpnicfDot11DownPacketNumber      Counter64,
        hpnicfDot11DownByteNumber        Counter64
    }

hpnicfDot11SSIDIndex OBJECT-TYPE
    SYNTAX      OCTET STRING
    MAX-ACCESS  not-accessible
    STATUS      current
    DESCRIPTION
        "Represents the SSID."
    ::= { hpnicfDot11TrafficEntry 1 }

hpnicfDot11UpPacketNumber OBJECT-TYPE
    SYNTAX      Counter64
    MAX-ACCESS  read-only
    STATUS      current
    DESCRIPTION
        "Represents the packet count of up link."
    ::= { hpnicfDot11TrafficEntry 2 }

hpnicfDot11UpByteNumber OBJECT-TYPE
    SYNTAX      Counter64
    MAX-ACCESS  read-only
    STATUS      current
    DESCRIPTION
        "Represents the byte count of up link."
    ::= { hpnicfDot11TrafficEntry 3 }

hpnicfDot11DownPacketNumber OBJECT-TYPE
    SYNTAX      Counter64
    MAX-ACCESS  read-only
    STATUS      current
    DESCRIPTION
        "Represents the packet count of down link."
    ::= { hpnicfDot11TrafficEntry 4 }

hpnicfDot11DownByteNumber OBJECT-TYPE
    SYNTAX      Counter64
    MAX-ACCESS  read-only
    STATUS      current
    DESCRIPTION
        "Represents the byte count of down link."
    ::= { hpnicfDot11TrafficEntry 5 }

-- *****************************************************************************
-- *  End of hpnicfDot11TrafficTable Definition
-- *****************************************************************************

-- *****************************************************************************
-- *  hpnicfDot11APEchoStatisTable Definition
-- *****************************************************************************
hpnicfDot11APEchoStatisTable OBJECT-TYPE
    SYNTAX      SEQUENCE OF HpnicfDot11APEchoInfoStatisEntry
    MAX-ACCESS  not-accessible
    STATUS      current
    DESCRIPTION
        "The table will provide the Echo statistic of this AP."
    ::= { hpnicfDot11APStatisGroup 28 }

hpnicfDot11APEchoInfoStatisEntry OBJECT-TYPE
    SYNTAX      HpnicfDot11APEchoInfoStatisEntry
    MAX-ACCESS  not-accessible
    STATUS      current
    DESCRIPTION
        "Each entry of the table will provide the Echo statistic
        of this AP."
    INDEX
        {
            hpnicfDot11CurAPID
        }
    ::= { hpnicfDot11APEchoStatisTable 1 }

HpnicfDot11APEchoInfoStatisEntry ::= SEQUENCE
    {
        hpnicfDot11APEchoAvgDelay                 Integer32,
        hpnicfDot11APEchoRequestCnt               Counter64,
        hpnicfDot11APEchoRespLossCnt              Counter64
    }

hpnicfDot11APEchoAvgDelay OBJECT-TYPE
    SYNTAX      Integer32
    UNITS       "millisecond"
    MAX-ACCESS  read-only
    STATUS      current
    DESCRIPTION
        "This object represents the average time delay of heart beat in this AP."
    ::= { hpnicfDot11APEchoInfoStatisEntry 1 }

hpnicfDot11APEchoRequestCnt OBJECT-TYPE
    SYNTAX      Counter64
    MAX-ACCESS  read-only
    STATUS      current
    DESCRIPTION
        "This object represents the count of echo request in this AP."
    ::= { hpnicfDot11APEchoInfoStatisEntry 2 }

hpnicfDot11APEchoRespLossCnt OBJECT-TYPE
    SYNTAX      Counter64
    MAX-ACCESS  read-only
    STATUS      current
    DESCRIPTION
        "This object represents the loss count of echo response in this AP."
    ::= { hpnicfDot11APEchoInfoStatisEntry 3 }

-- *****************************************************************************
-- *  End of hpnicfDot11APEchoStatisTable Definition
-- *****************************************************************************

-- *****************************************************************************
-- *  hpnicfDot11APUserSecAuthTypeStatisTable Definition
-- *****************************************************************************
hpnicfDot11APUserSecAuthTypeStatisTable OBJECT-TYPE
    SYNTAX      SEQUENCE OF HpnicfDot11APUserSecAuthTypeStatisEntry
    MAX-ACCESS  not-accessible
    STATUS      current
    DESCRIPTION
        "The table will provide the user authentication type statistic for this AP."
    ::= { hpnicfDot11APStatisGroup 29 }

hpnicfDot11APUserSecAuthTypeStatisEntry OBJECT-TYPE
    SYNTAX      HpnicfDot11APUserSecAuthTypeStatisEntry
    MAX-ACCESS  not-accessible
    STATUS      current
    DESCRIPTION
        "Each entry of the table will provide the user authentication type statistic
        for this AP."
    INDEX
        {
            hpnicfDot11CurAPID
        }
    ::= { hpnicfDot11APUserSecAuthTypeStatisTable 1 }

HpnicfDot11APUserSecAuthTypeStatisEntry ::= SEQUENCE
    {
        hpnicfDot11APPortalOnlineUserNum          Integer32,
        hpnicfDot11APAuthFreeOnlineUserNum        Integer32,
        hpnicfDot11APAssocAuthOnlineUserNum       Integer32,
        hpnicfDot11APMacAuthOnlineUserNum         Integer32,
        hpnicfDot11APAllPortalUserOnlineTime      TimeTicks,
        hpnicfDot11APAllAuthFreeUserOnlineTime    TimeTicks,
        hpnicfDot11APAllAssocAuthUserOnlineTime   TimeTicks,
        hpnicfDot11APAllMacAuthUserOnlineTime     TimeTicks,
        hpnicfDot11APPortalUserLostCnntCnt        Counter32,
        hpnicfDot11APAuthFreeUserLostCnntCnt      Counter32,
        hpnicfDot11APAssocAuthUserLostCnntCnt     Counter32,
        hpnicfDot11APMacAuthUserLostCnntCnt       Counter32,
        hpnicfDot11APPortalAuthReqCnt             Counter32,
        hpnicfDot11APAssocAuthReqCnt              Counter32,
        hpnicfDot11APMacAuthReqCnt                Counter32,
        hpnicfDot11APPortalAuthSucCnt             Counter32,
        hpnicfDot11APAssocAuthSucCnt              Counter32,
        hpnicfDot11APMacAuthSucCnt                Counter32,
        hpnicfDot11APPortalAuthReqFailCnt         Counter32,
        hpnicfDot11APAssocAuthReqFailCnt          Counter32,
        hpnicfDot11APMacAuthReqFailCnt            Counter32,
        hpnicfDot11APAutoAuthOnlineUserNumCM      Integer32,
        hpnicfDot11APAllAutoAuthUserOnlineTimeCM  TimeTicks,
        hpnicfDot11APAutoAuthUserLostCnntCntCM    Counter32,
        hpnicfDot11APAutoAuthReqCntCM             Counter32,
        hpnicfDot11APAutoAuthSucCntCM             Counter32,
        hpnicfDot11APAutoAuthReqFailCntCM         Counter32
    }

hpnicfDot11APPortalOnlineUserNum OBJECT-TYPE
    SYNTAX      Integer32
    MAX-ACCESS  read-only
    STATUS      current
    DESCRIPTION
        "Represents the number of online portal users of this AP, including
        MAC-trigger and IMSIAuth users."
    ::= { hpnicfDot11APUserSecAuthTypeStatisEntry 1 }

hpnicfDot11APAuthFreeOnlineUserNum OBJECT-TYPE
    SYNTAX      Integer32
    MAX-ACCESS  read-only
    STATUS      current
    DESCRIPTION
        "Represents the online number of user free authenticated with this AP."
    ::= { hpnicfDot11APUserSecAuthTypeStatisEntry 2 }

hpnicfDot11APAssocAuthOnlineUserNum OBJECT-TYPE
    SYNTAX      Integer32
    MAX-ACCESS  read-only
    STATUS      current
    DESCRIPTION
        "Represents the number of online users authenticated by associated
        authentication with this AP, excluding AutoAuth users."
    ::= { hpnicfDot11APUserSecAuthTypeStatisEntry 3 }

hpnicfDot11APMacAuthOnlineUserNum OBJECT-TYPE
    SYNTAX      Integer32
    MAX-ACCESS  read-only
    STATUS      current
    DESCRIPTION
        "Represents the online number of user MAC address authenticated with this AP."
    ::= { hpnicfDot11APUserSecAuthTypeStatisEntry 4 }

hpnicfDot11APAllPortalUserOnlineTime OBJECT-TYPE
    SYNTAX      TimeTicks
    MAX-ACCESS  read-only
    STATUS      current
    DESCRIPTION
        "Represents the online time of all user portal authenticated with this AP."
    ::= { hpnicfDot11APUserSecAuthTypeStatisEntry 5 }

hpnicfDot11APAllAuthFreeUserOnlineTime OBJECT-TYPE
    SYNTAX      TimeTicks
    MAX-ACCESS  read-only
    STATUS      current
    DESCRIPTION
        "Represents the online time of all user free authenticated with this AP."
    ::= { hpnicfDot11APUserSecAuthTypeStatisEntry 6 }

hpnicfDot11APAllAssocAuthUserOnlineTime OBJECT-TYPE
    SYNTAX      TimeTicks
    MAX-ACCESS  read-only
    STATUS      current
    DESCRIPTION
        "Represents the online time of all user associated authenticated with this AP."
    ::= { hpnicfDot11APUserSecAuthTypeStatisEntry 7 }

hpnicfDot11APAllMacAuthUserOnlineTime OBJECT-TYPE
    SYNTAX      TimeTicks
    MAX-ACCESS  read-only
    STATUS      current
    DESCRIPTION
        "Represents the online time of all user MAC address authenticated with this AP."
    ::= { hpnicfDot11APUserSecAuthTypeStatisEntry 8 }

hpnicfDot11APPortalUserLostCnntCnt OBJECT-TYPE
    SYNTAX      Counter32
    MAX-ACCESS  read-only
    STATUS      current
    DESCRIPTION
        "Represents the lost connective count of user portal authenticated with this AP."
    ::= { hpnicfDot11APUserSecAuthTypeStatisEntry 9 }

hpnicfDot11APAuthFreeUserLostCnntCnt OBJECT-TYPE
    SYNTAX      Counter32
    MAX-ACCESS  read-only
    STATUS      current
    DESCRIPTION
        "Represents the lost connective count of user free authenticated with this AP."
    ::= { hpnicfDot11APUserSecAuthTypeStatisEntry 10 }

hpnicfDot11APAssocAuthUserLostCnntCnt OBJECT-TYPE
    SYNTAX      Counter32
    MAX-ACCESS  read-only
    STATUS      current
    DESCRIPTION
        "Represents the lost connective count of user associate authenticated with this AP."
    ::= { hpnicfDot11APUserSecAuthTypeStatisEntry 11 }

hpnicfDot11APMacAuthUserLostCnntCnt OBJECT-TYPE
    SYNTAX      Counter32
    MAX-ACCESS  read-only
    STATUS      current
    DESCRIPTION
        "Represents the lost connective count of user MAC address authenticated with this AP."
    ::= { hpnicfDot11APUserSecAuthTypeStatisEntry 12 }

hpnicfDot11APPortalAuthReqCnt OBJECT-TYPE
    SYNTAX      Counter32
    MAX-ACCESS  read-only
    STATUS      current
    DESCRIPTION
        "Represents the request count of user portal authenticated with this AP."
    ::= { hpnicfDot11APUserSecAuthTypeStatisEntry 13 }

hpnicfDot11APAssocAuthReqCnt OBJECT-TYPE
    SYNTAX      Counter32
    MAX-ACCESS  read-only
    STATUS      current
    DESCRIPTION
        "Represents the request count of user associate authenticated with this AP."
    ::= { hpnicfDot11APUserSecAuthTypeStatisEntry 14 }

hpnicfDot11APMacAuthReqCnt OBJECT-TYPE
    SYNTAX      Counter32
    MAX-ACCESS  read-only
    STATUS      current
    DESCRIPTION
        "Represents the request count of user MAC address authenticated with this AP."
    ::= { hpnicfDot11APUserSecAuthTypeStatisEntry 15 }

hpnicfDot11APPortalAuthSucCnt OBJECT-TYPE
    SYNTAX      Counter32
    MAX-ACCESS  read-only
    STATUS      current
    DESCRIPTION
        "Represents the count of user portal authenticated successed with this AP."
    ::= { hpnicfDot11APUserSecAuthTypeStatisEntry 16 }

hpnicfDot11APAssocAuthSucCnt OBJECT-TYPE
    SYNTAX      Counter32
    MAX-ACCESS  read-only
    STATUS      current
    DESCRIPTION
        "Represents the count of user associate authenticated successed with this AP."
    ::= { hpnicfDot11APUserSecAuthTypeStatisEntry 17 }

hpnicfDot11APMacAuthSucCnt OBJECT-TYPE
    SYNTAX      Counter32
    MAX-ACCESS  read-only
    STATUS      current
    DESCRIPTION
        "Represents the count of user MAC address authenticated successed with this AP."
    ::= { hpnicfDot11APUserSecAuthTypeStatisEntry 18 }

hpnicfDot11APPortalAuthReqFailCnt OBJECT-TYPE
    SYNTAX      Counter32
    MAX-ACCESS  read-only
    STATUS      current
    DESCRIPTION
        "Represents the count of user portal authenticated failed with this AP."
    ::= { hpnicfDot11APUserSecAuthTypeStatisEntry 19 }

hpnicfDot11APAssocAuthReqFailCnt OBJECT-TYPE
    SYNTAX      Counter32
    MAX-ACCESS  read-only
    STATUS      current
    DESCRIPTION
        "Represents the count of user associate authenticated failed with this AP."
    ::= { hpnicfDot11APUserSecAuthTypeStatisEntry 20 }

hpnicfDot11APMacAuthReqFailCnt OBJECT-TYPE
    SYNTAX      Counter32
    MAX-ACCESS  read-only
    STATUS      current
    DESCRIPTION
        "Represents the count of user MAC address authenticated failed with this AP."
    ::= { hpnicfDot11APUserSecAuthTypeStatisEntry 21 }

hpnicfDot11APAutoAuthOnlineUserNumCM OBJECT-TYPE
    SYNTAX      Integer32
    MAX-ACCESS  read-only
    STATUS      current
    DESCRIPTION
        "Represents the number of online users authenticated by auto authentication
        with this AP."
    ::= { hpnicfDot11APUserSecAuthTypeStatisEntry 22 }

hpnicfDot11APAllAutoAuthUserOnlineTimeCM OBJECT-TYPE
    SYNTAX      TimeTicks
    MAX-ACCESS  read-only
    STATUS      current
    DESCRIPTION
        "Represents the online time of users authenticated by auto authentication
        with this AP."
    ::= { hpnicfDot11APUserSecAuthTypeStatisEntry 23 }

hpnicfDot11APAutoAuthUserLostCnntCntCM OBJECT-TYPE
    SYNTAX      Counter32
    MAX-ACCESS  read-only
    STATUS      current
    DESCRIPTION
        "Represents the disconnection count of AutoAuth users."
    ::= { hpnicfDot11APUserSecAuthTypeStatisEntry 24 }

hpnicfDot11APAutoAuthReqCntCM OBJECT-TYPE
    SYNTAX      Counter32
    MAX-ACCESS  read-only
    STATUS      current
    DESCRIPTION
        "Represents the count of AutoAuth requests with this AP."
    ::= { hpnicfDot11APUserSecAuthTypeStatisEntry 25 }

hpnicfDot11APAutoAuthSucCntCM OBJECT-TYPE
    SYNTAX      Counter32
    MAX-ACCESS  read-only
    STATUS      current
    DESCRIPTION
        "Represents the count of successful AutoAuth authentications with this AP."
    ::= { hpnicfDot11APUserSecAuthTypeStatisEntry 26 }

hpnicfDot11APAutoAuthReqFailCntCM OBJECT-TYPE
    SYNTAX      Counter32
    MAX-ACCESS  read-only
    STATUS      current
    DESCRIPTION
        "Represents the count of failed AutoAuth requests with this AP."
    ::= { hpnicfDot11APUserSecAuthTypeStatisEntry 27 }

-- *****************************************************************************
-- *  End of hpnicfDot11APUserSecAuthTypeStatisTable Definition
-- *****************************************************************************

-- *****************************************************************************
-- *  hpnicfDot11RadioRxStatis64Table Definition
-- *****************************************************************************
hpnicfDot11RadioRxStatis64Table OBJECT-TYPE
    SYNTAX      SEQUENCE OF HpnicfDot11RadioRxStatis64Entry
    MAX-ACCESS  not-accessible
    STATUS      current
    DESCRIPTION
        "The table will provide the reception statistic for a specific
        radio of AP."
    ::= { hpnicfDot11APStatisGroup 30 }

hpnicfDot11RadioRxStatis64Entry OBJECT-TYPE
    SYNTAX      HpnicfDot11RadioRxStatis64Entry
    MAX-ACCESS  not-accessible
    STATUS      current
    DESCRIPTION
        "Each entry of the table will provide the reception statistic
        data for each radio of a specific AP."
    INDEX
        {
            hpnicfDot11CurAPID,
            hpnicfDot11RadioID
        }
    ::= { hpnicfDot11RadioRxStatis64Table 1 }

HpnicfDot11RadioRxStatis64Entry ::= SEQUENCE
    {
        hpnicfDot11Rx64FrameDupCnt          Counter64,
        hpnicfDot11Rx64FrameCnt             Counter64,
        hpnicfDot11Rx64UcastFrameCnt        Counter64,
        hpnicfDot11Rx64BcastFrameCnt        Counter64,
        hpnicfDot11Rx64McastFrameCnt        Counter64,
        hpnicfDot11Rx64DiscardFrameCnt      Counter64,
        hpnicfDot11Rx64FragCnt              Counter64,
        hpnicfDot11Rx64FcsErrCnt            Counter64,
        hpnicfDot11Rx64FrameBytes           Counter64,
        hpnicfDot11Rx64UcastFrameBytes      Counter64,
        hpnicfDot11Rx64BcastFrameBytes      Counter64,
        hpnicfDot11Rx64McastFrameBytes      Counter64,
        hpnicfDot11Rx64DiscardFrameBytes    Counter64,
        hpnicfDot11Rx64MgmtFrameCnt         Counter64,
        hpnicfDot11Rx64CtrlFrameCnt         Counter64,
        hpnicfDot11Rx64DataFrameCnt         Counter64,
        hpnicfDot11Rx64DecryptErrorCnt      Counter64,
        hpnicfDot11Rx64AuthenFrameCnt       Counter64,
        hpnicfDot11Rx64AssociateFrameCnt    Counter64,
        hpnicfDot11Rx64PhyErrorCnt          Counter64,
        hpnicfDot11Rx64MICErrorCnt          Counter64,
        hpnicfDot11Rx64DataFrameBytes       Counter64,
        hpnicfDot11Rx64PayloadBytes         Counter64,
        hpnicfDot11Rx64DataFrameBytesCM     Counter64
    }

hpnicfDot11Rx64FrameDupCnt OBJECT-TYPE
    SYNTAX      Counter64
    MAX-ACCESS  read-only
    STATUS      current
    DESCRIPTION
        "Represents the number of duplicate frames reception."
    ::= { hpnicfDot11RadioRxStatis64Entry 1 }

hpnicfDot11Rx64FrameCnt OBJECT-TYPE
    SYNTAX      Counter64
    MAX-ACCESS  read-only
    STATUS      current
    DESCRIPTION
        "Represents the number of frames reception."
    ::= { hpnicfDot11RadioRxStatis64Entry 2 }

hpnicfDot11Rx64UcastFrameCnt OBJECT-TYPE
    SYNTAX      Counter64
    MAX-ACCESS  read-only
    STATUS      current
    DESCRIPTION
        "Represents the number of unicast frames reception."
    ::= { hpnicfDot11RadioRxStatis64Entry 3 }

hpnicfDot11Rx64BcastFrameCnt OBJECT-TYPE
    SYNTAX      Counter64
    MAX-ACCESS  read-only
    STATUS      current
    DESCRIPTION
        "Represents the number of broadcast frames reception."
    ::= { hpnicfDot11RadioRxStatis64Entry 4 }

hpnicfDot11Rx64McastFrameCnt OBJECT-TYPE
    SYNTAX      Counter64
    MAX-ACCESS  read-only
    STATUS      current
    DESCRIPTION
        "Represents the number of multicast frames reception."
    ::= { hpnicfDot11RadioRxStatis64Entry 5 }

hpnicfDot11Rx64DiscardFrameCnt OBJECT-TYPE
    SYNTAX      Counter64
    MAX-ACCESS  read-only
    STATUS      current
    DESCRIPTION
        "Represents the number of discarded frames reception."
    ::= { hpnicfDot11RadioRxStatis64Entry 6 }

hpnicfDot11Rx64FragCnt OBJECT-TYPE
    SYNTAX      Counter64
    MAX-ACCESS  read-only
    STATUS      current
    DESCRIPTION
        "Represents the number of frame fragments reception."
    ::= { hpnicfDot11RadioRxStatis64Entry 7 }

hpnicfDot11Rx64FcsErrCnt OBJECT-TYPE
    SYNTAX      Counter64
    MAX-ACCESS  read-only
    STATUS      current
    DESCRIPTION
        "Represents the number of FCS error frames reception."
    ::= { hpnicfDot11RadioRxStatis64Entry 8 }

hpnicfDot11Rx64FrameBytes OBJECT-TYPE
    SYNTAX      Counter64
    MAX-ACCESS  read-only
    STATUS      current
    DESCRIPTION
        "Represents the bytes of frames reception."
    ::= { hpnicfDot11RadioRxStatis64Entry 9 }

hpnicfDot11Rx64UcastFrameBytes OBJECT-TYPE
    SYNTAX      Counter64
    MAX-ACCESS  read-only
    STATUS      current
    DESCRIPTION
        "Represents the bytes of unicast frames reception."
    ::= { hpnicfDot11RadioRxStatis64Entry 10 }

hpnicfDot11Rx64BcastFrameBytes OBJECT-TYPE
    SYNTAX      Counter64
    MAX-ACCESS  read-only
    STATUS      current
    DESCRIPTION
        "Represents the bytes of broadcast frames reception."
    ::= { hpnicfDot11RadioRxStatis64Entry 11 }

hpnicfDot11Rx64McastFrameBytes OBJECT-TYPE
    SYNTAX      Counter64
    MAX-ACCESS  read-only
    STATUS      current
    DESCRIPTION
        "Represents the bytes of multicast frames reception."
    ::= { hpnicfDot11RadioRxStatis64Entry 12 }

hpnicfDot11Rx64DiscardFrameBytes OBJECT-TYPE
    SYNTAX      Counter64
    MAX-ACCESS  read-only
    STATUS      current
    DESCRIPTION
        "Represents the bytes of discarded frames reception."
    ::= { hpnicfDot11RadioRxStatis64Entry 13 }

hpnicfDot11Rx64MgmtFrameCnt OBJECT-TYPE
    SYNTAX      Counter64
    MAX-ACCESS  read-only
    STATUS      current
    DESCRIPTION
        "Represents the number of management frames reception."
    ::= { hpnicfDot11RadioRxStatis64Entry 14 }

hpnicfDot11Rx64CtrlFrameCnt OBJECT-TYPE
    SYNTAX      Counter64
    MAX-ACCESS  read-only
    STATUS      current
    DESCRIPTION
        "Represents the number of control frames reception."
    ::= { hpnicfDot11RadioRxStatis64Entry 15 }

hpnicfDot11Rx64DataFrameCnt OBJECT-TYPE
    SYNTAX      Counter64
    MAX-ACCESS  read-only
    STATUS      current
    DESCRIPTION
        "Represents the number of data frames reception."
    ::= { hpnicfDot11RadioRxStatis64Entry 16 }

hpnicfDot11Rx64DecryptErrorCnt OBJECT-TYPE
    SYNTAX      Counter64
    MAX-ACCESS  read-only
    STATUS      current
    DESCRIPTION
        "Represents the number of decryption error reception."
    ::= { hpnicfDot11RadioRxStatis64Entry 17 }

hpnicfDot11Rx64AuthenFrameCnt OBJECT-TYPE
    SYNTAX      Counter64
    MAX-ACCESS  read-only
    STATUS      current
    DESCRIPTION
        "Represents the number of authentication frame reception."
    ::= { hpnicfDot11RadioRxStatis64Entry 18 }

hpnicfDot11Rx64AssociateFrameCnt OBJECT-TYPE
    SYNTAX      Counter64
    MAX-ACCESS  read-only
    STATUS      current
    DESCRIPTION
        "Represents the number of associate frame reception."
    ::= { hpnicfDot11RadioRxStatis64Entry 19 }

hpnicfDot11Rx64PhyErrorCnt OBJECT-TYPE
    SYNTAX      Counter64
    MAX-ACCESS  read-only
    STATUS      current
    DESCRIPTION
        "Represents the number of physical error reception."
    ::= { hpnicfDot11RadioRxStatis64Entry 20 }

hpnicfDot11Rx64MICErrorCnt OBJECT-TYPE
    SYNTAX      Counter64
    MAX-ACCESS  read-only
    STATUS      current
    DESCRIPTION
        "Represents the number of MIC verification error reception."
    ::= { hpnicfDot11RadioRxStatis64Entry 21 }

hpnicfDot11Rx64DataFrameBytes OBJECT-TYPE
    SYNTAX      Counter64
    MAX-ACCESS  read-only
    STATUS      current
    DESCRIPTION
        "Represents the bytes of data frames reception."
    ::= { hpnicfDot11RadioRxStatis64Entry 22 }

hpnicfDot11Rx64PayloadBytes OBJECT-TYPE
    SYNTAX      Counter64
    MAX-ACCESS  read-only
    STATUS      current
    DESCRIPTION
        "Represents the payload bytes of data frames reception."
    ::= { hpnicfDot11RadioRxStatis64Entry 23 }

hpnicfDot11Rx64DataFrameBytesCM OBJECT-TYPE
    SYNTAX      Counter64
    MAX-ACCESS  read-only
    STATUS      current
    DESCRIPTION
        "Represents the number of received data frames, excluding retransmitted
        frames."
    ::= { hpnicfDot11RadioRxStatis64Entry 24 }

-- *****************************************************************************
-- *  End of hpnicfDot11RadioRxStatis64Table Definition
-- *****************************************************************************

-- *****************************************************************************
-- *  hpnicfDot11RadioTxStatis64Table Definition
-- *****************************************************************************
hpnicfDot11RadioTxStatis64Table OBJECT-TYPE
    SYNTAX      SEQUENCE OF HpnicfDot11RadioTxStatis64Entry
    MAX-ACCESS  not-accessible
    STATUS      current
    DESCRIPTION
        "The table will provide the transmission statistic for a
        specific radio of AP."
    ::= { hpnicfDot11APStatisGroup 31 }

hpnicfDot11RadioTxStatis64Entry OBJECT-TYPE
    SYNTAX      HpnicfDot11RadioTxStatis64Entry
    MAX-ACCESS  not-accessible
    STATUS      current
    DESCRIPTION
        "Each entry of the table will provide the transmission
        statistic data for each radio of a specific AP."
    INDEX
        {
            hpnicfDot11CurAPID,
            hpnicfDot11RadioID
        }
    ::= { hpnicfDot11RadioTxStatis64Table 1 }

HpnicfDot11RadioTxStatis64Entry ::= SEQUENCE
    {
        hpnicfDot11Tx64FragCnt              Counter64,
        hpnicfDot11Tx64FailedCnt            Counter64,
        hpnicfDot11Tx64RetryCnt             Counter64,
        hpnicfDot11Tx64MultiRetryCnt        Counter64,
        hpnicfDot11Tx64RtsSuccessCnt        Counter64,
        hpnicfDot11Tx64RtsFailCnt           Counter64,
        hpnicfDot11Tx64AckFailCnt           Counter64,
        hpnicfDot11Tx64FrameCnt             Counter64,
        hpnicfDot11Tx64UcastFrameCnt        Counter64,
        hpnicfDot11Tx64BcastFrameCnt        Counter64,
        hpnicfDot11Tx64McastFrameCnt        Counter64,
        hpnicfDot11Tx64DiscardFrameCnt      Counter64,
        hpnicfDot11Tx64FrameBytes           Counter64,
        hpnicfDot11Tx64UcastFrameBytes      Counter64,
        hpnicfDot11Tx64BcastFrameBytes      Counter64,
        hpnicfDot11Tx64McastFrameBytes      Counter64,
        hpnicfDot11Tx64DiscardFrameBytes    Counter64,
        hpnicfDot11Tx64AuthenFrameCnt       Counter64,
        hpnicfDot11Tx64AssociateFrameCnt    Counter64,
        hpnicfDot11Tx64DataFrameCnt         Counter64,
        hpnicfDot11Tx64DataFrameBytes       Counter64,
        hpnicfDot11Tx64MSDUCnt              Counter64,
        hpnicfDot11Tx64DiscardMSDUCnt       Counter64,
        hpnicfDot11Tx64RetryMSDUCnt         Counter64,
        hpnicfDot11Tx64PayloadBytes         Counter64,
        hpnicfDot11Tx64MgtFrameCnt          Counter64,
        hpnicfDot11Tx64CtrlFrameCnt         Counter64,
        hpnicfDot11Tx64MACErrCnt            Counter64,
        hpnicfDot11Tx64ErrFrameCnt          Counter64
    }

hpnicfDot11Tx64FragCnt OBJECT-TYPE
    SYNTAX      Counter64
    MAX-ACCESS  read-only
    STATUS      current
    DESCRIPTION
        "Represents the number of fragmented frames transmission."
    ::= { hpnicfDot11RadioTxStatis64Entry 1 }

hpnicfDot11Tx64FailedCnt OBJECT-TYPE
    SYNTAX      Counter64
    MAX-ACCESS  read-only
    STATUS      current
    DESCRIPTION
        "Represents the number of failures transmission."
    ::= { hpnicfDot11RadioTxStatis64Entry 2 }

hpnicfDot11Tx64RetryCnt OBJECT-TYPE
    SYNTAX      Counter64
    MAX-ACCESS  read-only
    STATUS      current
    DESCRIPTION
        "Represents the number of retries transmission."
    ::= { hpnicfDot11RadioTxStatis64Entry 3 }

hpnicfDot11Tx64MultiRetryCnt OBJECT-TYPE
    SYNTAX      Counter64
    MAX-ACCESS  read-only
    STATUS      current
    DESCRIPTION
        "Represents the number of transmits that required more than
        one retry transmission."
    ::= { hpnicfDot11RadioTxStatis64Entry 4 }

hpnicfDot11Tx64RtsSuccessCnt OBJECT-TYPE
    SYNTAX      Counter64
    MAX-ACCESS  read-only
    STATUS      current
    DESCRIPTION
        "Represents the number of successful RTS (Request to send)
        transmission."
    ::= { hpnicfDot11RadioTxStatis64Entry 5 }

hpnicfDot11Tx64RtsFailCnt OBJECT-TYPE
    SYNTAX      Counter64
    MAX-ACCESS  read-only
    STATUS      current
    DESCRIPTION
        "Represents the number of RTS failures transmission."
    ::= { hpnicfDot11RadioTxStatis64Entry 6 }

hpnicfDot11Tx64AckFailCnt OBJECT-TYPE
    SYNTAX      Counter64
    MAX-ACCESS  read-only
    STATUS      current
    DESCRIPTION
        "Represents the number of acknowledgement failures transmission."
    ::= { hpnicfDot11RadioTxStatis64Entry 7 }

hpnicfDot11Tx64FrameCnt OBJECT-TYPE
    SYNTAX      Counter64
    MAX-ACCESS  read-only
    STATUS      current
    DESCRIPTION
        "Represents the total number of frames transmission."
    ::= { hpnicfDot11RadioTxStatis64Entry 8 }

hpnicfDot11Tx64UcastFrameCnt OBJECT-TYPE
    SYNTAX      Counter64
    MAX-ACCESS  read-only
    STATUS      current
    DESCRIPTION
        "Represents the number of unicast frames transmission."
    ::= { hpnicfDot11RadioTxStatis64Entry 9 }

hpnicfDot11Tx64BcastFrameCnt OBJECT-TYPE
    SYNTAX      Counter64
    MAX-ACCESS  read-only
    STATUS      current
    DESCRIPTION
        "Represents the number of broadcast frames transmission."
    ::= { hpnicfDot11RadioTxStatis64Entry 10 }

hpnicfDot11Tx64McastFrameCnt OBJECT-TYPE
    SYNTAX      Counter64
    MAX-ACCESS  read-only
    STATUS      current
    DESCRIPTION
        "Represents the number of multicast frames transmission."
    ::= { hpnicfDot11RadioTxStatis64Entry 11 }

hpnicfDot11Tx64DiscardFrameCnt OBJECT-TYPE
    SYNTAX      Counter64
    MAX-ACCESS  read-only
    STATUS      current
    DESCRIPTION
        "Represents the number of discarded frames transmission."
    ::= { hpnicfDot11RadioTxStatis64Entry 12 }

hpnicfDot11Tx64FrameBytes OBJECT-TYPE
    SYNTAX      Counter64
    MAX-ACCESS  read-only
    STATUS      current
    DESCRIPTION
        "Represents the total bytes of frames transmission."
    ::= { hpnicfDot11RadioTxStatis64Entry 13 }

hpnicfDot11Tx64UcastFrameBytes OBJECT-TYPE
    SYNTAX      Counter64
    MAX-ACCESS  read-only
    STATUS      current
    DESCRIPTION
        "Represents the bytes of unicast frames transmission."
    ::= { hpnicfDot11RadioTxStatis64Entry 14 }

hpnicfDot11Tx64BcastFrameBytes OBJECT-TYPE
    SYNTAX      Counter64
    MAX-ACCESS  read-only
    STATUS      current
    DESCRIPTION
        "Represents the bytes of broadcast frames transmission."
    ::= { hpnicfDot11RadioTxStatis64Entry 15 }

hpnicfDot11Tx64McastFrameBytes OBJECT-TYPE
    SYNTAX      Counter64
    MAX-ACCESS  read-only
    STATUS      current
    DESCRIPTION
        "Represents the bytes of multicast frames transmission."
    ::= { hpnicfDot11RadioTxStatis64Entry 16 }

hpnicfDot11Tx64DiscardFrameBytes OBJECT-TYPE
    SYNTAX      Counter64
    MAX-ACCESS  read-only
    STATUS      current
    DESCRIPTION
        "Represents the bytes of discard frames transmission."
    ::= { hpnicfDot11RadioTxStatis64Entry 17 }

hpnicfDot11Tx64AuthenFrameCnt OBJECT-TYPE
    SYNTAX      Counter64
    MAX-ACCESS  read-only
    STATUS      current
    DESCRIPTION
        "Represents the number of authentication frame transmission."
    ::= { hpnicfDot11RadioTxStatis64Entry 18 }

hpnicfDot11Tx64AssociateFrameCnt OBJECT-TYPE
    SYNTAX      Counter64
    MAX-ACCESS  read-only
    STATUS      current
    DESCRIPTION
        "Represents the number of associate frame transmission."
    ::= { hpnicfDot11RadioTxStatis64Entry 19 }

hpnicfDot11Tx64DataFrameCnt OBJECT-TYPE
    SYNTAX      Counter64
    MAX-ACCESS  read-only
    STATUS      current
    DESCRIPTION
        "Represents the number of data frame transmission."
    ::= { hpnicfDot11RadioTxStatis64Entry 20 }

hpnicfDot11Tx64DataFrameBytes OBJECT-TYPE
    SYNTAX      Counter64
    MAX-ACCESS  read-only
    STATUS      current
    DESCRIPTION
        "Represents the bytes of data frame transmission."
    ::= { hpnicfDot11RadioTxStatis64Entry 21 }

hpnicfDot11Tx64MSDUCnt OBJECT-TYPE
    SYNTAX      Counter64
    MAX-ACCESS  read-only
    STATUS      current
    DESCRIPTION
        "Represents the total number of MSDU transmission."
    ::= { hpnicfDot11RadioTxStatis64Entry 22 }

hpnicfDot11Tx64DiscardMSDUCnt OBJECT-TYPE
    SYNTAX      Counter64
    MAX-ACCESS  read-only
    STATUS      current
    DESCRIPTION
        "Represents the number of discarded MSDU transmission."
    ::= { hpnicfDot11RadioTxStatis64Entry 23 }

hpnicfDot11Tx64RetryMSDUCnt OBJECT-TYPE
    SYNTAX      Counter64
    MAX-ACCESS  read-only
    STATUS      current
    DESCRIPTION
        "Represents the number of retransfer MSDU transmission."
    ::= { hpnicfDot11RadioTxStatis64Entry 24 }

hpnicfDot11Tx64PayloadBytes OBJECT-TYPE
    SYNTAX      Counter64
    MAX-ACCESS  read-only
    STATUS      current
    DESCRIPTION
        "Represents the payload bytes of data frames transmission."
    ::= { hpnicfDot11RadioTxStatis64Entry 25 }

hpnicfDot11Tx64MgtFrameCnt OBJECT-TYPE
    SYNTAX      Counter64
    MAX-ACCESS  read-only
    STATUS      current
    DESCRIPTION
        "Represents the number of management frames transmission."
    ::= { hpnicfDot11RadioTxStatis64Entry 26 }

hpnicfDot11Tx64CtrlFrameCnt OBJECT-TYPE
    SYNTAX      Counter64
    MAX-ACCESS  read-only
    STATUS      current
    DESCRIPTION
        "Represents the number of control frames transmission."
    ::= { hpnicfDot11RadioTxStatis64Entry 27 }
hpnicfDot11Tx64MACErrCnt OBJECT-TYPE
    SYNTAX      Counter64
    MAX-ACCESS  read-only
    STATUS      current
    DESCRIPTION
        "Represents the number of MAC error frame transmission."
    ::= { hpnicfDot11RadioTxStatis64Entry 28 }

hpnicfDot11Tx64ErrFrameCnt OBJECT-TYPE
    SYNTAX      Counter64
    MAX-ACCESS  read-only
    STATUS      current
    DESCRIPTION
        "Represents the number of error frame transmission."
    ::= { hpnicfDot11RadioTxStatis64Entry 29 }

-- *****************************************************************************
-- *  End of hpnicfDot11RadioTxStatis64Table Definition
-- *****************************************************************************

-- *****************************************************************************
-- *  hpnicfDot11BSSRxStatis64Table Definition
-- *****************************************************************************
hpnicfDot11BSSRxStatis64Table OBJECT-TYPE
    SYNTAX      SEQUENCE OF HpnicfDot11BSSRxStatis64Entry
    MAX-ACCESS  not-accessible
    STATUS      current
    DESCRIPTION
        "The table will provide the reception statistic for a
        specific BSS on a radio."
    ::= { hpnicfDot11APStatisGroup 32 }

hpnicfDot11BSSRxStatis64Entry OBJECT-TYPE
    SYNTAX      HpnicfDot11BSSRxStatis64Entry
    MAX-ACCESS  not-accessible
    STATUS      current
    DESCRIPTION
        "Each entry of the table will provide the reception statistic data for
        each BSS on a specific radio."
    INDEX
        {
            hpnicfDot11CurAPID,
            hpnicfDot11RadioID,
            hpnicfDot11WlanID
        }
    ::= { hpnicfDot11BSSRxStatis64Table 1 }

HpnicfDot11BSSRxStatis64Entry ::= SEQUENCE
    {
        hpnicfDot11BSSRx64FrameCnt             Counter64,
        hpnicfDot11BSSRx64FrameBytes           Counter64,
        hpnicfDot11BSSRx64DataFrameCnt         Counter64,
        hpnicfDot11BSSRx64DataFrameBytes       Counter64,
        hpnicfDot11BSSRx64AssocFrameCnt        Counter64,
        hpnicfDot11BSSRx64PayloadBytes         Counter64,
        hpnicfDot11BSSRx64UniFrameCnt          Counter64,
        hpnicfDot11BSSRx64NonUniFrameCnt       Counter64,
        hpnicfDot11BSSRx64AuthenFrameCnt       Counter64
    }

hpnicfDot11BSSRx64FrameCnt OBJECT-TYPE
    SYNTAX      Counter64
    MAX-ACCESS  read-only
    STATUS      current
    DESCRIPTION
        "Represents the number of frames reception with this BSS."
    ::= { hpnicfDot11BSSRxStatis64Entry 1 }

hpnicfDot11BSSRx64FrameBytes OBJECT-TYPE
    SYNTAX      Counter64
    MAX-ACCESS  read-only
    STATUS      current
    DESCRIPTION
        "Represents the bytes of frames reception with this BSS."
    ::= { hpnicfDot11BSSRxStatis64Entry 2 }

hpnicfDot11BSSRx64DataFrameCnt OBJECT-TYPE
    SYNTAX      Counter64
    MAX-ACCESS  read-only
    STATUS      current
    DESCRIPTION
        "Represents the number of data frames reception with this BSS."
    ::= { hpnicfDot11BSSRxStatis64Entry 3 }

hpnicfDot11BSSRx64DataFrameBytes OBJECT-TYPE
    SYNTAX      Counter64
    MAX-ACCESS  read-only
    STATUS      current
    DESCRIPTION
        "Represents the bytes of data frames reception with this BSS."
    ::= { hpnicfDot11BSSRxStatis64Entry 4 }

hpnicfDot11BSSRx64AssocFrameCnt OBJECT-TYPE
    SYNTAX      Counter64
    MAX-ACCESS  read-only
    STATUS      current
    DESCRIPTION
        "Represents the number of associate frames reception with this BSS."
    ::= { hpnicfDot11BSSRxStatis64Entry 5 }

hpnicfDot11BSSRx64PayloadBytes OBJECT-TYPE
    SYNTAX      Counter64
    MAX-ACCESS  read-only
    STATUS      current
    DESCRIPTION
        "Represents the payload bytes of data frames reception with this BSS."
    ::= { hpnicfDot11BSSRxStatis64Entry 6 }

hpnicfDot11BSSRx64UniFrameCnt OBJECT-TYPE
    SYNTAX      Counter64
    MAX-ACCESS  read-only
    STATUS      current
    DESCRIPTION
        "Represents the number of unicast frames reception with this BSS."
    ::= { hpnicfDot11BSSRxStatis64Entry 7 }

hpnicfDot11BSSRx64NonUniFrameCnt  OBJECT-TYPE
    SYNTAX      Counter64
    MAX-ACCESS  read-only
    STATUS      current
    DESCRIPTION
        "Represents the number of non-unicast frames reception with this BSS."
    ::= { hpnicfDot11BSSRxStatis64Entry 8 }

hpnicfDot11BSSRx64AuthenFrameCnt OBJECT-TYPE
    SYNTAX      Counter64
    MAX-ACCESS  read-only
    STATUS      current
    DESCRIPTION
        "Represents the number of authentication frames reception with this BSS."
    ::= { hpnicfDot11BSSRxStatis64Entry 9 }

-- *****************************************************************************
-- *  End of hpnicfDot11BSSRxStatis64Table Definition
-- *****************************************************************************

-- *****************************************************************************
-- *  hpnicfDot11BSSTxStatis64Table Definition
-- *****************************************************************************
hpnicfDot11BSSTxStatis64Table OBJECT-TYPE
    SYNTAX      SEQUENCE OF HpnicfDot11BSSTxStatis64Entry
    MAX-ACCESS  not-accessible
    STATUS      current
    DESCRIPTION
        "The table will provide the transmission statistic for a
        specific BSS on a radio."
    ::= { hpnicfDot11APStatisGroup 33 }

hpnicfDot11BSSTxStatis64Entry OBJECT-TYPE
    SYNTAX      HpnicfDot11BSSTxStatis64Entry
    MAX-ACCESS  not-accessible
    STATUS      current
    DESCRIPTION
        "Each entry of the table will provide the transmission statistic data for
        each BSS on a specific radio."
    INDEX
        {
            hpnicfDot11CurAPID,
            hpnicfDot11RadioID,
            hpnicfDot11WlanID
        }
    ::= { hpnicfDot11BSSTxStatis64Table 1 }

HpnicfDot11BSSTxStatis64Entry ::= SEQUENCE
    {
        hpnicfDot11BSSTx64FrameCnt             Counter64,
        hpnicfDot11BSSTx64FrameBytes           Counter64,
        hpnicfDot11BSSTx64DataFrameCnt         Counter64,
        hpnicfDot11BSSTx64DataFrameBytes       Counter64,
        hpnicfDot11BSSTx64AssocFrameCnt        Counter64,
        hpnicfDot11BSSTx64PayloadBytes         Counter64,
        hpnicfDot11BSSTx64RetryCnt             Counter64,
        hpnicfDot11BSSTx64UniFrameCnt          Counter64,
        hpnicfDot11BSSTx64NonUniFrameCnt       Counter64,
        hpnicfDot11BSSTx64AuthenFrameCnt       Counter64
    }

hpnicfDot11BSSTx64FrameCnt OBJECT-TYPE
    SYNTAX      Counter64
    MAX-ACCESS  read-only
    STATUS      current
    DESCRIPTION
        "Represents the total number of frames transmission with this BSS."
    ::= { hpnicfDot11BSSTxStatis64Entry 1 }

hpnicfDot11BSSTx64FrameBytes OBJECT-TYPE
    SYNTAX      Counter64
    MAX-ACCESS  read-only
    STATUS      current
    DESCRIPTION
        "Represents the total number of bytes transmission with this BSS."
    ::= { hpnicfDot11BSSTxStatis64Entry 2 }

hpnicfDot11BSSTx64DataFrameCnt OBJECT-TYPE
    SYNTAX      Counter64
    MAX-ACCESS  read-only
    STATUS      current
    DESCRIPTION
        "Represents the number of data frame transmission with this BSS."
    ::= { hpnicfDot11BSSTxStatis64Entry 3 }

hpnicfDot11BSSTx64DataFrameBytes OBJECT-TYPE
    SYNTAX      Counter64
    MAX-ACCESS  read-only
    STATUS      current
    DESCRIPTION
        "Represents the bytes of data frame transmission with this BSS."
    ::= { hpnicfDot11BSSTxStatis64Entry 4 }

hpnicfDot11BSSTx64AssocFrameCnt OBJECT-TYPE
    SYNTAX      Counter64
    MAX-ACCESS  read-only
    STATUS      current
    DESCRIPTION
        "Represents the number of associate frame transmission with this BSS."
    ::= { hpnicfDot11BSSTxStatis64Entry 5 }

hpnicfDot11BSSTx64PayloadBytes OBJECT-TYPE
    SYNTAX      Counter64
    MAX-ACCESS  read-only
    STATUS      current
    DESCRIPTION
        "Represents the payload bytes of data frame transmission with this BSS."
    ::= { hpnicfDot11BSSTxStatis64Entry 6 }

hpnicfDot11BSSTx64RetryCnt   OBJECT-TYPE
    SYNTAX      Counter64
    MAX-ACCESS  read-only
    STATUS      current
    DESCRIPTION
        "Represents the number of bytes retransmitted with this BSS."
    ::= { hpnicfDot11BSSTxStatis64Entry 7 }

hpnicfDot11BSSTx64UniFrameCnt OBJECT-TYPE
    SYNTAX      Counter64
    MAX-ACCESS  read-only
    STATUS      current
    DESCRIPTION
        "Represents the number of unicast frames transmission with this BSS."
    ::= { hpnicfDot11BSSTxStatis64Entry 8 }

hpnicfDot11BSSTx64NonUniFrameCnt OBJECT-TYPE
    SYNTAX      Counter64
    MAX-ACCESS  read-only
    STATUS      current
    DESCRIPTION
        "Represents the number of non-unicast frames transmission with this BSS."
    ::= { hpnicfDot11BSSTxStatis64Entry 9 }

hpnicfDot11BSSTx64AuthenFrameCnt OBJECT-TYPE
    SYNTAX      Counter64
    MAX-ACCESS  read-only
    STATUS      current
    DESCRIPTION
        "Represents the number of authentication frames transmission with this BSS."
    ::= { hpnicfDot11BSSTxStatis64Entry 10 }

-- *****************************************************************************
-- *  End of hpnicfDot11BSSTxStatis64Table Definition
-- *****************************************************************************

-- *****************************************************************************
-- *  hpnicfDot11APPacketMCSRateStatis2Table Definition
-- *****************************************************************************
hpnicfDot11APPacketMCSRateStatis2Table  OBJECT-TYPE
    SYNTAX        SEQUENCE OF HpnicfDot11APPacketMCSRateStatis2Entry
    MAX-ACCESS    not-accessible
    STATUS        current
    DESCRIPTION
        "This table provides packet statistics based on MCS rate."
    ::= { hpnicfDot11APStatisGroup 34 }

hpnicfDot11APPacketMCSRateStatis2Entry  OBJECT-TYPE
    SYNTAX        HpnicfDot11APPacketMCSRateStatis2Entry
    MAX-ACCESS    not-accessible
    STATUS        current
    DESCRIPTION
        "Each entry provides packet statistics based on MCS rate for each radio
        of a specific AP."
    INDEX
        {
            hpnicfDot11CurAPID,
            hpnicfDot11RadioID,
            hpnicfDot11APPacketMCS2Rate
        }
    ::= { hpnicfDot11APPacketMCSRateStatis2Table 1 }

HpnicfDot11APPacketMCSRateStatis2Entry  ::=SEQUENCE
    {
        hpnicfDot11APPacketMCS2Rate          Integer32,
        hpnicfDot11APRXPacketMCSRate2Count   Counter64,
        hpnicfDot11APTXPacketMCSRate2Count   Counter64
    }

hpnicfDot11APPacketMCS2Rate    OBJECT-TYPE
    SYNTAX        Integer32 (1..2000000000)
    MAX-ACCESS    not-accessible
    STATUS        current
    DESCRIPTION
        "Represents data transmission rate(Tenfold as actual rate)."
    ::= { hpnicfDot11APPacketMCSRateStatis2Entry 1 }

hpnicfDot11APRXPacketMCSRate2Count    OBJECT-TYPE
    SYNTAX        Counter64
    MAX-ACCESS    read-only
    STATUS        current
    DESCRIPTION
        "Represents the count of packets received based on data transmission rate."
    ::= { hpnicfDot11APPacketMCSRateStatis2Entry 2 }

hpnicfDot11APTXPacketMCSRate2Count    OBJECT-TYPE
    SYNTAX        Counter64
    MAX-ACCESS    read-only
    STATUS        current
    DESCRIPTION
        "Represents the count of packets transmitted base on data transmission rate."
    ::= { hpnicfDot11APPacketMCSRateStatis2Entry 3 }

-- *****************************************************************************
-- *  End of hpnicfDot11APPacketMcsRateStatis2Table Definition
-- *****************************************************************************

-- *****************************************************************************
-- *  hpnicfDot11APUserSecAuthStatisCMTable Definition
-- *****************************************************************************
hpnicfDot11APUserSecAuthStatisCMTable OBJECT-TYPE
    SYNTAX      SEQUENCE OF HpnicfDot11APUserSecAuthStatisCMEntry
    MAX-ACCESS  not-accessible
    STATUS      current
    DESCRIPTION
        "The table provides the user authentication statistics."
    ::= { hpnicfDot11APStatisGroup 35 }

hpnicfDot11APUserSecAuthStatisCMEntry OBJECT-TYPE
    SYNTAX      HpnicfDot11APUserSecAuthStatisCMEntry
    MAX-ACCESS  not-accessible
    STATUS      current
    DESCRIPTION
        "Each entry of the table provides the user authentication statistics
        of AP."
    INDEX
        {
            hpnicfDot11CurAPID,
            hpnicfDot11RadioID,
            hpnicfDot11WlanID
       }
    ::= { hpnicfDot11APUserSecAuthStatisCMTable 1 }

HpnicfDot11APUserSecAuthStatisCMEntry ::= SEQUENCE
    {
        hpnicfDot11APUserConnFailCntCM              Counter32,
        hpnicfDot11APUserAuthReqCntCM               Counter32,
        hpnicfDot11APUserAuthSuccCntCM              Counter32,
        hpnicfDot11APUserAuthFailCntCM              Counter32,
        hpnicfDot11AllUserOnlineTimeCM              TimeTicks
    }

hpnicfDot11APUserConnFailCntCM OBJECT-TYPE
    SYNTAX      Counter32
    MAX-ACCESS  read-only
    STATUS      current
    DESCRIPTION
        "Represents the failed connection count of users with this AP."
    ::= { hpnicfDot11APUserSecAuthStatisCMEntry 1 }

hpnicfDot11APUserAuthReqCntCM OBJECT-TYPE
    SYNTAX      Counter32
    MAX-ACCESS  read-only
    STATUS      current
    DESCRIPTION
        "Represents the total number of user authentication requests with this AP."
    ::= { hpnicfDot11APUserSecAuthStatisCMEntry 2 }

hpnicfDot11APUserAuthSuccCntCM OBJECT-TYPE
    SYNTAX      Counter32
    MAX-ACCESS  read-only
    STATUS      current
    DESCRIPTION
        "Represents the total number of successful user authentications with this AP."
    ::= { hpnicfDot11APUserSecAuthStatisCMEntry 3 }

hpnicfDot11APUserAuthFailCntCM OBJECT-TYPE
    SYNTAX      Counter32
    MAX-ACCESS  read-only
    STATUS      current
    DESCRIPTION
        "Represents the total number of failed user authentications with this AP."
    ::= { hpnicfDot11APUserSecAuthStatisCMEntry 4 }

hpnicfDot11AllUserOnlineTimeCM OBJECT-TYPE
    SYNTAX      TimeTicks
    MAX-ACCESS  read-only
    STATUS      current
    DESCRIPTION
        "Represents the online time of all users with this AP."
    ::= { hpnicfDot11APUserSecAuthStatisCMEntry 5 }

-- *****************************************************************************
-- *  End of hpnicfDot11APUserSecAuthStatisCMTable Definition
-- *****************************************************************************

-- *****************************************************************************
-- *  AP Management Notifications Definition
-- *****************************************************************************
-- AP Management Notification

        hpnicfDot11APMtTraps OBJECT IDENTIFIER
    ::= { hpnicfDot11APMtNotifyGroup 0 }

hpnicfDot11APMtWorkModeChgTrap NOTIFICATION-TYPE
    OBJECTS
        {
            hpnicfDot11APID,
            hpnicfDot11APChgWorkMode,
            hpnicfDot11APMtTrapAPMacAddress
        }
    STATUS      current
    DESCRIPTION
        "The notification will be sent when AP changes the work mode, and
         hpnicfDot11APWorkMode suggests which work mode will be used by AP."
    ::= { hpnicfDot11APMtTraps 1 }

hpnicfDot11APMtCfgErrorTrap NOTIFICATION-TYPE
    OBJECTS
        {
            hpnicfDot11APID,
            hpnicfDot11RadioID,
            hpnicfDot11APMtTrapCfgErrReason
        }
    STATUS      current
    DESCRIPTION
        "The notification will represent errors caused by the
        configuration operation of AP."
    ::= { hpnicfDot11APMtTraps 2 }

hpnicfDot11APMtRadioFailTrap NOTIFICATION-TYPE
    OBJECTS
        {
            hpnicfDot11APID,
            hpnicfDot11RadioID,
            hpnicfDot11APMtTrapRadioFailReason
        }
    STATUS      current
    DESCRIPTION
        "The notification will notify which the operational status
        of radio becomes down."
    ::= { hpnicfDot11APMtTraps 3 }

hpnicfDot11APMtRadioFailRecoverTrap NOTIFICATION-TYPE
    OBJECTS
        {
            hpnicfDot11APID,
            hpnicfDot11RadioID
        }
    STATUS      current
    DESCRIPTION
        "The notification will notify the operational status of which radio
        becomes up again."
    ::= { hpnicfDot11APMtTraps 4 }

hpnicfDot11APMtRdoChanlChgTrap NOTIFICATION-TYPE
    OBJECTS
        {
            hpnicfDot11APID,
            hpnicfDot11RadioID,
            hpnicfDot11APChannelChgMode,
            hpnicfDot11APMtTrapOldChannel,
            hpnicfDot11APMtTrapNewChannel,
            hpnicfDot11APMtChanlChgCount,
            hpnicfDot11APMtTrapAPMacAddress
        }
    STATUS      current
    DESCRIPTION
        "The notification will represent which radio changes the channel."
    ::= { hpnicfDot11APMtTraps 5 }

hpnicfDot11APMtTimeSynFail NOTIFICATION-TYPE
    OBJECTS
        {
            hpnicfDot11APID
        }
    STATUS      current
    DESCRIPTION
        "The notification will be sent when AC and AP failed to
        synchronize their time."
    ::= { hpnicfDot11APMtTraps 6 }

hpnicfDot11APMtChlIntfDetected NOTIFICATION-TYPE
    OBJECTS
        {
            hpnicfDot11Channel
        }
    STATUS      current
    DESCRIPTION
        "The notification will be sent when some ambient device interferes with
        current channel."
    ::= { hpnicfDot11APMtTraps 7 }

hpnicfDot11APMtIntfAPDetected NOTIFICATION-TYPE
    OBJECTS
        {
            hpnicfDot11Channel,
            hpnicfDot11APIntfDevMACAddress
        }
    STATUS current
    DESCRIPTION
        "The notification will be sent when some ambient AP interferes with
        current channel."
    ::= { hpnicfDot11APMtTraps 8 }

hpnicfDot11APMtIntfStaDetected NOTIFICATION-TYPE
    OBJECTS
        {
            hpnicfDot11Channel,
            hpnicfDot11APIntfDevMACAddress
        }
    STATUS current
    DESCRIPTION
        "The notification will be sent when some ambient station interferes with
        current channel."
    ::= { hpnicfDot11APMtTraps 9 }

hpnicfDot11APMtIPChange NOTIFICATION-TYPE
    OBJECTS
        {
            hpnicfDot11APIPAddress,
            hpnicfDot11APMtTrapOldIPAddr
        }
    STATUS current
    DESCRIPTION
        "The notification will be sent when IP address of the AP changes."
    ::= { hpnicfDot11APMtTraps 10 }

hpnicfDot11APFlashWriteFailure NOTIFICATION-TYPE
    OBJECTS
        {
            hpnicfDot11APID,
            hpnicfDot11APMtFormerApVersion,
            hpnicfDot11APMtTrapAPMacAddress
        }
    STATUS      current
    DESCRIPTION
        "The notification will be sent when AP failed to write data
        into flash."
    ::= { hpnicfDot11APMtTraps 11 }

hpnicfDot11APSysReboot NOTIFICATION-TYPE
    OBJECTS
        {
            hpnicfDot11APID
        }
    STATUS current
    DESCRIPTION
        "The notification will be sent when AP reboots."
    ::= { hpnicfDot11APMtTraps 12 }

hpnicfDot11APMtAvailChlTooLow NOTIFICATION-TYPE
    OBJECTS
        {
            hpnicfDot11RadioID,
            hpnicfDot11APMtAPID,
            hpnicfDot11APMtTrapAPMacAddress
        }
    STATUS current
    DESCRIPTION
        "The notification will be sent when number of available channels is
         too low.
        "
    ::= { hpnicfDot11APMtTraps 13 }

hpnicfDot11APImgDwldSuccess NOTIFICATION-TYPE
    OBJECTS
        {
            hpnicfDot11CurrAPName,
            hpnicfDot11CurrAPIPAddress,
            hpnicfDot11CurrAPSoftwareVersion
        }
    STATUS current
    DESCRIPTION
        "The notification will be sent when AP succeeds to download image from
        AC.
        "
    ::= { hpnicfDot11APMtTraps 14 }

hpnicfDot11APInterfDetectedTrap NOTIFICATION-TYPE
    OBJECTS
        {
            hpnicfDot11Channel,
            hpnicfDot11CurrInterfDetectedNum,
            hpnicfDot11InterfMacList
        }
    STATUS current
    DESCRIPTION
        "This notification will be sent when some ambient AP interferes with
         current channel."
    ::= { hpnicfDot11APMtTraps 15 }

hpnicfDot11APInterfClearTrap NOTIFICATION-TYPE
    OBJECTS
        {
            hpnicfDot11Channel,
            hpnicfDot11APMtAPID,
            hpnicfDot11APMtRadioID,
            hpnicfDot11APMtInterfMacAdd,
            hpnicfDot11APMtFirstTrapTime,
            hpnicfDot11APMtTrapAPMacAddress
        }
    STATUS current
    DESCRIPTION
        "This notification will be sent when interference caused by ambient
         APs on the current channel disappears."
    ::= { hpnicfDot11APMtTraps 16 }

hpnicfDot11StaInterfDetectedTrap NOTIFICATION-TYPE
    OBJECTS
        {
            hpnicfDot11Channel,
            hpnicfDot11CurrInterfDetectedNum,
            hpnicfDot11InterfMacList,
            hpnicfDot11APMtFirstTrapTime
        }
    STATUS current
    DESCRIPTION
        "This notification will be sent when interference caused by ambient
         STAs on the current channel disappears."
    ::= { hpnicfDot11APMtTraps 17 }

hpnicfDot11StaInterfClearTrap NOTIFICATION-TYPE
    OBJECTS
        {
            hpnicfDot11Channel,
            hpnicfDot11APMtAPID,
            hpnicfDot11APMtRadioID,
            hpnicfDot11APMtInterfMacAdd,
            hpnicfDot11APMtFirstTrapTime,
            hpnicfDot11APMtTrapAPMacAddress
        }
    STATUS current
    DESCRIPTION
        "This notification will be sent when interference caused by ambient
         devices on the current channel happens."
    ::= { hpnicfDot11APMtTraps 18 }

hpnicfDot11OtherDevIntDetectedTrap NOTIFICATION-TYPE
    OBJECTS
        {
            hpnicfDot11Channel,
            hpnicfDot11APMtFirstTrapTime
        }
    STATUS      current
    DESCRIPTION
        "This notification will be sent when interference caused by ambient
         devices on the current channel disappears."
    ::= { hpnicfDot11APMtTraps 19 }

hpnicfDot11OtherDevIntClearTrap NOTIFICATION-TYPE
    OBJECTS
        {
            hpnicfDot11Channel,
            hpnicfDot11APMtAPID,
            hpnicfDot11APMtRadioID,
            hpnicfDot11APMtFirstTrapTime,
            hpnicfDot11APMtTrapAPMacAddress
        }
    STATUS      current
    DESCRIPTION
        "This notification will be sent when previous ambient device disappeared with
         the same channel."
    ::= { hpnicfDot11APMtTraps 20 }

hpnicfDot11APModuleTroubleTrap NOTIFICATION-TYPE
    OBJECTS
        {
            hpnicfDot11RadioID,
            hpnicfDot11APMtAPID,
            hpnicfDot11APMtTrapAPMacAddress
        }
    STATUS current
    DESCRIPTION
        "This notification will be sent when WLAN module failed."
    ::= { hpnicfDot11APMtTraps 21 }

hpnicfDot11APModuleTroubleClearTrap NOTIFICATION-TYPE
    OBJECTS
        {
            hpnicfDot11RadioID,
            hpnicfDot11APMtAPID,
            hpnicfDot11APMtTrapAPMacAddress
        }
    STATUS current
    DESCRIPTION
        "The notification will be sent when WLAN module recovered."
    ::= { hpnicfDot11APMtTraps 22 }

hpnicfDot11APRadioDownTrap NOTIFICATION-TYPE
    OBJECTS
        {
            hpnicfDot11RadioID,
            hpnicfDot11APRadioDownReason,
            hpnicfDot11APMtAPID,
            hpnicfDot11APMtFirstTrapTime,
            hpnicfDot11APMtTrapAPMacAddress
        }
    STATUS current
    DESCRIPTION
        "This notification will be sent when WLAN links interrupted."
    ::= { hpnicfDot11APMtTraps 23 }

hpnicfDot11APRadioDownRecovTrap NOTIFICATION-TYPE
    OBJECTS
        {
            hpnicfDot11RadioID,
            hpnicfDot11APMtAPID,
            hpnicfDot11APMtFirstTrapTime,
            hpnicfDot11APMtTrapAPMacAddress
        }
    STATUS current
    DESCRIPTION
        "This notification will be sent when WLAN links recover."
    ::= { hpnicfDot11APMtTraps 24 }

hpnicfDot11APStaFullTrap NOTIFICATION-TYPE
    OBJECTS
        {
            hpnicfDot11APID,
            hpnicfDot11StaLimitNumber,
            hpnicfDot11StaFullReason,
            hpnicfDot11APMtFirstTrapTime,
            hpnicfDot11APMtTrapAPMacAddress
        }
    STATUS current
    DESCRIPTION
        "This notification will be sent when STA number reach limit number."
    ::= { hpnicfDot11APMtTraps 25 }

hpnicfDot11APStaFullRecoverTrap NOTIFICATION-TYPE
    OBJECTS
        {
            hpnicfDot11APID,
            hpnicfDot11StaLimitNumber,
            hpnicfDot11StaFullReason,
            hpnicfDot11APMtFirstTrapTime,
            hpnicfDot11APMtTrapAPMacAddress
        }
    STATUS current
    DESCRIPTION
        "This notification will be sent when STA number recover enough level."
    ::= { hpnicfDot11APMtTraps 26 }

hpnicfDot11DFSFreeCntBelowThrRecov NOTIFICATION-TYPE
    OBJECTS
        {
            hpnicfDot11RadioID,
            hpnicfDot11APMtAPID,
            hpnicfDot11APMtTrapAPMacAddress
        }
    STATUS current
    DESCRIPTION
        "This notification will be sent when available channels number
        recover enough level."
    ::= { hpnicfDot11APMtTraps 27 }

hpnicfDot11APCpuUsageHigh NOTIFICATION-TYPE
    OBJECTS
        {
            hpnicfDot11APID,
            hpnicfDot11APCPURTUsage,
            hpnicfDot11APMtFirstTrapTime,
            hpnicfDot11APMtTrapAPMacAddress
        }
    STATUS current
    DESCRIPTION
        "The notification will be sent when the AP CPU usage exceeds the
         threshold.
        "
    ::= { hpnicfDot11APMtTraps 28 }

hpnicfDot11APCpuUsageHighRecover NOTIFICATION-TYPE
    OBJECTS
        {
            hpnicfDot11APID,
            hpnicfDot11APCPURTUsage,
            hpnicfDot11APMtFirstTrapTime,
            hpnicfDot11APMtTrapAPMacAddress
        }
    STATUS current
    DESCRIPTION
        "The notification will be sent when the AP CPU usage descends the
         threshold.
        "
    ::= { hpnicfDot11APMtTraps 29 }

hpnicfDot11APMemUsageHigh NOTIFICATION-TYPE
    OBJECTS
        {
            hpnicfDot11APID,
            hpnicfDot11APMemRTUsage,
            hpnicfDot11APMtFirstTrapTime,
            hpnicfDot11APMtTrapAPMacAddress
        }
    STATUS current
    DESCRIPTION
        "The notification will be sent when the AP memory usage exceeds the
         threshold.
        "
    ::= { hpnicfDot11APMtTraps 30 }

hpnicfDot11APMemUsageHighRecover NOTIFICATION-TYPE
    OBJECTS
        {
            hpnicfDot11APID,
            hpnicfDot11APMemRTUsage,
            hpnicfDot11APMtFirstTrapTime,
            hpnicfDot11APMtTrapAPMacAddress
        }
    STATUS current
    DESCRIPTION
        "The notification will be sent when the AP memory usage descends the
         threshold.
         "
    ::= { hpnicfDot11APMtTraps 31 }

hpnicfDot11APTrapUserCntExceedThre NOTIFICATION-TYPE
    OBJECTS
        {
            hpnicfDot11APID,
            hpnicfDot11APTrapUserCnt,
            hpnicfDot11APTrapUserThreshold
        }
    STATUS      current
    DESCRIPTION
        "The notification will be sent when the online user counter exceeds
        the threshold."
    ::= { hpnicfDot11APMtTraps 32 }

hpnicfDot11APMtDetectedIntfAP NOTIFICATION-TYPE
    OBJECTS
        {
            hpnicfDot11APMtAPID,
            hpnicfDot11APMtRadioID,
            hpnicfDot11APMtChannel,
            hpnicfDot11APMtInterfMacAdd,
            hpnicfDot11APMtFirstTrapTime,
            hpnicfDot11APMtTrapAPMacAddress
        }
    STATUS current
    DESCRIPTION
        "This notification will be sent when some ambient AP interferes with
         current channel."
    ::= { hpnicfDot11APMtTraps 33 }

hpnicfDot11APMtDetectedIntfSTA NOTIFICATION-TYPE
    OBJECTS
        {
            hpnicfDot11APMtAPID,
            hpnicfDot11APMtRadioID,
            hpnicfDot11APMtChannel,
            hpnicfDot11APMtInterfMacAdd,
            hpnicfDot11APMtFirstTrapTime,
            hpnicfDot11APMtTrapAPMacAddress
        }
    STATUS current
    DESCRIPTION
        "This notification will be sent when some ambient STA interferes with
         current channel."
    ::= { hpnicfDot11APMtTraps 34 }

hpnicfDot11APMtDetectedIntfOtherDev NOTIFICATION-TYPE
    OBJECTS
        {
            hpnicfDot11APMtAPID,
            hpnicfDot11APMtRadioID,
            hpnicfDot11APMtChannel,
            hpnicfDot11APMtTrapAPMacAddress
        }
    STATUS      current
    DESCRIPTION
        "This notification will be sent when other device interferes with
         current channel."
    ::= { hpnicfDot11APMtTraps 35 }

hpnicfDot11DetcAdjChlIntfAP NOTIFICATION-TYPE
    OBJECTS
        {
            hpnicfDot11APMtAPID,
            hpnicfDot11APMtRadioID,
            hpnicfDot11APMtChannel,
            hpnicfDot11APMtAdjChannel,
            hpnicfDot11APMtInterfMacAdd,
            hpnicfDot11APMtFirstTrapTime
        }
    STATUS current
    DESCRIPTION
        "This notification will be sent when some ambient AP interferes with
         adjacent channel."
    ::= { hpnicfDot11APMtTraps 36 }

hpnicfDot11DetcAdjChlIntfAPClear NOTIFICATION-TYPE
    OBJECTS
        {
            hpnicfDot11APMtAPID,
            hpnicfDot11APMtRadioID,
            hpnicfDot11APMtChannel,
            hpnicfDot11APMtAdjChannel,
            hpnicfDot11APMtInterfMacAdd,
            hpnicfDot11APMtFirstTrapTime
        }
    STATUS current
    DESCRIPTION
        "This notification will be sent when interference caused by ambient
         APs on the adjacent channel disappears."
    ::= { hpnicfDot11APMtTraps 37 }

-- AP Management Notification variable object

hpnicfDot11APMtTrapVarObjects OBJECT IDENTIFIER
    ::= { hpnicfDot11APMtNotifyGroup 1 }

hpnicfDot11APMtTrapCfgErrReason OBJECT-TYPE
    SYNTAX      HpnicfDot11NotifyReasonType
    MAX-ACCESS  accessible-for-notify
    STATUS      current
    DESCRIPTION
        "Represents errors caused by configuration operation."
    ::= { hpnicfDot11APMtTrapVarObjects 1 }

hpnicfDot11APMtTrapRadioFailReason OBJECT-TYPE
    SYNTAX      INTEGER
        {
            config(1),
            hpnicferror(2),
            swerror(3),
            radar(4),
            unknown(8)
        }
    MAX-ACCESS  accessible-for-notify
    STATUS      current
    DESCRIPTION
        "Represents errors caused by configuration operation.
        The following values are supported:
        config     - Configuration error
        hpnicferror  - Hardware error
        swerror    - Software error
        radar      - Radar Detection
        unknown    - Unknown reason"
    ::= { hpnicfDot11APMtTrapVarObjects 2 }

hpnicfDot11APMtTrapOldChannel OBJECT-TYPE
    SYNTAX      HpnicfDot11ChannelScopeType
    MAX-ACCESS  accessible-for-notify
    STATUS      current
    DESCRIPTION
        "Represents which channel the radio used to use."
    ::= { hpnicfDot11APMtTrapVarObjects 3 }

hpnicfDot11APMtTrapNewChannel OBJECT-TYPE
    SYNTAX      HpnicfDot11ChannelScopeType
    MAX-ACCESS  accessible-for-notify
    STATUS      current
    DESCRIPTION
        "Represents which channel the radio will use."
    ::= { hpnicfDot11APMtTrapVarObjects 4 }

hpnicfDot11APChannelChgMode OBJECT-TYPE
    SYNTAX      HpnicfDot11RFModeType
    MAX-ACCESS  accessible-for-notify
    STATUS      current
    DESCRIPTION
        "Represents the channel change mode for a radio."
    ::= { hpnicfDot11APMtTrapVarObjects 5 }

hpnicfDot11APChgWorkMode OBJECT-TYPE
    SYNTAX      INTEGER
        {
            normal(1),
            monitor(2),
            hybrid(3)
        }
    MAX-ACCESS  accessible-for-notify
    STATUS      current
    DESCRIPTION
        "Represents what work mode for AP.
        The following values are supported:
        normal  - AP will supply WLAN service.
        monitor - AP will be a monitor to detect attack.
        hybrid  - AP will supply WLAN service and detect attack."
    ::= { hpnicfDot11APMtTrapVarObjects 6 }

hpnicfDot11APIntfDevMACAddress OBJECT-TYPE
    SYNTAX      MacAddress
    MAX-ACCESS  accessible-for-notify
    STATUS      current
    DESCRIPTION
        "Represents MAC address of the device which triggers the notification."
    ::= { hpnicfDot11APMtTrapVarObjects 7 }

hpnicfDot11APMtTrapOldIPAddr OBJECT-TYPE
    SYNTAX      IpAddress
    MAX-ACCESS  accessible-for-notify
    STATUS      current
    DESCRIPTION
        "Represents the IP address of AP."
    ::= { hpnicfDot11APMtTrapVarObjects 8 }

hpnicfDot11CurrInterfDetectedNum OBJECT-TYPE
    SYNTAX      Integer32
    MAX-ACCESS  accessible-for-notify
    STATUS      current
    DESCRIPTION
        "Represents the number of interfere detected."
    ::= { hpnicfDot11APMtTrapVarObjects 9 }

hpnicfDot11StaFullReason OBJECT-TYPE
    SYNTAX      INTEGER
        {
            ap(1),
            bss(2),
            radio(3),
            radioConcur(4),
            radiopolicy(5),
            ac(6),
            acConcur(7),
            aid(8)
        }
    MAX-ACCESS  accessible-for-notify
    STATUS      current
    DESCRIPTION
        "Reports which kind maximum number of STA
         is reached. New STA is not able to associate."
    ::= { hpnicfDot11APMtTrapVarObjects 10 }

hpnicfDot11StaLimitNumber OBJECT-TYPE
    SYNTAX      Integer32
    MAX-ACCESS  accessible-for-notify
    STATUS      current
    DESCRIPTION
        "Represents the limit number of STA."
    ::= { hpnicfDot11APMtTrapVarObjects 11 }

hpnicfDot11APRadioDownReason OBJECT-TYPE
    SYNTAX  INTEGER
        {
            phyicalUnusable(1),
            configDisable(2),
            operatinUnusable(3),
            apTunnelDown(4)
        }
    MAX-ACCESS  accessible-for-notify
    STATUS      current
    DESCRIPTION
        "Reports the reason why WLAN links is interrupted."
    ::= { hpnicfDot11APMtTrapVarObjects 12 }

hpnicfDot11InterfMacList OBJECT-TYPE
    SYNTAX      OCTET STRING
    MAX-ACCESS  accessible-for-notify
    STATUS      current
    DESCRIPTION
        "Represents MAC address list of interfere detected."
    ::= { hpnicfDot11APMtTrapVarObjects 13 }

hpnicfDot11APTrapUserCnt OBJECT-TYPE
    SYNTAX      Integer32
    MAX-ACCESS  accessible-for-notify
    STATUS      current
    DESCRIPTION
        "Represents the online user counter of AP."
    ::= { hpnicfDot11APMtTrapVarObjects 14 }

hpnicfDot11APTrapUserThreshold OBJECT-TYPE
    SYNTAX      Integer32
    MAX-ACCESS  accessible-for-notify
    STATUS      current
    DESCRIPTION
        "Represents threshold of AP's online user counter."
    ::= { hpnicfDot11APMtTrapVarObjects 15 }

hpnicfDot11APMtChanlChgCount OBJECT-TYPE
    SYNTAX      Integer32
    MAX-ACCESS  accessible-for-notify
    STATUS      current
    DESCRIPTION
        "Represents how many times that channel changed."
    ::= { hpnicfDot11APMtTrapVarObjects 16 }

hpnicfDot11APMtFormerApVersion OBJECT-TYPE
    SYNTAX      OCTET STRING
    MAX-ACCESS  accessible-for-notify
    STATUS      current
    DESCRIPTION
        "Represents former software version of AP."
    ::= { hpnicfDot11APMtTrapVarObjects 17 }

hpnicfDot11APMtAPID OBJECT-TYPE
    SYNTAX      HpnicfDot11ObjectIDType
    MAX-ACCESS  accessible-for-notify
    STATUS      current
    DESCRIPTION
        "To uniquely identify each AP."
    ::= { hpnicfDot11APMtTrapVarObjects 18 }

hpnicfDot11APMtRadioID OBJECT-TYPE
    SYNTAX      HpnicfDot11RadioScopeType
    MAX-ACCESS  accessible-for-notify
    STATUS      current
    DESCRIPTION
        "Represents each radio."
    ::= { hpnicfDot11APMtTrapVarObjects 19 }

hpnicfDot11APMtChannel OBJECT-TYPE
    SYNTAX      HpnicfDot11ChannelScopeType
    MAX-ACCESS  accessible-for-notify
    STATUS      current
    DESCRIPTION
        "Represents the current channel allocation for radio."
    ::= { hpnicfDot11APMtTrapVarObjects 20 }

hpnicfDot11APMtInterfMacAdd OBJECT-TYPE
    SYNTAX      MacAddress
    MAX-ACCESS  accessible-for-notify
    STATUS      current
    DESCRIPTION
        "Represents the MAC address of an AP."
    ::= { hpnicfDot11APMtTrapVarObjects 21 }

hpnicfDot11APMtAdjChannel OBJECT-TYPE
    SYNTAX      HpnicfDot11ChannelScopeType
    MAX-ACCESS  accessible-for-notify
    STATUS      current
    DESCRIPTION
        "Represents the adjacent channel of radio."
    ::= { hpnicfDot11APMtTrapVarObjects 22 }

hpnicfDot11APMtFirstTrapTime OBJECT-TYPE
    SYNTAX      TimeTicks
    MAX-ACCESS  accessible-for-notify
    STATUS      current
    DESCRIPTION
        "Represents the first trap time."
    ::= { hpnicfDot11APMtTrapVarObjects 23 }

hpnicfDot11APMtTrapAPMacAddress OBJECT-TYPE
    SYNTAX      MacAddress
    MAX-ACCESS  accessible-for-notify
    STATUS      current
    DESCRIPTION
        "Represents the MAC address of an AP."
    ::= {hpnicfDot11APMtTrapVarObjects 24}


-- *****************************************************************************
-- *  End of AP Management Notification  Definition
-- *****************************************************************************
END
