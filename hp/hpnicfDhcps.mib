-- =========================================================================
-- Copyright (c) 2010-2013 Hewlett-Packard Development Company, L.P.
--
-- Description:  DHCP Server MIB
-- Reference:  Enterprise MIB
-- Version:V1.52
-- History:
--     initial version 2003-03-06
--     V1.0 6th Mar 2004
--  V1.1 Modified by chenhua 2004-08-13
--   Add 0 to the vlaue list of hpnicfDHCPSIPResetFlag for get-opporation
--  V1.2 Modified by chenhua 2004-09-16
--   Modify  the default value of hpnicfDHCPSWriteDataDelay  to 300
--  V1.3 2004-10-12 updated by gaolong
--   Import TEXTUAL-CONVENTION
--  v1.4 Modified by xinhaing 2004-03-03
--   Add a new table  : hpnicfDHCPSIPInUseExTable
--   The satus of the table hpnicfDHCPSIPInUseTable is modified to be deprecated
--   Correct some spelling errors in hpnicfDHCPSIPInUseTable's description
--   Adjust file format
-- v1.5 2006-02-22 Modified by xuyufei
--   Modify the default value of hpnicfDHCPSDetectingServerStatus to disabled
--   Modify the default value of hpnicfDHCPSGlobalPoolClientNetbiosType
--   and hpnicfDHCPSInterfacePoolClientNetbiosType to 0
--   Correct the description of hpnicfDHCPSGlobalPoolOptionHexString,
--   hpnicfDHCPSInterfacePoolOptionHexString, hpnicfDHCPSGlobalPoolNumber,
--   hpnicfDHCPSInterfacePoolNumber
-- v1.51 2006-04-13
--   change value range of hpnicfDHCPSIPInUsePoolName and hpnicfDHCPSIPInUsePoolNameEx
-- v1.52 2011-01-19 Modified by ganchanghua
--   change SYNTAX of hpnicfDHCPSConflictIPDetectTime to OCTET STRING(SIZE(1..20))
-- =========================================================================
HPN-ICF-DHCPS-MIB DEFINITIONS ::= BEGIN
    IMPORTS
        hpnicfRhw
            FROM HPN-ICF-OID-MIB
        ifIndex
            FROM RFC1213-MIB
        OBJECT-GROUP
            FROM SNMPv2-CONF
        IpAddress, Integer32, OBJECT-TYPE, MODULE-IDENTITY
            FROM SNMPv2-SMI
        RowStatus, MacAddress, TEXTUAL-CONVENTION
            FROM SNMPv2-TC;

    hpnicfDHCPServerMib MODULE-IDENTITY
        LAST-UPDATED "200602200000Z"        -- February 20, 2006 at 00:00 GMT
        ORGANIZATION
            ""
        CONTACT-INFO
            ""
        DESCRIPTION
            "This MIB describes objects used for managing DHCP server."
        ::= { hpnicfRhw 2 }
--
-- Textual Conventions
--

    HpnicfDhcpSEnabledStatus ::= TEXTUAL-CONVENTION
        STATUS      current
        DESCRIPTION
            "To descript the status of some function is Enabled or
            Disabled."
        SYNTAX      INTEGER
            {
                enabled(1),
                disabled(0)
            }

--
-- Node definitions
--

    hpnicfDHCPServerMibObject OBJECT IDENTIFIER ::= { hpnicfDHCPServerMib 1 }

--  Part 1: For DHCP server global pool
--
-- =================================================================
-- 1st Table of hpnicfDHCPServerMibObject: hpnicfDHCPSGlobalPoolTable
-- =================================================================
    hpnicfDHCPSGlobalPoolTable OBJECT-TYPE
        SYNTAX      SEQUENCE OF HpnicfDHCPSGlobalPoolEntry
        MAX-ACCESS  not-accessible
        STATUS      current
        DESCRIPTION
            "A table for creating DHCP server global pools."
        ::= { hpnicfDHCPServerMibObject 1 }

    hpnicfDHCPSGlobalPoolEntry OBJECT-TYPE
        SYNTAX      HpnicfDHCPSGlobalPoolEntry
        MAX-ACCESS  not-accessible
        STATUS      current
        DESCRIPTION
            "An entry containing objects for creating or
            deleting a global pool for the DHCP server."
        INDEX { hpnicfDHCPSGlobalPoolName }
        ::= { hpnicfDHCPSGlobalPoolTable 1 }

    HpnicfDHCPSGlobalPoolEntry ::=
        SEQUENCE
            {
                hpnicfDHCPSGlobalPoolName         OCTET STRING,
                hpnicfDHCPSGlobalPoolRowStatus    RowStatus
            }

    hpnicfDHCPSGlobalPoolName OBJECT-TYPE
        SYNTAX      OCTET STRING(SIZE(0..255))
        MAX-ACCESS  read-only
        STATUS      current
        DESCRIPTION
            "DHCP server global pool name."
        ::= { hpnicfDHCPSGlobalPoolEntry 1 }

    hpnicfDHCPSGlobalPoolRowStatus OBJECT-TYPE
        SYNTAX      RowStatus
        MAX-ACCESS  read-create
        STATUS      current
        DESCRIPTION
            "RowStatus. Three actions are used: active,
            createAndGo, destroy."
        ::= { hpnicfDHCPSGlobalPoolEntry 2 }

--  =================================================================
-- 2nd Table of hpnicfDHCPServerMibObject: hpnicfDHCPSGlobalPoolConfigTable
-- =================================================================
    hpnicfDHCPSGlobalPoolConfigTable OBJECT-TYPE
        SYNTAX      SEQUENCE OF HpnicfDHCPSGlobalPoolConfigEntry
        MAX-ACCESS  not-accessible
        STATUS      current
        DESCRIPTION
            "A table containing the configurations of dhcp
            server global pools."
        ::= { hpnicfDHCPServerMibObject 2 }

    hpnicfDHCPSGlobalPoolConfigEntry OBJECT-TYPE
        SYNTAX      HpnicfDHCPSGlobalPoolConfigEntry
        MAX-ACCESS  not-accessible
        STATUS      current
        DESCRIPTION
            "An entry containing the objects for configuring
            the network ip or host ip etc. to global pools for
            DHCP server."
        INDEX { hpnicfDHCPSGlobalPoolName }
        ::= { hpnicfDHCPSGlobalPoolConfigTable 1 }

    HpnicfDHCPSGlobalPoolConfigEntry ::=
        SEQUENCE
            {
                hpnicfDHCPSGlobalPoolType              INTEGER,
                hpnicfDHCPSGlobalPoolNetwork           IpAddress,
                hpnicfDHCPSGlobalPoolNetworkMask       IpAddress,
                hpnicfDHCPSGlobalPoolHostIPAddr        IpAddress,
                hpnicfDHCPSGlobalPoolHostMask          IpAddress,
                hpnicfDHCPSGlobalPoolHostHAddr         MacAddress,
                hpnicfDHCPSGlobalPoolConfigUndoFlag    INTEGER
            }

    hpnicfDHCPSGlobalPoolType OBJECT-TYPE
        SYNTAX      INTEGER
            {
                null(0),
                host(1),
                network(2)
            }
        MAX-ACCESS  read-write
        STATUS      current
        DESCRIPTION
            "Type of a DHCP global pool. Any operations of
            this object will be bound with the operations
            of hpnicfDHCPSGlobalPoolNetwork, hpnicfDHCPSGlobalPoolHostIPAddr,
            or hpnicfDHCPSGlobalPoolHostHAddr.
            That means any operation of this object alone will
            be regarded as invalid operation."
        ::= { hpnicfDHCPSGlobalPoolConfigEntry 1 }

    hpnicfDHCPSGlobalPoolNetwork OBJECT-TYPE
        SYNTAX      IpAddress
        MAX-ACCESS  read-write
        STATUS      current
        DESCRIPTION
            "Network ip of a DHCP global pool.
            To delete a configured network ip, please set
            hpnicfDHCPSGlobalPoolConfigUndoFlag to 1."
        ::= { hpnicfDHCPSGlobalPoolConfigEntry 2 }

    hpnicfDHCPSGlobalPoolNetworkMask OBJECT-TYPE
        SYNTAX      IpAddress
        MAX-ACCESS  read-write
        STATUS      current
        DESCRIPTION
            "Net mask of a DHCP global pool(network).
            The SET operation to this object ought to be with
            the SET of hpnicfDHCPSGlobalPoolNetwork together, and
            any SET operation alone to this object will be
            regarded as an invalid operation.
            When a network ip of a DHCP global pool was
            deleted, the net mask would also be deleted
            automatically, and no further operation needed."
        ::= { hpnicfDHCPSGlobalPoolConfigEntry 3 }

    hpnicfDHCPSGlobalPoolHostIPAddr OBJECT-TYPE
        SYNTAX      IpAddress
        MAX-ACCESS  read-write
        STATUS      current
        DESCRIPTION
            "Host ip of a DHCP global pool.
            To delete a configured network ip, please set
            hpnicfDHCPSGlobalPoolConfigUndoFlag to 2."
        ::= { hpnicfDHCPSGlobalPoolConfigEntry 4 }

    hpnicfDHCPSGlobalPoolHostMask OBJECT-TYPE
        SYNTAX      IpAddress
        MAX-ACCESS  read-write
        STATUS      current
        DESCRIPTION
            "Net mask of a DHCP global pool(host)
            The SET operation to this object ought to be with
            the SET of hpnicfDHCPSGlobalPoolHostIPAddr together,
            and any SET operation alone to this object will be
            regarded as an invalid operation.
            When a host ip of a DHCP global pool was
            deleted, the net mask would also be deleted
            automatically, and no further operation needed."
        ::= { hpnicfDHCPSGlobalPoolConfigEntry 5 }

    hpnicfDHCPSGlobalPoolHostHAddr OBJECT-TYPE
        SYNTAX      MacAddress
        MAX-ACCESS  read-write
        STATUS      current
        DESCRIPTION
            "Hardware address of a DHCP global pool(host).
            To delete a configured hardware address, please
            set hpnicfDHCPSGlobalPoolConfigUndoFlag to 3."
        ::= { hpnicfDHCPSGlobalPoolConfigEntry 6 }

    hpnicfDHCPSGlobalPoolConfigUndoFlag OBJECT-TYPE
        SYNTAX      INTEGER
            {
                undonetworkip(1),
                undohostip(2),
                undohosthaddr(3)
            }
        MAX-ACCESS  read-write
        STATUS      current
        DESCRIPTION
            "Flag of undo operation for hpnicfDHCPSGlobalPoolConfigTable."
        ::= { hpnicfDHCPSGlobalPoolConfigEntry 7 }

--  =================================================================
-- 3rd Table of hpnicfDHCPServerMibObject: hpnicfDHCPSGlobalPoolParaTable
-- =================================================================
    hpnicfDHCPSGlobalPoolParaTable OBJECT-TYPE
        SYNTAX      SEQUENCE OF HpnicfDHCPSGlobalPoolParaEntry
        MAX-ACCESS  not-accessible
        STATUS      current
        DESCRIPTION
            "A table for configuring parameters to DHCP global
            pools."
        ::= { hpnicfDHCPServerMibObject 3 }

    hpnicfDHCPSGlobalPoolParaEntry OBJECT-TYPE
        SYNTAX      HpnicfDHCPSGlobalPoolParaEntry
        MAX-ACCESS  not-accessible
        STATUS      current
        DESCRIPTION
            "An entry containing the objects for the
            configurations of parameters of DHCP global pools."
        INDEX { hpnicfDHCPSGlobalPoolName }
        ::= { hpnicfDHCPSGlobalPoolParaTable 1 }

    HpnicfDHCPSGlobalPoolParaEntry ::=
        SEQUENCE
            {
                hpnicfDHCPSGlobalPoolLeaseDay                 INTEGER,
                hpnicfDHCPSGlobalPoolLeaseHour                INTEGER,
                hpnicfDHCPSGlobalPoolLeaseMinute              INTEGER,
                hpnicfDHCPSGlobalPoolLeaseUnlimited           INTEGER,
                hpnicfDHCPSGlobalPoolDomainName               OCTET STRING,
                hpnicfDHCPSGlobalPoolClientGatewayIPString    OCTET STRING,
                hpnicfDHCPSGlobalPoolClientGatewayIPUndo      IpAddress,
                hpnicfDHCPSGlobalPoolClientDNSIPString        OCTET STRING,
                hpnicfDHCPSGlobalPoolClientDNSIPUndo          IpAddress,
                hpnicfDHCPSGlobalPoolClientNetbiosType        INTEGER,
                hpnicfDHCPSGlobalPoolClientNbnsIPString       OCTET STRING,
                hpnicfDHCPSGlobalPoolClientNbnsIPUndo         IpAddress,
                hpnicfDHCPSGlobalPoolParaUndoFlag             INTEGER,
                hpnicfDHCPSGlobalPoolIPInUseReset             INTEGER
            }

    hpnicfDHCPSGlobalPoolLeaseDay OBJECT-TYPE
        SYNTAX      INTEGER(0..365)
        MAX-ACCESS  read-write
        STATUS      current
        DESCRIPTION
            "Number of days of the lease."
        DEFVAL { 1 }
        ::= { hpnicfDHCPSGlobalPoolParaEntry 1 }

    hpnicfDHCPSGlobalPoolLeaseHour OBJECT-TYPE
        SYNTAX      INTEGER(0..23)
        MAX-ACCESS  read-write
        STATUS      current
        DESCRIPTION
            "Number of hours of the lease."
        DEFVAL { 0 }
        ::= { hpnicfDHCPSGlobalPoolParaEntry 2 }

    hpnicfDHCPSGlobalPoolLeaseMinute OBJECT-TYPE
        SYNTAX      INTEGER(0..59)
        MAX-ACCESS  read-write
        STATUS      current
        DESCRIPTION
            "Number of minutes of the lease."
        DEFVAL { 0 }
        ::= { hpnicfDHCPSGlobalPoolParaEntry 3 }

    hpnicfDHCPSGlobalPoolLeaseUnlimited OBJECT-TYPE
        SYNTAX      INTEGER
            {
                invalid(0),
                unlimited(1)
            }
        MAX-ACCESS  read-write
        STATUS      current
        DESCRIPTION
            "A flag denoting if the lease of a pool is
            unlimited."
        ::= { hpnicfDHCPSGlobalPoolParaEntry 4 }

    hpnicfDHCPSGlobalPoolDomainName OBJECT-TYPE
        SYNTAX      OCTET STRING(SIZE(0..255))
        MAX-ACCESS  read-write
        STATUS      current
        DESCRIPTION
            "Domain name for DHCP clients."
        ::= { hpnicfDHCPSGlobalPoolParaEntry 5 }

    hpnicfDHCPSGlobalPoolClientGatewayIPString OBJECT-TYPE
        SYNTAX      OCTET STRING(SIZE(0..129))
        MAX-ACCESS  read-write
        STATUS      current
        DESCRIPTION
            "String of gateway ip addresses for DHCP clients.
            Since mostly 8 ip can be configured for a pool
            totally, a string is defined to get or configure 8 ip
            ip at a time."
        ::= { hpnicfDHCPSGlobalPoolParaEntry 6 }

    hpnicfDHCPSGlobalPoolClientGatewayIPUndo OBJECT-TYPE
        SYNTAX      IpAddress
        MAX-ACCESS  read-write
        STATUS      current
        DESCRIPTION
            "A gateway ip address to delete. This object is
            only for deleting a given ip of gateway router."
        ::= { hpnicfDHCPSGlobalPoolParaEntry 7 }

    hpnicfDHCPSGlobalPoolClientDNSIPString OBJECT-TYPE
        SYNTAX      OCTET STRING(SIZE(0..129))
        MAX-ACCESS  read-write
        STATUS      current
        DESCRIPTION
            "String of DNS server ip addresses for DHCP clients.
            Since mostly 8 ip can be configured for a pool
            totally, a string is defined to get or configure 8
            ip at a time."
        ::= { hpnicfDHCPSGlobalPoolParaEntry 8 }

    hpnicfDHCPSGlobalPoolClientDNSIPUndo OBJECT-TYPE
        SYNTAX      IpAddress
        MAX-ACCESS  read-write
        STATUS      current
        DESCRIPTION
            "A DNS server ip address to delete. This object
            is only for deleting a given ip of DNS server."
        ::= { hpnicfDHCPSGlobalPoolParaEntry 9 }

    hpnicfDHCPSGlobalPoolClientNetbiosType OBJECT-TYPE
        SYNTAX      INTEGER
            {
                null(0),
                bnode(1),
                pnode(2),
                mnode(4),
                hnode(8)
            }
        MAX-ACCESS  read-write
        STATUS      current
        DESCRIPTION
            "NetBios node type for DHCP clients."
        DEFVAL { 0 }
        ::= { hpnicfDHCPSGlobalPoolParaEntry 10 }

    hpnicfDHCPSGlobalPoolClientNbnsIPString OBJECT-TYPE
        SYNTAX      OCTET STRING(SIZE(0..129))
        MAX-ACCESS  read-write
        STATUS      current
        DESCRIPTION
            "String of NetBios server ip addresses for DHCP
            clients. Since mostly 8 ip can be configured for
            a pool totally, so a string is defined to get or
            configure 8 ip at a time."
        ::= { hpnicfDHCPSGlobalPoolParaEntry 11 }

    hpnicfDHCPSGlobalPoolClientNbnsIPUndo OBJECT-TYPE
        SYNTAX      IpAddress
        MAX-ACCESS  read-write
        STATUS      current
        DESCRIPTION
            "A NetBios server ip address to delete. This
            object is only for deleting a given ip of NetBios
            server."
        ::= { hpnicfDHCPSGlobalPoolParaEntry 12 }

    hpnicfDHCPSGlobalPoolParaUndoFlag OBJECT-TYPE
        SYNTAX      INTEGER
            {
                undoDomain(1),
                undoLease(2),
                undoGateway(3),
                undoDns(4),
                undoNbns(5),
                undoNbType(6)
            }
        MAX-ACCESS  read-write
        STATUS      current
        DESCRIPTION
            "Flag of undo-operation for hpnicfDHCPSGlobalPoolParaTable."
        ::= { hpnicfDHCPSGlobalPoolParaEntry 13 }

    hpnicfDHCPSGlobalPoolIPInUseReset OBJECT-TYPE
        SYNTAX      INTEGER
            {
                reset(1)
            }
        MAX-ACCESS  read-write
        STATUS      current
        DESCRIPTION
            "Reset the auto binding ip of the given global
            pool for DHCP server."
        ::= { hpnicfDHCPSGlobalPoolParaEntry 14 }

--  =================================================================
-- 4th Table of hpnicfDHCPServerMibObject: hpnicfDHCPSGlobalPoolOptionTable
-- =================================================================
    hpnicfDHCPSGlobalPoolOptionTable OBJECT-TYPE
        SYNTAX      SEQUENCE OF HpnicfDHCPSGlobalPoolOptionEntry
        MAX-ACCESS  not-accessible
        STATUS      current
        DESCRIPTION
            "A table for configuring options to DHCP global pools."
        ::= { hpnicfDHCPServerMibObject 4 }

    hpnicfDHCPSGlobalPoolOptionEntry OBJECT-TYPE
        SYNTAX      HpnicfDHCPSGlobalPoolOptionEntry
        MAX-ACCESS  not-accessible
        STATUS      current
        DESCRIPTION
            "An entry containing the objects for configuring
            options to DHCP global pools."
        INDEX { hpnicfDHCPSGlobalPoolName, hpnicfDHCPSGlobalPoolOptionCode }
        ::= { hpnicfDHCPSGlobalPoolOptionTable 1 }

    HpnicfDHCPSGlobalPoolOptionEntry ::=
        SEQUENCE
            {
                hpnicfDHCPSGlobalPoolOptionCode         INTEGER,
                hpnicfDHCPSGlobalPoolOptionType         INTEGER,
                hpnicfDHCPSGlobalPoolOptionAscii        OCTET STRING,
                hpnicfDHCPSGlobalPoolOptionHexString    OCTET STRING,
                hpnicfDHCPSGlobalPoolOptionIPString     OCTET STRING,
                hpnicfDHCPSGlobalPoolOptionRowStatus    RowStatus
             }

    hpnicfDHCPSGlobalPoolOptionCode OBJECT-TYPE
        SYNTAX      INTEGER(1..254)
        MAX-ACCESS  read-only
        STATUS      current
        DESCRIPTION
            "Option code."
        ::= { hpnicfDHCPSGlobalPoolOptionEntry 1 }

    hpnicfDHCPSGlobalPoolOptionType OBJECT-TYPE
        SYNTAX      INTEGER
            {
                ascii(1),
                hex(2),
                ip(3)
            }
        MAX-ACCESS  read-create
        STATUS      current
        DESCRIPTION
            "Option type."
        ::= { hpnicfDHCPSGlobalPoolOptionEntry 2 }

    hpnicfDHCPSGlobalPoolOptionAscii OBJECT-TYPE
        SYNTAX      OCTET STRING(SIZE(0..63))
        MAX-ACCESS  read-create
        STATUS      current
        DESCRIPTION
            "Ascii string of an option."
        ::= { hpnicfDHCPSGlobalPoolOptionEntry 3 }

    hpnicfDHCPSGlobalPoolOptionHexString OBJECT-TYPE
        SYNTAX      OCTET STRING(SIZE(0..143))
        MAX-ACCESS  read-create
        STATUS      current
        DESCRIPTION
            "Hex string of an option. 1st to 16th hex strings,
            which are 2 bytes, 4 bytes, 6 bytes or 8 bytes,
            can be configured at most simultaneously.
            That means the format of each string
            must be '12', '1234', '123456' or '12345678'."
        ::= { hpnicfDHCPSGlobalPoolOptionEntry 4 }

    hpnicfDHCPSGlobalPoolOptionIPString OBJECT-TYPE
        SYNTAX      OCTET STRING(SIZE(0..129))
        MAX-ACCESS  read-create
        STATUS      current
        DESCRIPTION
            "Ip string of an option. 1 to 8 ip addresses  can
            be configured at most simultaneously."
        ::= { hpnicfDHCPSGlobalPoolOptionEntry 5 }

    hpnicfDHCPSGlobalPoolOptionRowStatus OBJECT-TYPE
        SYNTAX      RowStatus
        MAX-ACCESS  read-create
        STATUS      current
        DESCRIPTION
            "RowStatus. Three actions are used: active,
            createAndGo, destroy."
        ::= { hpnicfDHCPSGlobalPoolOptionEntry 6 }

--  =================================================================
-- 5th Table of hpnicfDHCPServerMibObject:hpnicfDHCPSGlobalTreeTable
-- =================================================================
    hpnicfDHCPSGlobalTreeTable OBJECT-TYPE
        SYNTAX      SEQUENCE OF HpnicfDHCPSGlobalTreeEntry
        MAX-ACCESS  not-accessible
        STATUS      current
        DESCRIPTION
            "A table containing the information of the tree of
            DHCP global pools."
        ::= { hpnicfDHCPServerMibObject 5 }

    hpnicfDHCPSGlobalTreeEntry OBJECT-TYPE
        SYNTAX      HpnicfDHCPSGlobalTreeEntry
        MAX-ACCESS  not-accessible
        STATUS      current
        DESCRIPTION
            "An entry of objects containing the information
            for displaying the tree of DHCP global pools."
        INDEX { hpnicfDHCPSGlobalPoolName }
        ::= { hpnicfDHCPSGlobalTreeTable 1 }

    HpnicfDHCPSGlobalTreeEntry ::=
        SEQUENCE
            {
                hpnicfDHCPSGlobalTreeParentNodeName        OCTET STRING,
                hpnicfDHCPSGlobalTreeChildNodeName         OCTET STRING,
                hpnicfDHCPSGlobalTreePreSiblingNodeName    OCTET STRING,
                hpnicfDHCPSGlobalTreeSiblingNodeName       OCTET STRING
             }

    hpnicfDHCPSGlobalTreeParentNodeName OBJECT-TYPE
        SYNTAX      OCTET STRING(SIZE(0..255))
        MAX-ACCESS  read-only
        STATUS      current
        DESCRIPTION
            "Pool name of the parent node."
        ::= { hpnicfDHCPSGlobalTreeEntry 1 }

    hpnicfDHCPSGlobalTreeChildNodeName OBJECT-TYPE
        SYNTAX      OCTET STRING(SIZE(0..255))
        MAX-ACCESS  read-only
        STATUS      current
        DESCRIPTION
            "Pool name of the child node."
        ::= { hpnicfDHCPSGlobalTreeEntry 2 }

    hpnicfDHCPSGlobalTreePreSiblingNodeName OBJECT-TYPE
        SYNTAX      OCTET STRING(SIZE(0..255))
        MAX-ACCESS  read-only
        STATUS      current
        DESCRIPTION
            "Pool name of the presibling node."
        ::= { hpnicfDHCPSGlobalTreeEntry 3 }

    hpnicfDHCPSGlobalTreeSiblingNodeName OBJECT-TYPE
        SYNTAX      OCTET STRING(SIZE(0..255))
        MAX-ACCESS  read-only
        STATUS      current
        DESCRIPTION
            "Pool name of the sibling node."
        ::= { hpnicfDHCPSGlobalTreeEntry 4 }

--  Part 2: For DHCP server interface pool
--
-- =================================================================
-- 6th Table of hpnicfDHCPServerMibObject: hpnicfDHCPSInterfacePoolParaTable
-- =================================================================
    hpnicfDHCPSInterfacePoolParaTable OBJECT-TYPE
        SYNTAX      SEQUENCE OF HpnicfDHCPSInterfacePoolParaEntry
        MAX-ACCESS  not-accessible
        STATUS      current
        DESCRIPTION
            "A table for configuring parameters to DHCP interface
            pools."
        ::= { hpnicfDHCPServerMibObject 6 }

    hpnicfDHCPSInterfacePoolParaEntry OBJECT-TYPE
        SYNTAX      HpnicfDHCPSInterfacePoolParaEntry
        MAX-ACCESS  not-accessible
        STATUS      current
        DESCRIPTION
            "An entry of objects for configuring parameters
            to DHCP interface pools.
            The index of this entry is the ifIndex of ethernet."
        INDEX { ifIndex }
        ::= { hpnicfDHCPSInterfacePoolParaTable 1 }

    HpnicfDHCPSInterfacePoolParaEntry ::=
        SEQUENCE
            {
                hpnicfDHCPSInterfacePoolLeaseDay              INTEGER,
                hpnicfDHCPSInterfacePoolLeaseHour             INTEGER,
                hpnicfDHCPSInterfacePoolLeaseMinute           INTEGER,
                hpnicfDHCPSInterfacePoolLeaseUnlimited        INTEGER,
                hpnicfDHCPSInterfacePoolDomainName            OCTET STRING,
                hpnicfDHCPSInterfacePoolClientDNSIPString     OCTET STRING,
                hpnicfDHCPSInterfacePoolClientDNSIPUndo       IpAddress,
                hpnicfDHCPSInterfacePoolClientNetbiosType     INTEGER,
                hpnicfDHCPSInterfacePoolClientNbnsIPString    OCTET STRING,
                hpnicfDHCPSInterfacePoolClientNbnsIPUndo      IpAddress,
                hpnicfDHCPSInterfacePoolParaUndoFlag          INTEGER,
                hpnicfDHCPSInterfacePoolIPInUseReset          INTEGER
    }

    hpnicfDHCPSInterfacePoolLeaseDay OBJECT-TYPE
        SYNTAX      INTEGER(0..365)
        MAX-ACCESS  read-write
        STATUS      current
        DESCRIPTION
            "Number of days of the lease."
        DEFVAL { 1 }
        ::= { hpnicfDHCPSInterfacePoolParaEntry 1 }

    hpnicfDHCPSInterfacePoolLeaseHour OBJECT-TYPE
        SYNTAX      INTEGER(0..23)
        MAX-ACCESS  read-write
        STATUS      current
        DESCRIPTION
            "Number of hours of the lease."
        DEFVAL { 0 }
        ::= { hpnicfDHCPSInterfacePoolParaEntry 2 }

    hpnicfDHCPSInterfacePoolLeaseMinute OBJECT-TYPE
        SYNTAX      INTEGER(0..59)
        MAX-ACCESS  read-write
        STATUS      current
        DESCRIPTION
            "Number of minutes of the lease."
        DEFVAL { 0 }
        ::= { hpnicfDHCPSInterfacePoolParaEntry 3 }

    hpnicfDHCPSInterfacePoolLeaseUnlimited OBJECT-TYPE
        SYNTAX      INTEGER
            {
                invalid(0),
                unlimited(1)
            }
        MAX-ACCESS  read-write
        STATUS      current
        DESCRIPTION
            "A flag denoting if the lease of a pool is
            unlimited."
        ::= { hpnicfDHCPSInterfacePoolParaEntry 4 }

    hpnicfDHCPSInterfacePoolDomainName OBJECT-TYPE
        SYNTAX      OCTET STRING(SIZE(0..255))
        MAX-ACCESS  read-write
        STATUS      current
        DESCRIPTION
            "Domain name for DHCP clients."
        ::= { hpnicfDHCPSInterfacePoolParaEntry 5 }

    hpnicfDHCPSInterfacePoolClientDNSIPString OBJECT-TYPE
        SYNTAX      OCTET STRING(SIZE(0..129))
        MAX-ACCESS  read-write
        STATUS      current
        DESCRIPTION
            "String of DNS server ip addresses for DHCP clients.
            Since mostly 8 ip can be configured for a pool
            totally, a string is defined to get or configure 8
            ip at a time."
        ::= { hpnicfDHCPSInterfacePoolParaEntry 6 }

    hpnicfDHCPSInterfacePoolClientDNSIPUndo OBJECT-TYPE
        SYNTAX      IpAddress
        MAX-ACCESS  read-write
        STATUS      current
        DESCRIPTION
            "A DNS server ip address to delete. This object
            is only for deleting a given ip of DNS server."
        ::= { hpnicfDHCPSInterfacePoolParaEntry 7 }

    hpnicfDHCPSInterfacePoolClientNetbiosType OBJECT-TYPE
        SYNTAX      INTEGER
            {
                 null(0),
                 bnode(1),
                 pnode(2),
                 mnode(4),
                 hnode(8)
            }
        MAX-ACCESS  read-write
        STATUS      current
        DESCRIPTION
            "NetBios node type for DHCP clients."
        DEFVAL { 0 }
        ::= { hpnicfDHCPSInterfacePoolParaEntry 8 }

    hpnicfDHCPSInterfacePoolClientNbnsIPString OBJECT-TYPE
        SYNTAX      OCTET STRING(SIZE(0..129))
        MAX-ACCESS  read-write
        STATUS      current
        DESCRIPTION
            "String of NetBios server ip addresses for DHCP
            clients. Since mostly 8 ip can be configured for
            a pool totally, so a string is defined to get or
            configure 8 ip at a time."
        ::= { hpnicfDHCPSInterfacePoolParaEntry 9 }

    hpnicfDHCPSInterfacePoolClientNbnsIPUndo OBJECT-TYPE
        SYNTAX      IpAddress
        MAX-ACCESS  read-write
        STATUS      current
        DESCRIPTION
            "A NetBios server ip address to delete. This
            object is only for deleting a given ip of NetBios
            server."
        ::= { hpnicfDHCPSInterfacePoolParaEntry 10 }

    hpnicfDHCPSInterfacePoolParaUndoFlag OBJECT-TYPE
        SYNTAX      INTEGER
            {
                undoDomain(1),
                undoLease(2),
                undoDns(4),
                undoNbns(5),
                undoNbType(6)
            }
        MAX-ACCESS  read-write
        STATUS      current
        DESCRIPTION
            "Flag of undo-operation for
            hpnicfDHCPSInterfacePoolParaTable."
        ::= { hpnicfDHCPSInterfacePoolParaEntry 11 }

    hpnicfDHCPSInterfacePoolIPInUseReset OBJECT-TYPE
        SYNTAX      INTEGER
            {
                reset(1)
            }
        MAX-ACCESS  read-write
        STATUS      current
        DESCRIPTION
            "Reset the auto binding ip of the given interface
            pool for DHCP server."
        ::= { hpnicfDHCPSInterfacePoolParaEntry 12 }

--  =====================================================================
-- 7th Table of hpnicfDHCPServerMibObject: hpnicfDHCPSInterfacePoolOptionTable
-- =====================================================================
    hpnicfDHCPSInterfacePoolOptionTable OBJECT-TYPE
        SYNTAX      SEQUENCE OF HpnicfDHCPSInterfacePoolOptionEntry
        MAX-ACCESS  not-accessible
        STATUS      current
        DESCRIPTION
            "A table for configuring options to DHCP interface pools."
        ::= { hpnicfDHCPServerMibObject 7 }

    hpnicfDHCPSInterfacePoolOptionEntry OBJECT-TYPE
        SYNTAX      HpnicfDHCPSInterfacePoolOptionEntry
        MAX-ACCESS  not-accessible
        STATUS      current
        DESCRIPTION
            "An entry of objects for configuring options
            to DHCP interface pools.
            The index of this entry is the ifIndex of ethernet."
        INDEX { ifIndex, hpnicfDHCPSInterfacePoolOptionCode }
        ::= { hpnicfDHCPSInterfacePoolOptionTable 1 }

    HpnicfDHCPSInterfacePoolOptionEntry ::=
        SEQUENCE
            {
                hpnicfDHCPSInterfacePoolOptionCode         INTEGER,
                hpnicfDHCPSInterfacePoolOptionType         INTEGER,
                hpnicfDHCPSInterfacePoolOptionAscii        OCTET STRING,
                hpnicfDHCPSInterfacePoolOptionHexString    OCTET STRING,
                hpnicfDHCPSInterfacePoolOptionIPString     OCTET STRING,
                hpnicfDHCPSInterfacePoolOptionRowStatus    RowStatus
             }

    hpnicfDHCPSInterfacePoolOptionCode OBJECT-TYPE
        SYNTAX      INTEGER(1..254)
        MAX-ACCESS  read-only
        STATUS      current
        DESCRIPTION
            "Option Code."
        ::= { hpnicfDHCPSInterfacePoolOptionEntry 1 }

    hpnicfDHCPSInterfacePoolOptionType OBJECT-TYPE
        SYNTAX      INTEGER
            {
                ascii(1),
                hex(2),
                ip(3)
            }
        MAX-ACCESS  read-create
        STATUS      current
        DESCRIPTION
            "Option type."
        ::= { hpnicfDHCPSInterfacePoolOptionEntry 2 }

    hpnicfDHCPSInterfacePoolOptionAscii OBJECT-TYPE
        SYNTAX      OCTET STRING(SIZE(0..63))
        MAX-ACCESS  read-create
        STATUS      current
        DESCRIPTION
            "Ascii string of an option."
        ::= { hpnicfDHCPSInterfacePoolOptionEntry 3 }

    hpnicfDHCPSInterfacePoolOptionHexString OBJECT-TYPE
        SYNTAX      OCTET STRING(SIZE(0..143))
        MAX-ACCESS  read-create
        STATUS      current
        DESCRIPTION
            "Hex string of an option. 1st to 16th hex strings,
            which are 2 bytes, 4 bytes, 6 bytes or 8 bytes,
            can be configured at most simultaneously.
            That means the format of each string
            must be '12', '1234', '123456' or '12345678'."
        ::= { hpnicfDHCPSInterfacePoolOptionEntry 4 }

    hpnicfDHCPSInterfacePoolOptionIPString OBJECT-TYPE
        SYNTAX      OCTET STRING(SIZE(0..129))
        MAX-ACCESS  read-create
        STATUS      current
        DESCRIPTION
            "Ip string of an option. 1 to 8 ip addresses  can
            be configured at most simultaneously."
        ::= { hpnicfDHCPSInterfacePoolOptionEntry 5 }

    hpnicfDHCPSInterfacePoolOptionRowStatus OBJECT-TYPE
        SYNTAX      RowStatus
        MAX-ACCESS  read-create
        STATUS      current
        DESCRIPTION
            "RowStatus. Three actions are used: active,
            createAndGo, destroy."
        ::= { hpnicfDHCPSInterfacePoolOptionEntry 6 }

--  =========================================================================
-- 8th Table of hpnicfDHCPServerMibObject: hpnicfDHCPSInterfacePoolStaticBindTable
-- =========================================================================
    hpnicfDHCPSInterfacePoolStaticBindTable OBJECT-TYPE
        SYNTAX      SEQUENCE OF HpnicfDHCPSInterfacePoolStaticBindEntry
        MAX-ACCESS  not-accessible
        STATUS      current
        DESCRIPTION
            "A table for configuring static binding to DHCP
            interface pools."
        ::= { hpnicfDHCPServerMibObject 8 }

    hpnicfDHCPSInterfacePoolStaticBindEntry OBJECT-TYPE
        SYNTAX      HpnicfDHCPSInterfacePoolStaticBindEntry
        MAX-ACCESS  not-accessible
        STATUS      current
        DESCRIPTION
            "An entry of objects for configuring static
            binding to DHCP interface pools.
            The index of this entry is the ifIndex of ethernet."
        INDEX { ifIndex, hpnicfDHCPSInterfacePoolStaticBindIP }
        ::= { hpnicfDHCPSInterfacePoolStaticBindTable 1 }

    HpnicfDHCPSInterfacePoolStaticBindEntry ::=
        SEQUENCE
            {
                hpnicfDHCPSInterfacePoolStaticBindIP           IpAddress,
                hpnicfDHCPSInterfacePoolStaticBindMac          MacAddress,
                hpnicfDHCPSInterfacePoolStaticBindRowStatus    RowStatus
            }

    hpnicfDHCPSInterfacePoolStaticBindIP OBJECT-TYPE
        SYNTAX      IpAddress
        MAX-ACCESS  read-only
        STATUS      current
        DESCRIPTION
            "Ip address in static binding for DHCP
            interface pools."
        ::= { hpnicfDHCPSInterfacePoolStaticBindEntry 1 }

    hpnicfDHCPSInterfacePoolStaticBindMac OBJECT-TYPE
        SYNTAX      MacAddress
        MAX-ACCESS  read-create
        STATUS      current
        DESCRIPTION
            "Hardware address in static binding for DHCP
            interface pools."
        ::= { hpnicfDHCPSInterfacePoolStaticBindEntry 2 }

    hpnicfDHCPSInterfacePoolStaticBindRowStatus OBJECT-TYPE
        SYNTAX      RowStatus
        MAX-ACCESS  read-create
        STATUS      current
        DESCRIPTION
            "RowStatus. Three actions are used: active,
            createAndGo, destroy."
        ::= { hpnicfDHCPSInterfacePoolStaticBindEntry 3 }

--  Part 3: For DHCP server
--
-- =================================================================
-- 9th Table of hpnicfDHCPServerMibObject: hpnicfDHCPSIPInUseTable
-- =================================================================
    hpnicfDHCPSIPInUseTable OBJECT-TYPE
        SYNTAX      SEQUENCE OF HpnicfDHCPSIPInUseEntry
        MAX-ACCESS  not-accessible
        STATUS      deprecated
        DESCRIPTION
            "A table for displaying the information of ip in use
            for DHCP server pools."
        ::= { hpnicfDHCPServerMibObject 9 }

    hpnicfDHCPSIPInUseEntry OBJECT-TYPE
        SYNTAX      HpnicfDHCPSIPInUseEntry
        MAX-ACCESS  not-accessible
        STATUS      deprecated
        DESCRIPTION
            "An entry of objects for displaying information
            of ip in use for DHCP server pools."
        INDEX { hpnicfDHCPSIPInUseHAddr }
        ::= { hpnicfDHCPSIPInUseTable 1 }

    HpnicfDHCPSIPInUseEntry ::=
        SEQUENCE
            {
                hpnicfDHCPSIPInUseHAddr        MacAddress,
                hpnicfDHCPSIPInUseIP           IpAddress,
                hpnicfDHCPSIPInUseEndLease     OCTET STRING,
                hpnicfDHCPSIPInUseType         INTEGER,
                hpnicfDHCPSIPInUsePoolName     OCTET STRING,
                hpnicfDHCPSIPInUseInterface    INTEGER,
                hpnicfDHCPSIPInUseVlan         INTEGER,
                hpnicfDHCPSIPInUseAtmpvc       INTEGER
            }

    hpnicfDHCPSIPInUseHAddr OBJECT-TYPE
        SYNTAX      MacAddress
        MAX-ACCESS  read-only
        STATUS      deprecated
        DESCRIPTION
            "Hardware address."
        ::= { hpnicfDHCPSIPInUseEntry 1 }

    hpnicfDHCPSIPInUseIP OBJECT-TYPE
        SYNTAX      IpAddress
        MAX-ACCESS  read-only
        STATUS      deprecated
        DESCRIPTION
            "Ip address in use."
        ::= { hpnicfDHCPSIPInUseEntry 2 }

    hpnicfDHCPSIPInUseEndLease OBJECT-TYPE
        SYNTAX      OCTET STRING(SIZE(1..20))
        MAX-ACCESS  read-only
        STATUS      deprecated
        DESCRIPTION
            "End time of lease.
            The structure of the OCTET STRING is
            month/day/year hour:munite:second --
            MM/DD/YYYY hh:mm:ss. "
        ::= { hpnicfDHCPSIPInUseEntry 3 }

    hpnicfDHCPSIPInUseType OBJECT-TYPE
        SYNTAX      INTEGER
            {
                manual(1),
                auto(2),
                release(3)
            }
        MAX-ACCESS  read-only
        STATUS      deprecated
        DESCRIPTION
            "Type of binding."
        ::= { hpnicfDHCPSIPInUseEntry 4 }

    hpnicfDHCPSIPInUsePoolName OBJECT-TYPE
        SYNTAX      OCTET STRING(SIZE(1..255))
        MAX-ACCESS  read-only
        STATUS      deprecated
        DESCRIPTION
            "Name of the DHCP server pool the ip belongs to."
        ::= { hpnicfDHCPSIPInUseEntry 5 }

    hpnicfDHCPSIPInUseInterface OBJECT-TYPE
        SYNTAX      INTEGER
        MAX-ACCESS  read-only
        STATUS      deprecated
        DESCRIPTION
            "Interface index information."
        ::= { hpnicfDHCPSIPInUseEntry 6 }

    hpnicfDHCPSIPInUseVlan OBJECT-TYPE
        SYNTAX      INTEGER(1..4094)
        MAX-ACCESS  read-only
        STATUS      deprecated
        DESCRIPTION
            "Vlan information."
        ::= { hpnicfDHCPSIPInUseEntry 7 }

    hpnicfDHCPSIPInUseAtmpvc OBJECT-TYPE
        SYNTAX      INTEGER
        MAX-ACCESS  read-only
        STATUS      deprecated
        DESCRIPTION
            "Pvc information."
        ::= { hpnicfDHCPSIPInUseEntry 8 }

--  =================================================================
-- 10th Table of hpnicfDHCPServerMibObject: hpnicfDHCPSForbiddenIPTable
-- =================================================================
    hpnicfDHCPSForbiddenIPTable OBJECT-TYPE
        SYNTAX      SEQUENCE OF HpnicfDHCPSForbiddenIPEntry
        MAX-ACCESS  not-accessible
        STATUS      current
        DESCRIPTION
            "A table for configuring forbidden ip to DHCP server."
        ::= { hpnicfDHCPServerMibObject 10 }

    hpnicfDHCPSForbiddenIPEntry OBJECT-TYPE
        SYNTAX      HpnicfDHCPSForbiddenIPEntry
        MAX-ACCESS  not-accessible
        STATUS      current
        DESCRIPTION
            "An entry for configuring forbidden ip to DHCP
            server."
        INDEX { hpnicfDHCPSForbiddenIPStart, hpnicfDHCPSForbiddenIPEnd }
        ::= { hpnicfDHCPSForbiddenIPTable 1 }

    HpnicfDHCPSForbiddenIPEntry ::=
        SEQUENCE
            {
                hpnicfDHCPSForbiddenIPStart        IpAddress,
                hpnicfDHCPSForbiddenIPEnd          IpAddress,
                hpnicfDHCPSForbiddenIPRowStatus    RowStatus
            }

    hpnicfDHCPSForbiddenIPStart OBJECT-TYPE
        SYNTAX      IpAddress
        MAX-ACCESS  read-only
        STATUS      current
        DESCRIPTION
            "Start ip of forbidden ip."
        ::= { hpnicfDHCPSForbiddenIPEntry 1 }

    hpnicfDHCPSForbiddenIPEnd OBJECT-TYPE
        SYNTAX      IpAddress
        MAX-ACCESS  read-only
        STATUS      current
        DESCRIPTION
            "End ip of forbidden ip."
        ::= { hpnicfDHCPSForbiddenIPEntry 2 }

    hpnicfDHCPSForbiddenIPRowStatus OBJECT-TYPE
        SYNTAX      RowStatus
        MAX-ACCESS  read-create
        STATUS      current
        DESCRIPTION
            "RowStatus. Three actions are used: active,
            createAndGo, destroy."
        ::= { hpnicfDHCPSForbiddenIPEntry 3 }

--  =================================================================
-- 11th Table of hpnicfDHCPServerMibObject: hpnicfDHCPSConflictIPTable
-- =================================================================
    hpnicfDHCPSConflictIPTable OBJECT-TYPE
        SYNTAX      SEQUENCE OF HpnicfDHCPSConflictIPEntry
        MAX-ACCESS  not-accessible
        STATUS      current
        DESCRIPTION
            "A table for displaying the information of conflict
            ip for DHCP server."
        ::= { hpnicfDHCPServerMibObject 11 }

    hpnicfDHCPSConflictIPEntry OBJECT-TYPE
        SYNTAX      HpnicfDHCPSConflictIPEntry
        MAX-ACCESS  not-accessible
        STATUS      current
        DESCRIPTION
            "An entry for displaying the information of
            conflict ip for DHCP server."
        INDEX { hpnicfDHCPSConflictIP }
        ::= { hpnicfDHCPSConflictIPTable 1 }

    HpnicfDHCPSConflictIPEntry ::=
        SEQUENCE
            {
                hpnicfDHCPSConflictIP              IpAddress,
                hpnicfDHCPSConflictIPType          INTEGER,
                hpnicfDHCPSConflictIPDetectTime    OCTET STRING
            }

    hpnicfDHCPSConflictIP OBJECT-TYPE
        SYNTAX      IpAddress
        MAX-ACCESS  read-only
        STATUS      current
        DESCRIPTION
            "Conflict ip."
        ::= { hpnicfDHCPSConflictIPEntry 1 }

    hpnicfDHCPSConflictIPType OBJECT-TYPE
        SYNTAX      INTEGER
            {
                ping(1),
                arp(2)
            }
        MAX-ACCESS  read-only
        STATUS      current
        DESCRIPTION
            "Type of the detection of conflict ip."
        ::= { hpnicfDHCPSConflictIPEntry 2 }

    hpnicfDHCPSConflictIPDetectTime OBJECT-TYPE
        SYNTAX      OCTET STRING(SIZE(1..20))
        MAX-ACCESS  read-only
        STATUS      current
        DESCRIPTION
            "Time when the conflict is detected.
            The structure of the OCTET STRING is
            month/day/year hour:munite:second --
            MM/DD/YYYY hh:mm:ss."
        ::= { hpnicfDHCPSConflictIPEntry 3 }

--  Part 4: Non-table object
--
    hpnicfDHCPSServiceStatus OBJECT-TYPE
        SYNTAX      HpnicfDhcpSEnabledStatus
        MAX-ACCESS  read-write
        STATUS      current
        DESCRIPTION
            "The status of DHCP service."
        DEFVAL { enabled }
        ::= { hpnicfDHCPServerMibObject 12 }

    hpnicfDHCPSDetectingServerStatus OBJECT-TYPE
        SYNTAX      HpnicfDhcpSEnabledStatus
        MAX-ACCESS  read-write
        STATUS      current
        DESCRIPTION
            "The status of DHCP servers detecting function."
        DEFVAL { disabled }
        ::= { hpnicfDHCPServerMibObject 13 }

    hpnicfDHCPSPingNum OBJECT-TYPE
        SYNTAX      INTEGER(0..10)
        MAX-ACCESS  read-write
        STATUS      current
        DESCRIPTION
            "The number of ping packets sent out."
        DEFVAL { 2 }
        ::= { hpnicfDHCPServerMibObject 14 }

    hpnicfDHCPSPingTimeout OBJECT-TYPE
        SYNTAX      INTEGER(0..10000)
        MAX-ACCESS  read-write
        STATUS      current
        DESCRIPTION
            "The delay for the reply of a ping packet.
            Unit: millisecond."
        DEFVAL { 500 }
        ::= { hpnicfDHCPServerMibObject 15 }

    hpnicfDHCPSWriteDataStatus OBJECT-TYPE
        SYNTAX      HpnicfDhcpSEnabledStatus
        MAX-ACCESS  read-write
        STATUS      current
        DESCRIPTION
            "The status of the function writing data to the
            harddisk."
        DEFVAL { disabled }
        ::= { hpnicfDHCPServerMibObject 16 }

    hpnicfDHCPSWriteDataDirection OBJECT-TYPE
        SYNTAX      OCTET STRING(SIZE(1..255))
        MAX-ACCESS  read-only
        STATUS      current
        DESCRIPTION
            "The direction of writing data to a harddisk."
        ::= { hpnicfDHCPServerMibObject 17 }

    hpnicfDHCPSWriteDataDelay OBJECT-TYPE
        SYNTAX      INTEGER(300..86400)
        MAX-ACCESS  read-write
        STATUS      current
        DESCRIPTION
            "The allowable delay of writing data to the
            harddisk. Unit: second."
        DEFVAL { 300 }
        ::= { hpnicfDHCPServerMibObject 18 }

    hpnicfDHCPSWriteDataRecover OBJECT-TYPE
        SYNTAX      HpnicfDhcpSEnabledStatus
        MAX-ACCESS  read-write
        STATUS      current
        DESCRIPTION
            "The flag used to recover DHCP data with the data on
            the harddisk."
        ::= { hpnicfDHCPServerMibObject 19 }

    hpnicfDHCPSIPInUseResetIP OBJECT-TYPE
        SYNTAX      IpAddress
        MAX-ACCESS  read-write
        STATUS      current
        DESCRIPTION
            "An ip in use that will be cleared. 0 returned for SET
            operation."
        ::= { hpnicfDHCPServerMibObject 20 }

    hpnicfDHCPSConflictIPResetIP OBJECT-TYPE
        SYNTAX      IpAddress
        MAX-ACCESS  read-write
        STATUS      current
        DESCRIPTION
            "A conflict ip that will be cleared. 0 returned for
            SET operation."
        ::= { hpnicfDHCPServerMibObject 21 }

    hpnicfDHCPSIPResetFlag OBJECT-TYPE
        SYNTAX      INTEGER
            {
                invalid(0),
                ipInUse(1),
                conflictIp(2)
            }
        MAX-ACCESS  read-write
        STATUS      current
        DESCRIPTION
            "A flag that descript the reset operation."
        ::= { hpnicfDHCPServerMibObject 22 }

    hpnicfDHCPSGlobalPoolNumber OBJECT-TYPE
        SYNTAX      Integer32
        MAX-ACCESS  read-only
        STATUS      current
        DESCRIPTION
            "The total number of DHCP server global-pools."
        ::= { hpnicfDHCPServerMibObject 23 }

    hpnicfDHCPSGlobalPoolAutoBindingNum OBJECT-TYPE
        SYNTAX      Integer32
        MAX-ACCESS  read-only
        STATUS      current
        DESCRIPTION
            "The total number of auto binding ip in DHCP server global-pools."
        ::= { hpnicfDHCPServerMibObject 24 }

    hpnicfDHCPSGlobalPoolManualBindingNum OBJECT-TYPE
        SYNTAX      Integer32
        MAX-ACCESS  read-only
        STATUS      current
        DESCRIPTION
            "The total number of manual binding ip in DHCP
            server global-pools."
        ::= { hpnicfDHCPServerMibObject 25 }

    hpnicfDHCPSGlobalPoolExpiredBindingNum OBJECT-TYPE
        SYNTAX      Integer32
        MAX-ACCESS  read-only
        STATUS      current
        DESCRIPTION
            "The total number of expired binding ip in DHCP
            server global-pools."
        ::= { hpnicfDHCPServerMibObject 26 }

    hpnicfDHCPSInterfacePoolNumber OBJECT-TYPE
        SYNTAX      Integer32
        MAX-ACCESS  read-only
        STATUS      current
        DESCRIPTION
            "The total number of DHCP server interface-pools."
        ::= { hpnicfDHCPServerMibObject 27 }

    hpnicfDHCPSInterfacePoolAutoBindingNum OBJECT-TYPE
        SYNTAX      Integer32
        MAX-ACCESS  read-only
        STATUS      current
        DESCRIPTION
            "The total number of auto binding ip in DHCP server
            interface-pools."
        ::= { hpnicfDHCPServerMibObject 28 }

    hpnicfDHCPSInterfacePoolManualBindingNum OBJECT-TYPE
        SYNTAX      Integer32
        MAX-ACCESS  read-only
        STATUS      current
        DESCRIPTION
            "The total number of manual binding ip in DHCP server
            interface-pools."
        ::= { hpnicfDHCPServerMibObject 29 }

    hpnicfDHCPSInterfacePoolExpiredBindingNum OBJECT-TYPE
        SYNTAX      Integer32
        MAX-ACCESS  read-only
        STATUS      current
        DESCRIPTION
            "The total number of expired binding ip in DHCP server
            interface-pools."
        ::= { hpnicfDHCPServerMibObject 30 }

    hpnicfDHCPSBadPktNum OBJECT-TYPE
        SYNTAX      Integer32
        MAX-ACCESS  read-only
        STATUS      current
        DESCRIPTION
            "The total number of the bad packets received."
        ::= { hpnicfDHCPServerMibObject 31 }

    hpnicfDHCPSBootRequestPktNum OBJECT-TYPE
        SYNTAX      Integer32
        MAX-ACCESS  read-only
        STATUS      current
        DESCRIPTION
            "The total number of the packets received by DHCP
            Server from DHCP clients."
        ::= { hpnicfDHCPServerMibObject 32 }

    hpnicfDHCPSDiscoverPktNum OBJECT-TYPE
        SYNTAX      Integer32
        MAX-ACCESS  read-only
        STATUS      current
        DESCRIPTION
            "The total number of the DHCP Discover packets
            received from the DHCP clients."
        ::= { hpnicfDHCPServerMibObject 33 }

    hpnicfDHCPSRequestPktNum OBJECT-TYPE
        SYNTAX      Integer32
        MAX-ACCESS  read-only
        STATUS      current
        DESCRIPTION
            "The total number of the DHCP Request packets
            received from the DHCP clients."
        ::= { hpnicfDHCPServerMibObject 34 }

    hpnicfDHCPSDeclinePktNum OBJECT-TYPE
        SYNTAX      Integer32
        MAX-ACCESS  read-only
        STATUS      current
        DESCRIPTION
            "The total number of the DHCP Decline packets
            received from the DHCP clients."
        ::= { hpnicfDHCPServerMibObject 35 }

    hpnicfDHCPSReleasePktNum OBJECT-TYPE
        SYNTAX      Integer32
        MAX-ACCESS  read-only
        STATUS      current
        DESCRIPTION
            "The total number of the DHCP Release packets
            received from the DHCP clients."
        ::= { hpnicfDHCPServerMibObject 36 }

    hpnicfDHCPSInformPktNum OBJECT-TYPE
        SYNTAX      Integer32
        MAX-ACCESS  read-only
        STATUS      current
        DESCRIPTION
            "The total number of the DHCP Inform packets
            received from the DHCP clients."
        ::= { hpnicfDHCPServerMibObject 37 }

    hpnicfDHCPSBootReplyPktNum OBJECT-TYPE
        SYNTAX      Integer32
        MAX-ACCESS  read-only
        STATUS      current
        DESCRIPTION
            "The total number of the packets sent by DHCP server
            to DHCP clients."
        ::= { hpnicfDHCPServerMibObject 38 }

    hpnicfDHCPSOfferPktNum OBJECT-TYPE
        SYNTAX      Integer32
        MAX-ACCESS  read-only
        STATUS      current
        DESCRIPTION
            "The total number of the DHCP Offer packets
            sent by the DHCP server."
        ::= { hpnicfDHCPServerMibObject 39 }

    hpnicfDHCPSAckPktNum OBJECT-TYPE
        SYNTAX      Integer32
        MAX-ACCESS  read-only
        STATUS      current
        DESCRIPTION
            "The total number of the DHCP Ack packets
            sent by the DHCP server."
        ::= { hpnicfDHCPServerMibObject 40 }

    hpnicfDHCPSNakPktNum OBJECT-TYPE
        SYNTAX      Integer32
        MAX-ACCESS  read-only
        STATUS      current
        DESCRIPTION
            "The total number of the DHCP Nak packets
            sent by the DHCP server."
        ::= { hpnicfDHCPServerMibObject 41 }

    hpnicfDHCPSStatisticsReset OBJECT-TYPE
        SYNTAX      INTEGER
            {
                reset(1)
            }
        MAX-ACCESS  read-write
        STATUS      current
        DESCRIPTION
            "Reset the above statistic information of packets
            received and sent by the DHCP server."
        ::= { hpnicfDHCPServerMibObject 42 }

-- =================================================================
-- 43th Table of hpnicfDHCPServerMibObject: hpnicfDHCPSIPInUseTableEx
-- =================================================================
    hpnicfDHCPSIPInUseExTable OBJECT-TYPE
        SYNTAX SEQUENCE OF HpnicfDHCPSIPInUseExEntry
        MAX-ACCESS not-accessible
        STATUS current
        DESCRIPTION
            "A table for displaying the information of ip in use
            for DHCP Server pools. "
        ::= { hpnicfDHCPServerMibObject 43 }

    hpnicfDHCPSIPInUseExEntry OBJECT-TYPE
        SYNTAX      HpnicfDHCPSIPInUseExEntry
        MAX-ACCESS  not-accessible
        STATUS      current
        DESCRIPTION
            "An entry of objects for displaying information
            of ip in use for DHCP server pools."
        INDEX { hpnicfDHCPSIPInUseHAddrEx, hpnicfDHCPSIPInUseVlanIdEx }
        ::= { hpnicfDHCPSIPInUseExTable 1 }

    HpnicfDHCPSIPInUseExEntry ::=
        SEQUENCE
            {
                hpnicfDHCPSIPInUseHAddrEx               MacAddress,
                hpnicfDHCPSIPInUseVlanIdEx              INTEGER,
                hpnicfDHCPSIPInUseIPEx                  IpAddress,
                hpnicfDHCPSIPInUseEndLeaseEx            OCTET STRING,
                hpnicfDHCPSIPInUseTypeEx                INTEGER,
                hpnicfDHCPSIPInUsePoolNameEx            OCTET STRING,
                hpnicfDHCPSIPInUseIfIndexEx             INTEGER,
                hpnicfDHCPSIPInUseServerPortVlanIdEx    INTEGER,
                hpnicfDHCPSIPInUseAtmpvcEx              INTEGER
            }

    hpnicfDHCPSIPInUseHAddrEx OBJECT-TYPE
        SYNTAX      MacAddress
        MAX-ACCESS  accessible-for-notify
        STATUS      current
        DESCRIPTION
            "Hardware address."
        ::= { hpnicfDHCPSIPInUseExEntry 1 }

    hpnicfDHCPSIPInUseVlanIdEx OBJECT-TYPE
        SYNTAX      INTEGER(1..4094|60000)
        MAX-ACCESS  accessible-for-notify
        STATUS      current
        DESCRIPTION
            "User's vlanID.
            60000 means that a client doesn't have vlanID or have an
            invalid vlanID."
        ::= { hpnicfDHCPSIPInUseExEntry 2 }

    hpnicfDHCPSIPInUseIPEx OBJECT-TYPE
        SYNTAX      IpAddress
        MAX-ACCESS  read-only
        STATUS      current
        DESCRIPTION
            "Ip address in use."
        ::= { hpnicfDHCPSIPInUseExEntry 3 }

    hpnicfDHCPSIPInUseEndLeaseEx OBJECT-TYPE
        SYNTAX      OCTET STRING(SIZE(1..20))
        MAX-ACCESS  read-only
        STATUS      current
        DESCRIPTION
            "End time of lease.
            The structure of the OCTET STRING is
            month/day/year hour:munite:second --
            MM/DD/YYYY hh:mm:ss."
        ::= { hpnicfDHCPSIPInUseExEntry 4 }

    hpnicfDHCPSIPInUseTypeEx OBJECT-TYPE
        SYNTAX      INTEGER
            {
                manual(1),
                auto(2),
                release(3)
            }
        MAX-ACCESS  read-only
        STATUS      current
        DESCRIPTION
            "Type of binding."
        ::= { hpnicfDHCPSIPInUseExEntry 5 }

    hpnicfDHCPSIPInUsePoolNameEx OBJECT-TYPE
        SYNTAX      OCTET STRING(SIZE(1..255))
        MAX-ACCESS  read-only
        STATUS      current
        DESCRIPTION
            "Name of the DHCP server pool the ip belongs to."
        ::= { hpnicfDHCPSIPInUseExEntry 6 }

    hpnicfDHCPSIPInUseIfIndexEx OBJECT-TYPE
        SYNTAX      INTEGER
        MAX-ACCESS  read-only
        STATUS      current
        DESCRIPTION
            "Interface index information."
        ::= { hpnicfDHCPSIPInUseExEntry 7 }

    hpnicfDHCPSIPInUseServerPortVlanIdEx OBJECT-TYPE
        SYNTAX      INTEGER(1..4094)
        MAX-ACCESS  read-only
        STATUS      current
        DESCRIPTION
            "Vlan information of port on server through
             which the client user accesses server."
        ::= { hpnicfDHCPSIPInUseExEntry 8 }

    hpnicfDHCPSIPInUseAtmpvcEx OBJECT-TYPE
        SYNTAX      INTEGER
        MAX-ACCESS  read-only
        STATUS      current
        DESCRIPTION
            "Pvc information."
        ::= { hpnicfDHCPSIPInUseExEntry 9 }

--  Conformance information
--
    hpnicfDHCPServerMIBConformance OBJECT IDENTIFIER ::= { hpnicfDHCPServerMib 2 }

    hpnicfDHCPServerMIBCompliances OBJECT IDENTIFIER ::= { hpnicfDHCPServerMIBConformance 1 }

    hpnicfDHCPServerMIBGroups OBJECT IDENTIFIER ::= { hpnicfDHCPServerMIBConformance 2 }

--  Units of conformance
--
    hpnicfDHCPServerMIBGroup OBJECT-GROUP
        OBJECTS { hpnicfDHCPSGlobalPoolName, hpnicfDHCPSGlobalPoolRowStatus, hpnicfDHCPSGlobalPoolType, hpnicfDHCPSGlobalPoolNetwork, hpnicfDHCPSGlobalPoolNetworkMask,
            hpnicfDHCPSGlobalPoolHostIPAddr, hpnicfDHCPSGlobalPoolHostMask, hpnicfDHCPSGlobalPoolHostHAddr, hpnicfDHCPSGlobalPoolConfigUndoFlag, hpnicfDHCPSGlobalPoolLeaseDay,
            hpnicfDHCPSGlobalPoolLeaseHour, hpnicfDHCPSGlobalPoolLeaseMinute, hpnicfDHCPSGlobalPoolLeaseUnlimited, hpnicfDHCPSGlobalPoolDomainName, hpnicfDHCPSGlobalPoolClientGatewayIPString,
            hpnicfDHCPSGlobalPoolClientGatewayIPUndo, hpnicfDHCPSGlobalPoolClientDNSIPString, hpnicfDHCPSGlobalPoolClientDNSIPUndo, hpnicfDHCPSGlobalPoolClientNetbiosType, hpnicfDHCPSGlobalPoolClientNbnsIPString,
            hpnicfDHCPSGlobalPoolClientNbnsIPUndo, hpnicfDHCPSGlobalPoolParaUndoFlag, hpnicfDHCPSGlobalPoolIPInUseReset, hpnicfDHCPSGlobalPoolOptionCode, hpnicfDHCPSGlobalPoolOptionType,
            hpnicfDHCPSGlobalPoolOptionAscii, hpnicfDHCPSGlobalPoolOptionHexString, hpnicfDHCPSGlobalPoolOptionIPString, hpnicfDHCPSGlobalPoolOptionRowStatus, hpnicfDHCPSGlobalTreeParentNodeName,
            hpnicfDHCPSGlobalTreeChildNodeName, hpnicfDHCPSGlobalTreePreSiblingNodeName, hpnicfDHCPSGlobalTreeSiblingNodeName, hpnicfDHCPSInterfacePoolLeaseDay, hpnicfDHCPSInterfacePoolLeaseHour,
            hpnicfDHCPSInterfacePoolLeaseMinute, hpnicfDHCPSInterfacePoolLeaseUnlimited, hpnicfDHCPSInterfacePoolDomainName, hpnicfDHCPSInterfacePoolClientDNSIPString, hpnicfDHCPSInterfacePoolClientDNSIPUndo,
            hpnicfDHCPSInterfacePoolClientNetbiosType, hpnicfDHCPSInterfacePoolClientNbnsIPString, hpnicfDHCPSInterfacePoolClientNbnsIPUndo, hpnicfDHCPSInterfacePoolParaUndoFlag, hpnicfDHCPSInterfacePoolIPInUseReset,
            hpnicfDHCPSInterfacePoolOptionCode, hpnicfDHCPSInterfacePoolOptionType, hpnicfDHCPSInterfacePoolOptionAscii, hpnicfDHCPSInterfacePoolOptionHexString, hpnicfDHCPSInterfacePoolOptionIPString,
            hpnicfDHCPSInterfacePoolOptionRowStatus, hpnicfDHCPSInterfacePoolStaticBindIP, hpnicfDHCPSInterfacePoolStaticBindMac, hpnicfDHCPSInterfacePoolStaticBindRowStatus, hpnicfDHCPSIPInUseHAddr,
            hpnicfDHCPSIPInUseIP, hpnicfDHCPSIPInUseEndLease, hpnicfDHCPSIPInUseType, hpnicfDHCPSIPInUsePoolName, hpnicfDHCPSIPInUseInterface,
            hpnicfDHCPSIPInUseVlan, hpnicfDHCPSIPInUseAtmpvc, hpnicfDHCPSForbiddenIPStart, hpnicfDHCPSForbiddenIPEnd, hpnicfDHCPSForbiddenIPRowStatus,
            hpnicfDHCPSConflictIP, hpnicfDHCPSConflictIPType, hpnicfDHCPSConflictIPDetectTime, hpnicfDHCPSServiceStatus, hpnicfDHCPSDetectingServerStatus,
            hpnicfDHCPSPingNum, hpnicfDHCPSPingTimeout, hpnicfDHCPSWriteDataStatus, hpnicfDHCPSWriteDataDirection, hpnicfDHCPSWriteDataDelay,
            hpnicfDHCPSWriteDataRecover, hpnicfDHCPSIPInUseResetIP, hpnicfDHCPSConflictIPResetIP, hpnicfDHCPSIPResetFlag, hpnicfDHCPSGlobalPoolNumber,
            hpnicfDHCPSGlobalPoolAutoBindingNum, hpnicfDHCPSGlobalPoolManualBindingNum, hpnicfDHCPSGlobalPoolExpiredBindingNum, hpnicfDHCPSInterfacePoolNumber, hpnicfDHCPSInterfacePoolAutoBindingNum,
            hpnicfDHCPSInterfacePoolManualBindingNum, hpnicfDHCPSInterfacePoolExpiredBindingNum, hpnicfDHCPSBadPktNum, hpnicfDHCPSBootRequestPktNum, hpnicfDHCPSDiscoverPktNum,
            hpnicfDHCPSRequestPktNum, hpnicfDHCPSDeclinePktNum, hpnicfDHCPSReleasePktNum, hpnicfDHCPSInformPktNum, hpnicfDHCPSBootReplyPktNum,
            hpnicfDHCPSOfferPktNum, hpnicfDHCPSAckPktNum, hpnicfDHCPSNakPktNum, hpnicfDHCPSStatisticsReset,hpnicfDHCPSIPInUseHAddrEx,hpnicfDHCPSIPInUseVlanIdEx,
            hpnicfDHCPSIPInUseIPEx, hpnicfDHCPSIPInUseEndLeaseEx,hpnicfDHCPSIPInUseTypeEx, hpnicfDHCPSIPInUsePoolNameEx, hpnicfDHCPSIPInUseIfIndexEx,
            hpnicfDHCPSIPInUseServerPortVlanIdEx, hpnicfDHCPSIPInUseAtmpvcEx }
        STATUS      current
        DESCRIPTION
            "The basic collection of objects providing management of
            DHCP server."
        ::= { hpnicfDHCPServerMIBGroups 1 }


    END
