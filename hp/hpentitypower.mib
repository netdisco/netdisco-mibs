HP-ENTITY-POWER-MIB  DEFINITIONS ::= BEGIN

IMPORTS
    MODULE-IDENTITY, OBJECT-TYPE, Unsigned32
        FROM SNMPv2-SMI

    MODULE-COMPLIANCE, OBJECT-GROUP
        FROM SNMPv2-CONF

    entPhysicalIndex
        FROM ENTITY-MIB

    hpSwitch
        FROM HP-ICF-OID;

hpEntityPowerMIB  MODULE-IDENTITY
    LAST-UPDATED "201004110000Z"  -- Apr 11, 2010
    ORGANIZATION "HP Networking"
    CONTACT-INFO "Hewlett-Packard Company
                  8000 Foothills Blvd.
                  Roseville, CA - 95747."
    DESCRIPTION  "This MIB defines HP proprietary objects that can be used to
                  set the power status of physical entities and report power
                  usage statistics."

    REVISION     "201004110000Z"  -- Apr 11, 2010
    DESCRIPTION  "Initial version of this MIB"
    ::= { hpSwitch 71 }

-- **********************************************************************
-- Entity Power Objects
-- **********************************************************************

    hpEntPowerObjects OBJECT IDENTIFIER ::= { hpEntityPowerMIB 1 }

    hpEntPowerTable OBJECT-TYPE
    SYNTAX      SEQUENCE OF HpEntPowerEntry
    MAX-ACCESS  not-accessible
    STATUS      current
    DESCRIPTION "A table of information about the power status of entities.
                 This is a sparse augment of the entPhysicalTable.  Entries
                 appear in this table for values of
                 entPhysicalClass [RFC4133] that in this implementation
                 are able to report any of the power state or status stored in
                 this table."
    ::= { hpEntPowerObjects 1 }

    hpEntPowerEntry OBJECT-TYPE
    SYNTAX      HpEntPowerEntry
    MAX-ACCESS  not-accessible
    STATUS      current
    DESCRIPTION "Power related information about this physical entity."
    INDEX       { entPhysicalIndex }
    ::= { hpEntPowerTable 1 }

    HpEntPowerEntry ::= 
        SEQUENCE {
            hpEntPowerMaxPowerUsage      Unsigned32,
            hpEntPowerMinPowerUsage      Unsigned32,
            hpEntPowerCurrentPowerUsage  Unsigned32
        }

    hpEntPowerMaxPowerUsage OBJECT-TYPE
        SYNTAX      Unsigned32
        UNITS       "Watts"
        MAX-ACCESS  read-only
        STATUS      current
        DESCRIPTION "This MIB object would return the maximum power
                     usage of this entity. This would typically correspond to
                     the maximum power rating of the entity."
        ::= { hpEntPowerEntry 1 }

    hpEntPowerMinPowerUsage OBJECT-TYPE
        SYNTAX      Unsigned32
        UNITS       "Watts"
        MAX-ACCESS  read-only
        STATUS      current
        DESCRIPTION "This MIB object would return the minimum power usage of
                     this entity. This is applicable only to those entities 
                     that can be administratively set to function in a low
                     power state."
        ::= { hpEntPowerEntry 2 }

    hpEntPowerCurrentPowerUsage OBJECT-TYPE
        SYNTAX      Unsigned32
        UNITS       "Watts"
        MAX-ACCESS  read-only
        STATUS      current
        DESCRIPTION "This MIB object returns the current power usage of this
                     entity. For entities that cannot be set to function in a
                     low power mode, the value returned by this object would be
                     the same as that of entPowerMaxPowerUsage. For entities
                     that are set to function in a low power mode, the value
                     returned would be the same as that of 
                     entPowerMinPowerUsage."
        ::= { hpEntPowerEntry 3 }

-- **********************************************************************
-- Conformance and Compliance
-- **********************************************************************

    hpEntPowerConformance OBJECT IDENTIFIER ::= { hpEntityPowerMIB 2 }

    hpEntPowerCompliances OBJECT IDENTIFIER
        ::= { hpEntPowerConformance 1 }

    hpEntPowerCompliance MODULE-COMPLIANCE
    STATUS      current
    DESCRIPTION "The compliance statement for systems supporting
                the HP Entity Power MIB."
    MODULE -- this module
    MANDATORY-GROUPS {
       hpEntPowerGroup
    }
    ::= { hpEntPowerCompliances 1 }

    hpEntPowerGroups OBJECT IDENTIFIER ::= { hpEntPowerConformance 2 }

    hpEntPowerGroup OBJECT-GROUP
        OBJECTS {
            hpEntPowerMaxPowerUsage,
            hpEntPowerMinPowerUsage,
            hpEntPowerCurrentPowerUsage
        }
    STATUS   current
    DESCRIPTION "HP proprietary Entity Power group."
    ::= { hpEntPowerGroups 1 }

END
