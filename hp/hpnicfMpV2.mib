-- =================================================================
-- Copyright (c) 2010-2014 Hewlett-Packard Development Company, L.P.
--
-- Description: This MIB file is used for querying MP (Multilink PPP)
--              link status information.
-- Reference:
-- Version: V1.1
-- History:
--   V1.0 Initial version 2013-07-15
--   V1.1 2013-10-08 updated by jinlei 07761/h3c
--        Added enum active(1) and inactive(2) to hpnicfMpMemberlinkMpStatusV2
-- =================================================================
HPN-ICF-MP-V2-MIB DEFINITIONS ::= BEGIN

IMPORTS
    hpnicfCommon
        FROM HPN-ICF-OID-MIB
    ifIndex
        FROM IF-MIB
    Integer32, Counter32, OBJECT-TYPE, MODULE-IDENTITY
        FROM SNMPv2-SMI
    DisplayString
        FROM SNMPv2-TC;

hpnicfMultilinkPPPV2 MODULE-IDENTITY
    LAST-UPDATED "201307150000Z"            -- July 15, 2013 at 00:00 GMT
    ORGANIZATION
        ""
    CONTACT-INFO
        ""
    DESCRIPTION
         "The HPN-ICF-MP-V2-MIB provides read access to MP(Multilink PPP) link
          status information. The information available through this MIB includes:
          the father channel, the bundled son channel, the slot on which son channels
          are bundled,
          the number of son channels, the bundle name,
          the statistics for lost fragments, reordered packets, unassigned packets,
          interleaved packets, and the received/sent sequence number, etc."
    REVISION "201307150000Z"        -- July 15, 2013 at 00:00 GMT
    DESCRIPTION
        "HPN-ICF-MP-V2-MIB module for managing MP(Multilink PPP)."
    ::= { hpnicfCommon 140 }


hpnicfMpObjectsV2 OBJECT IDENTIFIER ::= { hpnicfMultilinkPPPV2  1 }

hpnicfMpMultilinkV2Table OBJECT-TYPE
    SYNTAX SEQUENCE OF HpnicfMpMultilinkV2Entry
    MAX-ACCESS not-accessible
    STATUS current
    DESCRIPTION
        "This table describes the information of MP link.
         The index of this table is the interface index of MP group or
         VA (Virtual Access) interface."
    ::= { hpnicfMpObjectsV2 1 }

hpnicfMpMultilinkV2Entry OBJECT-TYPE
    SYNTAX HpnicfMpMultilinkV2Entry
    MAX-ACCESS not-accessible
    STATUS current
    DESCRIPTION
        "Each entry in this table describes the information of MP link.
         The available information includes:
         the father channel, the slot on which son channels are bundled,
         the number of bundled son channels,
         the statistics for lost fragments, reordered packets,
         unassigned packets, interleaved packets,
         and received/sent sequence number."
    INDEX { ifIndex }
    ::= { hpnicfMpMultilinkV2Table 1 }

HpnicfMpMultilinkV2Entry ::=
    SEQUENCE {
        hpnicfMpMultilinkDescrV2
            DisplayString,
        hpnicfMpBundleNameV2
            DisplayString,
        hpnicfMpBundledSlotV2
            Integer32,
        hpnicfMpBundledMemberCntV2
            Integer32,
        hpnicfMpLostFragmentsV2
            Counter32,
        hpnicfMpReorderedPktsV2
            Counter32,
        hpnicfMpUnassignedPktsV2
            Counter32,
        hpnicfMpInterleavedPktsV2
            Counter32,
        hpnicfMpRcvdSequenceV2
            Integer32,
        hpnicfMpSentSequenceV2
            Integer32
        }

hpnicfMpMultilinkDescrV2 OBJECT-TYPE
    SYNTAX DisplayString (SIZE (0..255))
    MAX-ACCESS read-only
    STATUS current
    DESCRIPTION
        "The interface name of the father interface on which son channels are bundled.
        It is the name of a Virtual Access or an MP group."
    ::= { hpnicfMpMultilinkV2Entry 1 }

hpnicfMpBundleNameV2 OBJECT-TYPE
    SYNTAX DisplayString (SIZE (0..255))
    MAX-ACCESS read-only
    STATUS current
    DESCRIPTION
        "The bundle name of the multilink.
        When authentication is configured, the bundle name is the authenticated
        user name; when authentication is not configured, the bundle name is
        multilink.
        "
    ::= { hpnicfMpMultilinkV2Entry 2 }

hpnicfMpBundledSlotV2 OBJECT-TYPE
    SYNTAX Integer32
    MAX-ACCESS read-only
    STATUS current
    DESCRIPTION
        "The slot on which son channels are bundled.
        "
    ::= { hpnicfMpMultilinkV2Entry 3 }

hpnicfMpBundledMemberCntV2 OBJECT-TYPE
    SYNTAX Integer32
    MAX-ACCESS read-only
    STATUS current
    DESCRIPTION
        "The number of the bundled son channel of the MP link. "
    ::= { hpnicfMpMultilinkV2Entry 4 }

hpnicfMpLostFragmentsV2 OBJECT-TYPE
    SYNTAX Counter32
    MAX-ACCESS read-only
    STATUS current
    DESCRIPTION
        "The number of fragments of the MP link discarded because
        bad fragments were received, or assembling the packet failed, etc."
    ::= { hpnicfMpMultilinkV2Entry 5 }

hpnicfMpReorderedPktsV2 OBJECT-TYPE
    SYNTAX Counter32
    MAX-ACCESS read-only
    STATUS current
    DESCRIPTION
        "The number of reordered incoming packets of the MP link.
        "
    ::= { hpnicfMpMultilinkV2Entry 6 }

hpnicfMpUnassignedPktsV2 OBJECT-TYPE
    SYNTAX Counter32
    MAX-ACCESS read-only
    STATUS current
    DESCRIPTION
        "The number of received packets of the MP link waiting for reordering.
        "
    ::= { hpnicfMpMultilinkV2Entry 7 }

hpnicfMpInterleavedPktsV2 OBJECT-TYPE
    SYNTAX Counter32
    MAX-ACCESS read-only
    STATUS current
    DESCRIPTION
        "The number of received packets of the MP link interleaved by the
        packets queued in RTPQ (Real-time Transport Protocol Queue) or
        LLQ (Low Latency Queue).
        "
    ::= { hpnicfMpMultilinkV2Entry 8 }

hpnicfMpRcvdSequenceV2 OBJECT-TYPE
    SYNTAX Integer32
    MAX-ACCESS read-only
    STATUS current
    DESCRIPTION
        "The current sequence number for the MP link to receive.
        "
    ::= { hpnicfMpMultilinkV2Entry 9 }

hpnicfMpSentSequenceV2 OBJECT-TYPE
    SYNTAX Integer32
    MAX-ACCESS read-only
    STATUS current
    DESCRIPTION
        "The current sequence number for the MP link to send.
        "
    ::= { hpnicfMpMultilinkV2Entry 10 }


hpnicfMpMemberlinkV2Table OBJECT-TYPE
    SYNTAX SEQUENCE OF HpnicfMpMemberlinkV2Entry
    MAX-ACCESS not-accessible
    STATUS current
    DESCRIPTION
        "This table describes the information of son channels of the MP link.
        The index of this table is the interface index of MP group or
        VA (Virtual Access) interface.
        "
    ::= { hpnicfMpObjectsV2 2 }

hpnicfMpMemberlinkV2Entry OBJECT-TYPE
    SYNTAX HpnicfMpMemberlinkV2Entry
    MAX-ACCESS not-accessible
    STATUS current
    DESCRIPTION
        "Each entry in this table describes the information of the bundled
        son channels of MP link. The available information includes:
        the interface index of the son channel,
        the interface name of the son channel.
        "
    INDEX { ifIndex, hpnicfMpMemberlinkSeqNumberV2 }
    ::= { hpnicfMpMemberlinkV2Table 1 }

HpnicfMpMemberlinkV2Entry ::=
    SEQUENCE {
        hpnicfMpMemberlinkSeqNumberV2
            Integer32,
        hpnicfMpMemberlinkIfIndexV2
            Integer32,
        hpnicfMpMemberlinkDescrV2
            DisplayString,
        hpnicfMpMemberlinkMpStatusV2
            INTEGER
    }

hpnicfMpMemberlinkSeqNumberV2 OBJECT-TYPE
    SYNTAX Integer32 (1..128)
    MAX-ACCESS read-only
    STATUS current
    DESCRIPTION
        "The bundled sequence number of the son channels of the MP link.
        This object is one of the index of the table.
        "
    ::= { hpnicfMpMemberlinkV2Entry 1 }

hpnicfMpMemberlinkIfIndexV2 OBJECT-TYPE
    SYNTAX Integer32
    MAX-ACCESS read-only
    STATUS current
    DESCRIPTION
        "The interface index of the son channels of the MP link.
        "
    ::= { hpnicfMpMemberlinkV2Entry 2 }

hpnicfMpMemberlinkDescrV2 OBJECT-TYPE
    SYNTAX DisplayString (SIZE (0..255))
    MAX-ACCESS read-only
    STATUS current
    DESCRIPTION
        "The interface name of the son channels of the MP link.
        "
    ::= { hpnicfMpMemberlinkV2Entry 3 }

hpnicfMpMemberlinkMpStatusV2 OBJECT-TYPE
    SYNTAX INTEGER
        {
            active(1),
            inactive(2)
        }
    MAX-ACCESS read-only
    STATUS current
    DESCRIPTION
        "The MP status of the son channels of the MP link.
        "
    ::= { hpnicfMpMemberlinkV2Entry 4 }

END
