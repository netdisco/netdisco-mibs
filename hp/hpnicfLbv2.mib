-- =================================================================
-- Copyright (c) 2010-2014 Hewlett-Packard Development Company, L.P.
--
-- Description: Private MIB File For LB
-- Reference:
-- Version: V1.0
-- History:
-- V1.0  2013-11 Initial Version created by y04448.
-- =================================================================
HPN-ICF-LBV2-MIB DEFINITIONS ::= BEGIN

IMPORTS
    hpnicfCommon
        FROM HPN-ICF-OID-MIB
    MODULE-IDENTITY, OBJECT-TYPE, Unsigned32, Counter64, NOTIFICATION-TYPE
        FROM SNMPv2-SMI         -- [RFC2578]
    RowStatus, DisplayString
        FROM SNMPv2-TC;         -- [RFC2578]

hpnicfLBv2 MODULE-IDENTITY
    LAST-UPDATED "201311010000Z"
    ORGANIZATION
        ""
    CONTACT-INFO
        ""
    DESCRIPTION
        "The private MIB file includes the LB information of
         the device."
    REVISION      "201311010000Z"
    DESCRIPTION
        "Initial revision of this MIB module."
    ::= { hpnicfCommon 148 }

hpnicfLBv2GlobalObjects OBJECT IDENTIFIER ::= { hpnicfLBv2 1 }

hpnicfLBv2TrapEnable OBJECT-TYPE
    SYNTAX      INTEGER {
         enabled     (1),
         disabled    (2)
    }
    MAX-ACCESS  read-write
    STATUS      current
    DESCRIPTION
        "Indicates whether the module of LB will generate
         traps for events defined in this MIB.  'enabled'
         results in SNMP traps; 'disabled', no traps are sent."
    DEFVAL { enabled }
    ::= { hpnicfLBv2GlobalObjects 1 }

hpnicfLBv2ActionTables OBJECT IDENTIFIER ::= { hpnicfLBv2 2 }
-- =================================================================
--    LB Action Table
-- =================================================================
hpnicfLBv2ActionTable OBJECT-TYPE
    SYNTAX SEQUENCE OF HpnicfLBv2ActionEntry
    MAX-ACCESS  not-accessible
    STATUS      current
    DESCRIPTION
        "Action table for LB."
    ::= { hpnicfLBv2ActionTables 1 }

hpnicfLBv2ActionEntry OBJECT-TYPE
    SYNTAX      HpnicfLBv2ActionEntry
    MAX-ACCESS  not-accessible
    STATUS      current
    DESCRIPTION
        "An entry contains the information of the action."
    INDEX {
            hpnicfLBv2ActionName
          }
    ::= { hpnicfLBv2ActionTable 1 }

HpnicfLBv2ActionEntry  ::=
    SEQUENCE{
        hpnicfLBv2ActionName                     DisplayString,
        hpnicfLBv2ActionDefaultSF                DisplayString,
        hpnicfLBv2ActionBackupSF                 DisplayString,
        hpnicfLBv2ActionInUseSF                  DisplayString,
        hpnicfLBv2ActionRowStatus                RowStatus
    }

hpnicfLBv2ActionName OBJECT-TYPE
    SYNTAX      DisplayString(SIZE(1..63))
    MAX-ACCESS  accessible-for-notify
    STATUS      current
    DESCRIPTION
        "Name of the action."
    ::= { hpnicfLBv2ActionEntry 1 }

hpnicfLBv2ActionDefaultSF OBJECT-TYPE
    SYNTAX      DisplayString(SIZE(0..63))
    MAX-ACCESS  read-create
    STATUS      current
    DESCRIPTION
        "Default server farm quoted by the action.  A zero length
         string indicates no default server farm has been assigned."
    ::= { hpnicfLBv2ActionEntry 2 }

hpnicfLBv2ActionBackupSF OBJECT-TYPE
    SYNTAX      DisplayString(SIZE(0..63))
    MAX-ACCESS  read-create
    STATUS      current
    DESCRIPTION
        "Backup server farm quoted by the action.  A zero length
         string indicates no backup server farm has been assigned."
    ::= { hpnicfLBv2ActionEntry 3 }

hpnicfLBv2ActionInUseSF OBJECT-TYPE
    SYNTAX      DisplayString(SIZE(0..63))
    MAX-ACCESS  read-only
    STATUS      current
    DESCRIPTION
        "Server farm in use quoted by the action."
    ::= { hpnicfLBv2ActionEntry 4 }

hpnicfLBv2ActionRowStatus OBJECT-TYPE
    SYNTAX      RowStatus
    MAX-ACCESS  read-create
    STATUS      current
    DESCRIPTION
        "Status of this conceptual row.  When create an action, default
         server farm and backup server farm are optional."
    ::= { hpnicfLBv2ActionEntry 5 }

hpnicfLBv2VSTables OBJECT IDENTIFIER ::= { hpnicfLBv2 3 }
-- =================================================================
--    LB Virtual Server Table
-- =================================================================
hpnicfLBv2VSTable OBJECT-TYPE
    SYNTAX SEQUENCE OF HpnicfLBv2VSEntry
    MAX-ACCESS  not-accessible
    STATUS      current
    DESCRIPTION
        "Virtual server table for LB."
    ::= { hpnicfLBv2VSTables 1 }

hpnicfLBv2VSEntry OBJECT-TYPE
    SYNTAX      HpnicfLBv2VSEntry
    MAX-ACCESS  not-accessible
    STATUS      current
    DESCRIPTION
        "An entry contains the information of the virtual server."
    INDEX {
            hpnicfLBv2VSName
          }
    ::= { hpnicfLBv2VSTable 1 }

HpnicfLBv2VSEntry  ::=
    SEQUENCE{
        hpnicfLBv2VSName                         DisplayString,
        hpnicfLBv2VSConnectionsLimit             Unsigned32,
        hpnicfLBv2VSConnectionsRateLimit         Unsigned32,
        hpnicfLBv2VSDefaultSF                    DisplayString,
        hpnicfLBv2VSBackupSF                     DisplayString,
        hpnicfLBv2VSInUseSF                      DisplayString,
        hpnicfLBv2VSRowStatus                    RowStatus
    }

hpnicfLBv2VSName OBJECT-TYPE
    SYNTAX      DisplayString(SIZE(1..63))
    MAX-ACCESS  accessible-for-notify
    STATUS      current
    DESCRIPTION
        "Name of the virtual server."
    ::= { hpnicfLBv2VSEntry 1 }

hpnicfLBv2VSConnectionsLimit OBJECT-TYPE
    SYNTAX      Unsigned32
    MAX-ACCESS  read-create
    STATUS      current
    DESCRIPTION
        "Max connections limit of the virtual server.  0 means there is
         no limit."
    DEFVAL { 0 }
    ::= { hpnicfLBv2VSEntry 2 }

hpnicfLBv2VSConnectionsRateLimit OBJECT-TYPE
    SYNTAX      Unsigned32
    MAX-ACCESS  read-create
    STATUS      current
    DESCRIPTION
        "Max connections rate limit of the virtual server.  0 means there is
         no limit."
    DEFVAL { 0 }
    ::= { hpnicfLBv2VSEntry 3 }

hpnicfLBv2VSDefaultSF OBJECT-TYPE
    SYNTAX      DisplayString(SIZE(0..63))
    MAX-ACCESS  read-create
    STATUS      current
    DESCRIPTION
        "Default server farm quoted by the virtual server.  A zero length
         string indicates no default server farm has been assigned."
    ::= { hpnicfLBv2VSEntry 4 }

hpnicfLBv2VSBackupSF OBJECT-TYPE
    SYNTAX      DisplayString(SIZE(0..63))
    MAX-ACCESS  read-create
    STATUS      current
    DESCRIPTION
        "Backup server farm quoted by the virtual server.  A zero length
         string indicates no backup server farm has been assigned."
    ::= { hpnicfLBv2VSEntry 5 }

hpnicfLBv2VSInUseSF OBJECT-TYPE
    SYNTAX      DisplayString(SIZE(0..63))
    MAX-ACCESS  read-only
    STATUS      current
    DESCRIPTION
        "Server farm in use quoted by the virtual server."
    ::= { hpnicfLBv2VSEntry 6 }

hpnicfLBv2VSRowStatus OBJECT-TYPE
    SYNTAX      RowStatus
    MAX-ACCESS  read-create
    STATUS      current
    DESCRIPTION
        "Status of this conceptual row.  When create an virtual server,
         default server farm and backup server farm are optional."
    ::= { hpnicfLBv2VSEntry 7 }

-- =================================================================
--    LB Virtual Server Statistic Table
-- =================================================================
hpnicfLBv2VSStatsTable OBJECT-TYPE
    SYNTAX SEQUENCE OF HpnicfLBv2VSStatsEntry
    MAX-ACCESS  not-accessible
    STATUS      current
    DESCRIPTION
        "Virtual server statistic table for LB."
    ::= { hpnicfLBv2VSTables 2 }

hpnicfLBv2VSStatsEntry OBJECT-TYPE
    SYNTAX      HpnicfLBv2VSStatsEntry
    MAX-ACCESS  not-accessible
    STATUS      current
    DESCRIPTION
        "An entry contains the statistic information of the virtual server."
    INDEX {
            hpnicfLBv2VSName,
            hpnicfLBv2VSStatChassis,
            hpnicfLBv2VSStatSlot,
            hpnicfLBv2VSStatCpuid
          }
    ::= { hpnicfLBv2VSStatsTable 1 }

HpnicfLBv2VSStatsEntry  ::=
    SEQUENCE{
        hpnicfLBv2VSStatChassis                  Unsigned32,
        hpnicfLBv2VSStatSlot                     Unsigned32,
        hpnicfLBv2VSStatCpuid                    Unsigned32,
        hpnicfLBv2VSStatTotalConnections         Counter64,
        hpnicfLBv2VSStatActiveConnections        Unsigned32,
        hpnicfLBv2VSStatClientSidePKTsIn         Counter64,
        hpnicfLBv2VSStatClientSidePKTsOut        Counter64,
        hpnicfLBv2VSStatDroppedPackets           Counter64,
        hpnicfLBv2VSStatClientSideBytesIn        Counter64,
        hpnicfLBv2VSStatClientSideBytesOut       Counter64,
        hpnicfLBv2VSStatReceivedRequests         Counter64,
        hpnicfLBv2VSStatSentResponses            Counter64,
        hpnicfLBv2VSStatConnectionsRate          Unsigned32
    }

hpnicfLBv2VSStatChassis OBJECT-TYPE
    SYNTAX      Unsigned32(0..255)
    MAX-ACCESS  accessible-for-notify
    STATUS      current
    DESCRIPTION
        "ID of the device that holds the card."
    ::= { hpnicfLBv2VSStatsEntry 1 }

hpnicfLBv2VSStatSlot OBJECT-TYPE
    SYNTAX      Unsigned32(0..255)
    MAX-ACCESS  accessible-for-notify
    STATUS      current
    DESCRIPTION
        "Member ID of the card on device."
    ::= { hpnicfLBv2VSStatsEntry 2 }

hpnicfLBv2VSStatCpuid OBJECT-TYPE
    SYNTAX      Unsigned32(0..255)
    MAX-ACCESS  accessible-for-notify
    STATUS      current
    DESCRIPTION
        "ID of the CPU on the card."
    ::= { hpnicfLBv2VSStatsEntry 3 }

hpnicfLBv2VSStatTotalConnections OBJECT-TYPE
    SYNTAX      Counter64
    MAX-ACCESS  read-only
    STATUS      current
    DESCRIPTION
        "Total number of connections that the virtual server received."
    ::= { hpnicfLBv2VSStatsEntry 4 }

hpnicfLBv2VSStatActiveConnections OBJECT-TYPE
    SYNTAX      Unsigned32
    MAX-ACCESS  read-only
    STATUS      current
    DESCRIPTION
        "Active connections that the virtual server received."
    ::= { hpnicfLBv2VSStatsEntry 5 }

hpnicfLBv2VSStatClientSidePKTsIn OBJECT-TYPE
    SYNTAX      Counter64
    MAX-ACCESS  read-only
    STATUS      current
    DESCRIPTION
        "Number of packets that the virtual server received from client."
    ::= { hpnicfLBv2VSStatsEntry 6 }

hpnicfLBv2VSStatClientSidePKTsOut OBJECT-TYPE
    SYNTAX      Counter64
    MAX-ACCESS  read-only
    STATUS      current
    DESCRIPTION
        "Number of packets that the virtual server sent to client."
    ::= { hpnicfLBv2VSStatsEntry 7 }

hpnicfLBv2VSStatDroppedPackets OBJECT-TYPE
    SYNTAX      Counter64
    MAX-ACCESS  read-only
    STATUS      current
    DESCRIPTION
        "Number of packets that the virtual server dropped."
    ::= { hpnicfLBv2VSStatsEntry 8 }

hpnicfLBv2VSStatClientSideBytesIn OBJECT-TYPE
    SYNTAX      Counter64
    UNITS       "byte"
    MAX-ACCESS  read-only
    STATUS      current
    DESCRIPTION
        "Number of bytes that the virtual server received from client."
    ::= { hpnicfLBv2VSStatsEntry 9 }

hpnicfLBv2VSStatClientSideBytesOut OBJECT-TYPE
    SYNTAX      Counter64
    UNITS       "byte"
    MAX-ACCESS  read-only
    STATUS      current
    DESCRIPTION
        "Number of bytes that the virtual server sent to client."
    ::= { hpnicfLBv2VSStatsEntry 10 }

hpnicfLBv2VSStatReceivedRequests OBJECT-TYPE
    SYNTAX      Counter64
    MAX-ACCESS  read-only
    STATUS      current
    DESCRIPTION
        "Number of requests that the virtual server received from client."
    ::= { hpnicfLBv2VSStatsEntry 11 }

hpnicfLBv2VSStatSentResponses OBJECT-TYPE
    SYNTAX      Counter64
    MAX-ACCESS  read-only
    STATUS      current
    DESCRIPTION
        "Number of responses that the virtual server sent to client."
    ::= { hpnicfLBv2VSStatsEntry 12 }

hpnicfLBv2VSStatConnectionsRate OBJECT-TYPE
    SYNTAX      Unsigned32
    UNITS       "cps"
    MAX-ACCESS  read-only
    STATUS      current
    DESCRIPTION
        "Connections rate of the virtual server."
    ::= { hpnicfLBv2VSStatsEntry 13 }

hpnicfLBv2RSTables OBJECT IDENTIFIER ::= { hpnicfLBv2 4 }
-- =================================================================
--    LB Real Server Table
-- =================================================================
hpnicfLBv2RSTable OBJECT-TYPE
    SYNTAX SEQUENCE OF HpnicfLBv2RSEntry
    MAX-ACCESS  not-accessible
    STATUS      current
    DESCRIPTION
        "Real server table for LB."
    ::= { hpnicfLBv2RSTables 1 }

hpnicfLBv2RSEntry OBJECT-TYPE
    SYNTAX      HpnicfLBv2RSEntry
    MAX-ACCESS  not-accessible
    STATUS      current
    DESCRIPTION
        "An entry contains the information of the real server."
    INDEX {
            hpnicfLBv2RSName
          }
    ::= { hpnicfLBv2RSTable 1 }

HpnicfLBv2RSEntry  ::=
    SEQUENCE{
        hpnicfLBv2RSName                         DisplayString,
        hpnicfLBv2RSRowStatus                    RowStatus
    }

hpnicfLBv2RSName OBJECT-TYPE
    SYNTAX      DisplayString(SIZE(1..63))
    MAX-ACCESS  accessible-for-notify
    STATUS      current
    DESCRIPTION
        "Name of the real server."
    ::= { hpnicfLBv2RSEntry 1 }

hpnicfLBv2RSRowStatus OBJECT-TYPE
    SYNTAX      RowStatus
    MAX-ACCESS  read-create
    STATUS      current
    DESCRIPTION
        "Status of this conceptual row."
    ::= { hpnicfLBv2RSEntry 2 }

-- =================================================================
--    LB Real Server Statistic Table
-- =================================================================
hpnicfLBv2RSStatsTable OBJECT-TYPE
    SYNTAX SEQUENCE OF HpnicfLBv2RSStatsEntry
    MAX-ACCESS  not-accessible
    STATUS      current
    DESCRIPTION
        "Real server statistic table for LB."
    ::= { hpnicfLBv2RSTables 2 }

hpnicfLBv2RSStatsEntry OBJECT-TYPE
    SYNTAX      HpnicfLBv2RSStatsEntry
    MAX-ACCESS  not-accessible
    STATUS      current
    DESCRIPTION
        "An entry contains the statistic information of the real server."
    INDEX {
            hpnicfLBv2RSName,
            hpnicfLBv2RSStatChassis,
            hpnicfLBv2RSStatSlot,
            hpnicfLBv2RSStatCpuid
          }
    ::= { hpnicfLBv2RSStatsTable 1 }

HpnicfLBv2RSStatsEntry  ::=
    SEQUENCE{
        hpnicfLBv2RSStatChassis                  Unsigned32,
        hpnicfLBv2RSStatSlot                     Unsigned32,
        hpnicfLBv2RSStatCpuid                    Unsigned32,
        hpnicfLBv2RSStatTotalConnections         Counter64,
        hpnicfLBv2RSStatActiveConnections        Unsigned32,
        hpnicfLBv2RSStatServerSidePKTsIn         Counter64,
        hpnicfLBv2RSStatServerSidePKTsOut        Counter64,
        hpnicfLBv2RSStatDroppedPackets           Counter64,
        hpnicfLBv2RSStatServerSideBytesIn        Counter64,
        hpnicfLBv2RSStatServerSideBytesOut       Counter64,
        hpnicfLBv2RSStatReceivedRequests         Counter64,
        hpnicfLBv2RSStatSentResponses            Counter64
    }

hpnicfLBv2RSStatChassis OBJECT-TYPE
    SYNTAX      Unsigned32(0..255)
    MAX-ACCESS  not-accessible
    STATUS      current
    DESCRIPTION
        "ID of the device that holds the card."
    ::= { hpnicfLBv2RSStatsEntry 1 }

hpnicfLBv2RSStatSlot OBJECT-TYPE
    SYNTAX      Unsigned32(0..255)
    MAX-ACCESS  not-accessible
    STATUS      current
    DESCRIPTION
        "Member ID of the card on device."
    ::= { hpnicfLBv2RSStatsEntry 2 }

hpnicfLBv2RSStatCpuid OBJECT-TYPE
    SYNTAX      Unsigned32(0..255)
    MAX-ACCESS  not-accessible
    STATUS      current
    DESCRIPTION
        "ID of the CPU on the card."
    ::= { hpnicfLBv2RSStatsEntry 3 }

hpnicfLBv2RSStatTotalConnections OBJECT-TYPE
    SYNTAX      Counter64
    MAX-ACCESS  read-only
    STATUS      current
    DESCRIPTION
        "Total number of connections that the real server received."
    ::= { hpnicfLBv2RSStatsEntry 4 }

hpnicfLBv2RSStatActiveConnections OBJECT-TYPE
    SYNTAX      Unsigned32
    MAX-ACCESS  read-only
    STATUS      current
    DESCRIPTION
        "Active connections that the real server received."
    ::= { hpnicfLBv2RSStatsEntry 5 }

hpnicfLBv2RSStatServerSidePKTsIn OBJECT-TYPE
    SYNTAX      Counter64
    MAX-ACCESS  read-only
    STATUS      current
    DESCRIPTION
        "Number of packets that the real server received from device."
    ::= { hpnicfLBv2RSStatsEntry 6 }

hpnicfLBv2RSStatServerSidePKTsOut OBJECT-TYPE
    SYNTAX      Counter64
    MAX-ACCESS  read-only
    STATUS      current
    DESCRIPTION
        "Number of packets that the real server sent."
    ::= { hpnicfLBv2RSStatsEntry 7 }

hpnicfLBv2RSStatDroppedPackets OBJECT-TYPE
    SYNTAX      Counter64
    MAX-ACCESS  read-only
    STATUS      current
    DESCRIPTION
        "Number of packets that the real server dropped."
    ::= { hpnicfLBv2RSStatsEntry 8 }

hpnicfLBv2RSStatServerSideBytesIn OBJECT-TYPE
    SYNTAX      Counter64
    UNITS       "byte"
    MAX-ACCESS  read-only
    STATUS      current
    DESCRIPTION
        "Number of bytes that the real server received from device."
    ::= { hpnicfLBv2RSStatsEntry 9 }

hpnicfLBv2RSStatServerSideBytesOut OBJECT-TYPE
    SYNTAX      Counter64
    UNITS       "byte"
    MAX-ACCESS  read-only
    STATUS      current
    DESCRIPTION
        "Number of bytes that the real server sent."
    ::= { hpnicfLBv2RSStatsEntry 10 }

hpnicfLBv2RSStatReceivedRequests OBJECT-TYPE
    SYNTAX      Counter64
    MAX-ACCESS  read-only
    STATUS      current
    DESCRIPTION
        "Number of requests that the real server received from device."
    ::= { hpnicfLBv2RSStatsEntry 11 }

hpnicfLBv2RSStatSentResponses OBJECT-TYPE
    SYNTAX      Counter64
    MAX-ACCESS  read-only
    STATUS      current
    DESCRIPTION
        "Number of responses that the real server sent to device."
    ::= { hpnicfLBv2RSStatsEntry 12 }

hpnicfLBv2SFTables OBJECT IDENTIFIER ::= { hpnicfLBv2 5 }
-- =================================================================
--    LB Server Farm Table
-- =================================================================
hpnicfLBv2SFTable OBJECT-TYPE
    SYNTAX SEQUENCE OF HpnicfLBv2SFEntry
    MAX-ACCESS  not-accessible
    STATUS      current
    DESCRIPTION
        "Server farm table for LB."
    ::= { hpnicfLBv2SFTables 1 }

hpnicfLBv2SFEntry OBJECT-TYPE
    SYNTAX      HpnicfLBv2SFEntry
    MAX-ACCESS  not-accessible
    STATUS      current
    DESCRIPTION
        "An entry contains the information of the server farm."
    INDEX {
            hpnicfLBv2SFName
          }
    ::= { hpnicfLBv2SFTable 1 }

HpnicfLBv2SFEntry  ::=
    SEQUENCE{
        hpnicfLBv2SFName                         DisplayString,
        hpnicfLBv2SFRowStatus                    RowStatus
    }

hpnicfLBv2SFName OBJECT-TYPE
    SYNTAX      DisplayString(SIZE(1..63))
    MAX-ACCESS  accessible-for-notify
    STATUS      current
    DESCRIPTION
        "Name of the server farm."
    ::= { hpnicfLBv2SFEntry 1 }

hpnicfLBv2SFRowStatus OBJECT-TYPE
    SYNTAX      RowStatus
    MAX-ACCESS  read-create
    STATUS      current
    DESCRIPTION
        "Status of this conceptual row."
    ::= { hpnicfLBv2SFEntry 2 }

-- =================================================================
--    LB Server Farm Statistic Table
-- =================================================================
hpnicfLBv2SFStatsTable OBJECT-TYPE
    SYNTAX SEQUENCE OF HpnicfLBv2SFStatsEntry
    MAX-ACCESS  not-accessible
    STATUS      current
    DESCRIPTION
        "Server farm statistic for LB."
    ::= { hpnicfLBv2SFTables 2 }

hpnicfLBv2SFStatsEntry OBJECT-TYPE
    SYNTAX      HpnicfLBv2SFStatsEntry
    MAX-ACCESS  not-accessible
    STATUS      current
    DESCRIPTION
        "An entry contains the statistic information of the server farm."
    INDEX {
            hpnicfLBv2SFName,
            hpnicfLBv2SFStatChassis,
            hpnicfLBv2SFStatSlot,
            hpnicfLBv2SFStatCpuid
          }
    ::= { hpnicfLBv2SFStatsTable 1 }

HpnicfLBv2SFStatsEntry  ::=
    SEQUENCE{
        hpnicfLBv2SFStatChassis                  Unsigned32,
        hpnicfLBv2SFStatSlot                     Unsigned32,
        hpnicfLBv2SFStatCpuid                    Unsigned32,
        hpnicfLBv2SFStatTotalConnections         Counter64,
        hpnicfLBv2SFStatActiveConnections        Unsigned32,
        hpnicfLBv2SFStatServerSidePKTsIn         Counter64,
        hpnicfLBv2SFStatServerSidePKTsOut        Counter64,
        hpnicfLBv2SFStatDroppedPackets           Counter64,
        hpnicfLBv2SFStatServerSideBytesIn        Counter64,
        hpnicfLBv2SFStatServerSideBytesOut       Counter64,
        hpnicfLBv2SFStatReceivedRequests         Counter64,
        hpnicfLBv2SFStatSentResponses            Counter64
    }

hpnicfLBv2SFStatChassis OBJECT-TYPE
    SYNTAX      Unsigned32(0..255)
    MAX-ACCESS  not-accessible
    STATUS      current
    DESCRIPTION
        "ID of the device that holds the card."
    ::= { hpnicfLBv2SFStatsEntry 1 }

hpnicfLBv2SFStatSlot OBJECT-TYPE
    SYNTAX      Unsigned32(0..255)
    MAX-ACCESS  not-accessible
    STATUS      current
    DESCRIPTION
        "Member ID of the card on device."
    ::= { hpnicfLBv2SFStatsEntry 2 }

hpnicfLBv2SFStatCpuid OBJECT-TYPE
    SYNTAX      Unsigned32(0..255)
    MAX-ACCESS  not-accessible
    STATUS      current
    DESCRIPTION
        "ID of the CPU on the card."
    ::= { hpnicfLBv2SFStatsEntry 3 }

hpnicfLBv2SFStatTotalConnections OBJECT-TYPE
    SYNTAX      Counter64
    MAX-ACCESS  read-only
    STATUS      current
    DESCRIPTION
        "Total number of connections that the server farm received."
    ::= { hpnicfLBv2SFStatsEntry 4 }

hpnicfLBv2SFStatActiveConnections OBJECT-TYPE
    SYNTAX      Unsigned32
    MAX-ACCESS  read-only
    STATUS      current
    DESCRIPTION
        "Active connections that the server farm received."
    ::= { hpnicfLBv2SFStatsEntry 5 }

hpnicfLBv2SFStatServerSidePKTsIn OBJECT-TYPE
    SYNTAX      Counter64
    MAX-ACCESS  read-only
    STATUS      current
    DESCRIPTION
        "Number of packets that the server farm received from device."
    ::= { hpnicfLBv2SFStatsEntry 6 }

hpnicfLBv2SFStatServerSidePKTsOut OBJECT-TYPE
    SYNTAX      Counter64
    MAX-ACCESS  read-only
    STATUS      current
    DESCRIPTION
        "Number of packets that the server farm sent."
    ::= { hpnicfLBv2SFStatsEntry 7 }

hpnicfLBv2SFStatDroppedPackets OBJECT-TYPE
    SYNTAX      Counter64
    MAX-ACCESS  read-only
    STATUS      current
    DESCRIPTION
        "Number of packets that the server farm dropped."
    ::= { hpnicfLBv2SFStatsEntry 8 }

hpnicfLBv2SFStatServerSideBytesIn OBJECT-TYPE
    SYNTAX      Counter64
    UNITS       "byte"
    MAX-ACCESS  read-only
    STATUS      current
    DESCRIPTION
        "Number of bytes that the server farm received."
    ::= { hpnicfLBv2SFStatsEntry 9 }

hpnicfLBv2SFStatServerSideBytesOut OBJECT-TYPE
    SYNTAX      Counter64
    UNITS       "byte"
    MAX-ACCESS  read-only
    STATUS      current
    DESCRIPTION
        "Number of bytes that the server farm sent."
    ::= { hpnicfLBv2SFStatsEntry 10 }

hpnicfLBv2SFStatReceivedRequests OBJECT-TYPE
    SYNTAX      Counter64
    MAX-ACCESS  read-only
    STATUS      current
    DESCRIPTION
        "Number of requests that all real servers in the server farm
         received from device."
    ::= { hpnicfLBv2SFStatsEntry 11 }

hpnicfLBv2SFStatSentResponses OBJECT-TYPE
    SYNTAX      Counter64
    MAX-ACCESS  read-only
    STATUS      current
    DESCRIPTION
        "Number of responses that the server farm sent to device."
    ::= { hpnicfLBv2SFStatsEntry 12 }

-- =================================================================
--    LB NOTIFICATION
-- =================================================================
hpnicfLBv2Trap OBJECT IDENTIFIER ::= { hpnicfLBv2 6 }

hpnicfLBv2TrapPrefix OBJECT IDENTIFIER ::= { hpnicfLBv2Trap 0 }
-- =================================================================
--    Virtual Server Connections Overload Notification
-- =================================================================
hpnicfLBv2VSConnOverloadTrap NOTIFICATION-TYPE
    OBJECTS
        {
            hpnicfLBv2VSName,
            hpnicfLBv2VSConnectionsLimit,
            hpnicfLBv2VSStatChassis,
            hpnicfLBv2VSStatSlot,
            hpnicfLBv2VSStatCpuid,
            hpnicfLBv2VSStatActiveConnections
        }
    STATUS      current
    DESCRIPTION
        "A hpnicfLBv2VSConnOverloadTrap notification is sent when
         the number of active connections of the virtual server
         has reached the upper limit. "
    ::= { hpnicfLBv2TrapPrefix 1 }

-- =================================================================
--    Virtual Server Connections Overload Recovery Notification
-- =================================================================
hpnicfLBv2VSConnRecoveryTrap NOTIFICATION-TYPE
    OBJECTS
        {
            hpnicfLBv2VSName,
            hpnicfLBv2VSConnectionsLimit,
            hpnicfLBv2VSStatChassis,
            hpnicfLBv2VSStatSlot,
            hpnicfLBv2VSStatCpuid,
            hpnicfLBv2VSStatActiveConnections
        }
    STATUS      current
    DESCRIPTION
        "A hpnicfLBv2VSConnRecoveryTrap notification is sent when
         the number of active connections of the virtual server
         is less than the upper limit."
    ::= { hpnicfLBv2TrapPrefix 2 }
-- =================================================================
--    Virtual Server Connections Rate Overload Notification
-- =================================================================
hpnicfLBv2VSConnsRateOverloadTrap NOTIFICATION-TYPE
    OBJECTS
        {
            hpnicfLBv2VSName,
            hpnicfLBv2VSConnectionsRateLimit,
            hpnicfLBv2VSStatChassis,
            hpnicfLBv2VSStatSlot,
            hpnicfLBv2VSStatCpuid,
            hpnicfLBv2VSStatConnectionsRate
        }
    STATUS      current
    DESCRIPTION
        "A hpnicfLBv2VSConnsRateOverloadTrap notification is sent
         when the connection rate of the virtual server has
         reached the upper limit."
    ::= { hpnicfLBv2TrapPrefix 3 }

-- =================================================================
--    Virtual Server Connections Rate Overload Recovery Notification
-- =================================================================
hpnicfLBv2VSConnsRateRecoveryTrap NOTIFICATION-TYPE
    OBJECTS
        {
            hpnicfLBv2VSName,
            hpnicfLBv2VSConnectionsRateLimit,
            hpnicfLBv2VSStatChassis,
            hpnicfLBv2VSStatSlot,
            hpnicfLBv2VSStatCpuid,
            hpnicfLBv2VSStatConnectionsRate
        }
    STATUS      current
    DESCRIPTION
        "A hpnicfLBv2VSConnsRateRecoveryTrap notification is sent
         connection rate of the virtual server is smaller than
         the upper limit."
    ::= { hpnicfLBv2TrapPrefix 4 }

-- =================================================================
--    Virtual Server Active Notification
-- =================================================================
hpnicfLBv2VSActiveTrap NOTIFICATION-TYPE
    OBJECTS
        {
            hpnicfLBv2VSName
        }
    STATUS      current
    DESCRIPTION
        "A hpnicfLBv2VSStatusTrap notification is sent when virtual
         server status changes to active."
    ::= { hpnicfLBv2TrapPrefix 5 }

-- =================================================================
--    Virtual Server Inactive Notification
-- =================================================================
hpnicfLBv2VSInactiveTrap NOTIFICATION-TYPE
    OBJECTS
        {
            hpnicfLBv2VSName
        }
    STATUS      current
    DESCRIPTION
        "A hpnicfLBv2VSStatusTrap notification is sent when virtual
         server status changes to inactive."
    ::= { hpnicfLBv2TrapPrefix 6 }

-- =================================================================
--    Real Server Available Notification
-- =================================================================
hpnicfLBv2RSAvailableTrap NOTIFICATION-TYPE
    OBJECTS
        {
            hpnicfLBv2RSName
        }
    STATUS      current
    DESCRIPTION
        "A hpnicfLBv2RSStatusTrap notification is sent when the status of
         the real server changes to available."
    ::= { hpnicfLBv2TrapPrefix 7 }

-- =================================================================
--    Real Server Unavailable Notification
-- =================================================================
hpnicfLBv2RSUnavailableTrap NOTIFICATION-TYPE
    OBJECTS
        {
            hpnicfLBv2RSName
        }
    STATUS      current
    DESCRIPTION
        "A hpnicfLBv2RSStatusTrap notification is sent when the status of
         the real server changes to unavailable."
    ::= { hpnicfLBv2TrapPrefix 8 }

-- =================================================================
--    Server Farm Active Notification
-- =================================================================
hpnicfLBv2SFActiveTrap NOTIFICATION-TYPE
    OBJECTS
        {
            hpnicfLBv2SFName
        }
    STATUS      current
    DESCRIPTION
        "A hpnicfLBv2SFStatusTrap notification is sent when the status of
         the server farm changes to active."
    ::= { hpnicfLBv2TrapPrefix 9 }

-- =================================================================
--    Server Farm Inactive Notification
-- =================================================================
hpnicfLBv2SFInactiveTrap NOTIFICATION-TYPE
    OBJECTS
        {
            hpnicfLBv2SFName
        }
    STATUS      current
    DESCRIPTION
        "A hpnicfLBv2SFStatusTrap notification is sent when the status of
         the server farm changes to inactive."
    ::= { hpnicfLBv2TrapPrefix 10 }

-- =================================================================
--    Server Farm In Use Of Action Changes Notification
-- =================================================================
hpnicfLBv2ActionInUseSFChangeTrap NOTIFICATION-TYPE
    OBJECTS
        {
            hpnicfLBv2ActionName,
            hpnicfLBv2ActionDefaultSF,
            hpnicfLBv2ActionBackupSF,
            hpnicfLBv2ActionInUseSF
        }
    STATUS      current
    DESCRIPTION
         "A hpnicfLBv2VSInUseSFChangeTrap notification is sent when the
         server farm which is in use quoted by action changes."
    ::= { hpnicfLBv2TrapPrefix 11 }

-- =================================================================
--    Server Farm In Use Of Virtual Server Changes Notification
-- =================================================================
hpnicfLBv2VSInUseSFChangeTrap NOTIFICATION-TYPE
    OBJECTS
        {
            hpnicfLBv2VSName,
            hpnicfLBv2VSDefaultSF,
            hpnicfLBv2VSBackupSF,
            hpnicfLBv2VSInUseSF
        }
    STATUS      current
    DESCRIPTION
        "A hpnicfLBv2ActionInUseSFChangeTrap notification is sent when
         the server farm which is in use quoted by virtual server
         changes."
    ::= { hpnicfLBv2TrapPrefix 12 }

END
