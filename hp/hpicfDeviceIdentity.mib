-- *****************************************************************
-- HP-ICF-DEVICEIDENTITY-MIB :  DEVICE IDENTITY MIB file
-- Copyright (c) 2015 Hewlett-Packard Development Company, L.P.
-- All Rights Reserved.
-- *****************************************************************

HP-ICF-DEVICEIDENTITY-MIB DEFINITIONS  ::= BEGIN

IMPORTS
  Integer32, MODULE-IDENTITY,
  OBJECT-TYPE, Unsigned32
               FROM SNMPv2-SMI
  MODULE-COMPLIANCE, OBJECT-GROUP
               FROM SNMPv2-CONF
  hpSwitch
            FROM HP-ICF-OID
  RowStatus
            FROM SNMPv2-TC;

hpicfDeviceIdentityMIB MODULE-IDENTITY
  LAST-UPDATED "201701030000Z" -- January 03, 2017
  ORGANIZATION "HP Networking"
  CONTACT-INFO "Hewlett-Packard Company
               8000 Foothills Blvd.
               Roseville, CA 95747"
  DESCRIPTION  "Added new device identity table HpicfDeviceIdentityEntry.
                This table is used to identify  device using
                discovery protocol like LLDP. LLDP make use of 
                OUI and device subtype of organization specific TLV to 
                detect device."
  REVISION     "201701030000Z" -- January 03, 2017  
  DESCRIPTION  "Added new device identity table HpicfDeviceIdentityEntry.
                This table is used to identify  device using
                discovery protocol like LLDP. LLDP make use of 
                OUI and device subtype of organization specific TLV to 
                detect device."

  ::= { hpSwitch 135 }

 hpicfDeviceIdentityConfig      OBJECT IDENTIFIER ::= { hpicfDeviceIdentityMIB 1}
 hpicfDeviceIdentityConformance OBJECT IDENTIFIER ::= { hpicfDeviceIdentityMIB 2}

hpicfDeviceIdentityTable OBJECT-TYPE
        SYNTAX      	SEQUENCE OF HpicfDeviceIdentityEntry
        MAX-ACCESS  	not-accessible
        STATUS      	current
        DESCRIPTION  "The device identity configuration table.
                     This table is used to identify  device using
                     discovery protocol like LLDP. LLDP make use of 
                     OUI and device subtype of organigation specific TLV to 
                     detect device."
        ::= { hpicfDeviceIdentityConfig 1 }

   hpicfDeviceIdentityEntry OBJECT-TYPE
        SYNTAX         	HpicfDeviceIdentityEntry
        MAX-ACCESS      not-accessible
        STATUS        	current
        DESCRIPTION 	   "The device identity configuration entry."
        INDEX { hpicfDeviceIdentityIndex }
        ::= { hpicfDeviceIdentityTable 1 }

   HpicfDeviceIdentityEntry ::= SEQUENCE {
               hpicfDeviceIdentityIndex           Unsigned32,
               hpicfDeviceIdentityRowStatus       RowStatus,
               hpicfDeviceIdentityName            OCTET STRING,
               hpicfDeviceIdentityLldpOui         OCTET STRING,
               hpicfDeviceIdentityLldpSubType     Integer32
               }

   hpicfDeviceIdentityIndex OBJECT-TYPE
        SYNTAX     	 Unsigned32 (1..16)
        MAX-ACCESS 	 not-accessible 
        STATUS     	 current
        DESCRIPTION
             "The index value which uniquely identifies a row
             in the device identity table."
        ::= { hpicfDeviceIdentityEntry 1 }

    hpicfDeviceIdentityRowStatus OBJECT-TYPE
      SYNTAX      	RowStatus
      MAX-ACCESS 	   read-create
      STATUS      	current
      DESCRIPTION
           "The row status of this device identity entry. Allows
           creation/deletion of the device identity entry. Row cannot
           be deleted if the device identity is associated with other
           subsystem like device profile."
      ::= { hpicfDeviceIdentityEntry 2 }

   hpicfDeviceIdentityName OBJECT-TYPE
        SYNTAX     	 OCTET STRING ( SIZE (1..20))
        MAX-ACCESS    read-create
        STATUS     	 current
        DESCRIPTION
             "The name of the device identity. The maximum length
			    supported is 20 characters."
        ::= { hpicfDeviceIdentityEntry 3 }

   hpicfDeviceIdentityLldpOui  OBJECT-TYPE
    SYNTAX      OCTET STRING (SIZE(3))
    MAX-ACCESS  read-create
    STATUS      current
    DESCRIPTION
            "The Organizationally Unique Identifier (OUI), as defined
            in IEEE std 802-2001, is a 24 bit (three octets) globally
            unique assigned number referenced by various standards,
            of the information received from the remote system.
            Combination of hpicfLldpDeviceOui and hpicfLldpDeviceSubType
            used to identify LLDP device. The default OUI 000000 indicates
            that device-identity will not use LLDP to identify device."
    REFERENCE
            "IEEE 802.1AB-2005 9.5.1.3"
    ::= { hpicfDeviceIdentityEntry 4 }

   hpicfDeviceIdentityLldpSubType  OBJECT-TYPE
       SYNTAX      Integer32(0..255)
       MAX-ACCESS  read-create
       STATUS      current
       DESCRIPTION
            "The integer value used to identify the subtype of the
            organizationally defined information received from the
            remote system.
            The subtype value is required to identify different instances
            of organizationally defined information that could not be
            retrieved without a unique identifier that indicates the
            particular type of information contained in the information
            string. The default value (0) of the object indicates that
            subtype will be ignored in device  identification."

    REFERENCE
            "IEEE 802.1AB-2005 9.5.1.4"
       DEFVAL      { 0 }
    ::= { hpicfDeviceIdentityEntry 5 }

 hpicfDeviceIdentityGroups        OBJECT IDENTIFIER ::= { hpicfDeviceIdentityConformance 1 }
 hpicfDeviceIdentityCompliances   OBJECT IDENTIFIER ::= { hpicfDeviceIdentityConformance 2 }

 hpicfiDeviceIdentityCompliance MODULE-COMPLIANCE
        STATUS      current
        DESCRIPTION "The compliance statement for device identity using discovery 
                     protocol like LLDP."
        MODULE  -- this module
        MANDATORY-GROUPS { hpicfDeviceIdentityGroup
        }
    ::= { hpicfDeviceIdentityCompliances 1 }

 hpicfDeviceIdentityGroup    OBJECT-GROUP
      OBJECTS {
               hpicfDeviceIdentityRowStatus,
               hpicfDeviceIdentityName,
               hpicfDeviceIdentityLldpOui,
               hpicfDeviceIdentityLldpSubType
             }

    STATUS  current
    DESCRIPTION
            "The collection of objects which are used to configure the
            device identity using discovery protocol. LLDP make use of 
            organigation specific TLV.This device identity can be use by other 
            subsystem like device profile.

            This group is mandatory for agents which implement the LLDP."
    ::= { hpicfDeviceIdentityGroups 1 }


END
