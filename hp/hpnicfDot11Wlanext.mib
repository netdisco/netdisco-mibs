-- =============================================================================
-- Copyright (c) 2010-2013 Hewlett-Packard Development Company, L.P.
--
-- Description:
--   The file defines a MIB to provide more information for WLAN network.
-- Reference:
-- Version: V1.0
-- History:
--   V1.0 2007-06-08 Initial version, created by wanghao (Kumar)
-- =============================================================================
HPN-ICF-DOT11-WLANEXT-MIB DEFINITIONS ::= BEGIN

IMPORTS
        MODULE-IDENTITY,
        OBJECT-TYPE,
        Integer32,
        Counter32
    FROM SNMPv2-SMI
        hpnicfDot11,
        HpnicfDot11ObjectIDType,
        HpnicfDot11RadioScopeType,
        HpnicfDot11QosAcType
    FROM HPN-ICF-DOT11-REF-MIB;

hpnicfDot11WLANEXT MODULE-IDENTITY
    LAST-UPDATED "200706082000Z"            -- Jun. 08, 2007 at 20:00 GMT
    ORGANIZATION
        ""
    CONTACT-INFO
        ""
    DESCRIPTION
        "This MIB provides more information for WLAN network.

        GLOSSARY

        IEEE 802.11
        Standard to encourage interoperability among
        wireless networking equipment.

        IEEE 802.11e
        Standard to define the MAC procedures to support
        LAN applications with Quality of Service (QoS) requirements,
        including the transport of voice, audio and video over
        IEEE 802.11 wireless LANs.

        Access point (AP)
        Transmitter/receiver (transceiver) device
        that commonly connects and transports data
        between a wireless network and a wired network.

        Access control (AC)
        To control and manage multi-APs, it will bridge
        wireless and wired network.

        Radio
        The chip set to receive and send wireless signal.

        Fat AP
        Applied in the home, SOHO and so on, and it could
        independently work without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "200706082000Z"        -- Jun 08, 2007 at 20:00 GMT
    DESCRIPTION
        "The initial revision of this MIB module."
    ::= { hpnicfDot11 7 }

-- *****************************************************************************
-- *  Major sections
-- *****************************************************************************
--  RF Management Group
--  DEFINED AS "The group to provide the statistic information
--  for RF management feature.
hpnicfDot11RFGroup OBJECT IDENTIFIER   ::= { hpnicfDot11WLANEXT 1 }

--  The RF Management Group has the following children:
--  hpnicfDot11RFSignalStatisTable  ::= { hpnicfDot11RFGroup 1 }

--  Qos Group
--  DEFINED AS "The group to provide the statistic information
--  for Qos feature."
hpnicfDot11QosGroup OBJECT IDENTIFIER  ::= { hpnicfDot11WLANEXT 2 }

--  The Qos Group has the following children:
--  hpnicfDot11QosStatisTable    ::= { hpnicfDot11QosGroup 1 }
--  hpnicfDot11QosAcStatisTable  ::= { hpnicfDot11QosGroup 2 }

-- *****************************************************************************
-- *  hpnicfDot11RFSignalStatisticTable Definition
-- *****************************************************************************
hpnicfDot11RFSignalStatisTable OBJECT-TYPE
    SYNTAX      SEQUENCE OF HpnicfDot11RFSignalStatisEntry
    MAX-ACCESS  not-accessible
    STATUS      current
    DESCRIPTION
        "The table will describe statistic information of signal strength
        for AP radio."
    ::= { hpnicfDot11RFGroup 1 }

hpnicfDot11RFSignalStatisEntry OBJECT-TYPE
    SYNTAX      HpnicfDot11RFSignalStatisEntry
    MAX-ACCESS  not-accessible
    STATUS      current
    DESCRIPTION
        "Each entry contains the signal of each signal strength information of
        a specific AP."
    INDEX
        {
            hpnicfDot11RFAPID,
            hpnicfDot11RFRadioID
        }
    ::= { hpnicfDot11RFSignalStatisTable 1 }

HpnicfDot11RFSignalStatisEntry ::= SEQUENCE
    {
        hpnicfDot11RFAPID                     HpnicfDot11ObjectIDType,
        hpnicfDot11RFRadioID                  HpnicfDot11RadioScopeType,
        hpnicfDot11RFSignalStatisInterv       Integer32,
        hpnicfDot11RFAverageSignalStrength    Integer32,
        hpnicfDot11RFMaxSignalStrength        Integer32,
        hpnicfDot11RFMinSignalStrength        Integer32
    }

hpnicfDot11RFAPID OBJECT-TYPE
    SYNTAX      HpnicfDot11ObjectIDType
    MAX-ACCESS  not-accessible
    STATUS      current
    DESCRIPTION
        "To identify each AP, and AP is running status."
    ::= { hpnicfDot11RFSignalStatisEntry 1 }

hpnicfDot11RFRadioID OBJECT-TYPE
    SYNTAX      HpnicfDot11RadioScopeType
    MAX-ACCESS  not-accessible
    STATUS      current
    DESCRIPTION
        "Represents each radio."
    ::= { hpnicfDot11RFSignalStatisEntry 2 }

hpnicfDot11RFSignalStatisInterv OBJECT-TYPE
    SYNTAX      Integer32
    UNITS       "second"
    MAX-ACCESS  read-only
    STATUS      current
    DESCRIPTION
        "Represents the interval of statistic."
    ::= { hpnicfDot11RFSignalStatisEntry 3 }

hpnicfDot11RFAverageSignalStrength OBJECT-TYPE
    SYNTAX      Integer32
    UNITS       "dBm"
    MAX-ACCESS  read-only
    STATUS      current
    DESCRIPTION
        "Represents the average value of signal strength
        for stations on a specific radio."
    ::= { hpnicfDot11RFSignalStatisEntry 4 }

hpnicfDot11RFMaxSignalStrength OBJECT-TYPE
    SYNTAX      Integer32
    UNITS       "dBm"
    MAX-ACCESS  read-only
    STATUS      current
    DESCRIPTION
        "Represents the maximum value of signal strength
        for stations on a specific radio."
    ::= { hpnicfDot11RFSignalStatisEntry 5 }

hpnicfDot11RFMinSignalStrength OBJECT-TYPE
    SYNTAX      Integer32
    UNITS       "dBm"
    MAX-ACCESS  read-only
    STATUS      current
    DESCRIPTION
        "Represents the minimum value of signal strength
        for stations on a specific radio."
    ::= { hpnicfDot11RFSignalStatisEntry 6 }
-- *****************************************************************************
-- *  End of hpnicfDot11RFSignalStatisTable Definition
-- *****************************************************************************

-- *****************************************************************************
-- *  hpnicfDot11QosStatisTable Definition
-- *****************************************************************************
hpnicfDot11QosStatisTable OBJECT-TYPE
    SYNTAX      SEQUENCE OF HpnicfDot11QosStatisEntry
    MAX-ACCESS  not-accessible
    STATUS      current
    DESCRIPTION
        "The table defines the attributes for the Qos feature of radio."
    ::= { hpnicfDot11QosGroup 1 }

hpnicfDot11QosStatisEntry OBJECT-TYPE
    SYNTAX      HpnicfDot11QosStatisEntry
    MAX-ACCESS  not-accessible
    STATUS      current
    DESCRIPTION
        "Each entry contains information of the Qos attribute of each radio."
    INDEX
        {
            hpnicfDot11QosAPID,
            hpnicfDot11QosRadioID
        }
    ::= { hpnicfDot11QosStatisTable 1 }

HpnicfDot11QosStatisEntry ::= SEQUENCE
    {
        hpnicfDot11QosAPID               HpnicfDot11ObjectIDType,
        hpnicfDot11QosRadioID            HpnicfDot11RadioScopeType,
        hpnicfDot11QosAverageQueLen      Integer32,
        hpnicfDot11QosDropFrameRatio     Integer32,
        hpnicfDot11QosAverageDataRate    Integer32
    }

hpnicfDot11QosAPID OBJECT-TYPE
    SYNTAX      HpnicfDot11ObjectIDType
    MAX-ACCESS  not-accessible
    STATUS      current
    DESCRIPTION
        "To uniquely identify a AP in running status."
    ::= { hpnicfDot11QosStatisEntry 1 }

hpnicfDot11QosRadioID OBJECT-TYPE
    SYNTAX      HpnicfDot11RadioScopeType
    MAX-ACCESS  not-accessible
    STATUS      current
    DESCRIPTION
        "Represents each radio."
    ::= { hpnicfDot11QosStatisEntry 2 }

hpnicfDot11QosAverageQueLen OBJECT-TYPE
    SYNTAX      Integer32
    MAX-ACCESS  read-only
    STATUS      current
    DESCRIPTION
        "The average frame numbers to be sent out in the queue."
    ::= { hpnicfDot11QosStatisEntry 3 }

hpnicfDot11QosDropFrameRatio OBJECT-TYPE
    SYNTAX      Integer32
    MAX-ACCESS  read-only
    STATUS      current
    DESCRIPTION
        "The ratio of dropped frames in a minute because of full queue."
    ::= { hpnicfDot11QosStatisEntry 4 }

hpnicfDot11QosAverageDataRate OBJECT-TYPE
    SYNTAX      Integer32
    UNITS       "Kbps"
    MAX-ACCESS  read-only
    STATUS      current
    DESCRIPTION
        "The average transmit data rate of radio."
    ::= { hpnicfDot11QosStatisEntry 5 }
-- *****************************************************************************
-- *  End of hpnicfDot11QosStatisTable Definition
-- *****************************************************************************

-- *****************************************************************************
-- *  hpnicfDot11QosAcAttributeTable Definition
-- *****************************************************************************
hpnicfDot11QosAcStatisTable OBJECT-TYPE
    SYNTAX      SEQUENCE OF HpnicfDot11QosAcStatisEntry
    MAX-ACCESS  not-accessible
    STATUS      current
    DESCRIPTION
        "The table defines the parameters for Qos access category."
    ::= { hpnicfDot11QosGroup 2 }

hpnicfDot11QosAcStatisEntry OBJECT-TYPE
    SYNTAX      HpnicfDot11QosAcStatisEntry
    MAX-ACCESS  not-accessible
    STATUS      current
    DESCRIPTION
        "Each entry contains information of each Qos access category."
    INDEX
        {
            hpnicfDot11QosAPID,
            hpnicfDot11QosRadioID,
            hpnicfDot11QosAcType
        }
    ::= { hpnicfDot11QosAcStatisTable 1 }

HpnicfDot11QosAcStatisEntry ::= SEQUENCE
    {
        hpnicfDot11QosAcType         HpnicfDot11QosAcType,
        hpnicfDot11AcDropFrameCnt    Counter32
    }

hpnicfDot11QosAcType OBJECT-TYPE
    SYNTAX      HpnicfDot11QosAcType
    MAX-ACCESS  not-accessible
    STATUS      current
    DESCRIPTION
        "The access category type."
    ::= { hpnicfDot11QosAcStatisEntry 1 }

hpnicfDot11AcDropFrameCnt OBJECT-TYPE
    SYNTAX      Counter32
    MAX-ACCESS  read-only
    STATUS      current
    DESCRIPTION
        "The number of dropped frames in a minute for one specific access
        category because of full queue."
    ::= { hpnicfDot11QosAcStatisEntry 2 }
-- *****************************************************************************
-- *  End of hpnicfDot11AcAttributeTable Definition
-- *****************************************************************************
END
