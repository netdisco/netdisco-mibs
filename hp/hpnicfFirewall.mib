-- =========================================================================
-- Copyright (c) 2010-2013 Hewlett-Packard Development Company, L.P.
--
-- Description: The MIB is designed to get Firewall' statistic information.
-- Reference:
-- Version: V1.1
-- History:
--  V1.0 2008-01-17 created by ZhangBo 05309
--       Initial version.
--  V1.1 2012/12/01 Modified by y05947
--       Add hpnicfFWConnRate node.
-- =========================================================================
HPN-ICF-FIREWALL-MIB DEFINITIONS ::= BEGIN

IMPORTS
        hpnicfCommon
    FROM HPN-ICF-OID-MIB
        Unsigned32, Gauge32, OBJECT-TYPE, MODULE-IDENTITY
    FROM SNMPv2-SMI;


hpnicfFireWall MODULE-IDENTITY
    LAST-UPDATED "200801171450Z"
    ORGANIZATION
        ""
    CONTACT-INFO
        ""
    DESCRIPTION
        "The MIB is designed to manage Firewall products."
    ::= { hpnicfCommon 88 }


--
-- Node definitions
--

hpnicfFirewallobject OBJECT IDENTIFIER ::= { hpnicfFireWall 1 }

hpnicfFirewallSpecs OBJECT IDENTIFIER ::= { hpnicfFirewallobject 1 }

hpnicfFWMaxConnNum OBJECT-TYPE
    SYNTAX      Unsigned32
    MAX-ACCESS  read-only
    STATUS      current
    DESCRIPTION
        "Max connection number of system."
    ::= { hpnicfFirewallSpecs 1 }

hpnicfFirewallGlobalStats OBJECT IDENTIFIER ::= { hpnicfFirewallobject 2 }

hpnicfFWConnNumCurr OBJECT-TYPE
    SYNTAX      Gauge32
    MAX-ACCESS  read-only
    STATUS      current
    DESCRIPTION
        "The number of connections that currently exist."
    ::= { hpnicfFirewallGlobalStats 1 }

hpnicfFWConnRate OBJECT-TYPE
    SYNTAX Gauge32
    MAX-ACCESS read-only
    STATUS current
    DESCRIPTION
        "Connection establishment rate."
    ::= { hpnicfFirewallGlobalStats 2 }

END
