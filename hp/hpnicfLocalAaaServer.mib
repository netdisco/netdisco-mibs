-- ==========================================================================
-- Copyright (c) 2010-2014 Hewlett-Packard Development Company, L.P.
--
-- Description: Local AAA Server mib
-- Reference:
-- Version: V1.0
-- History:
--   V1.0 2013-07-06 created by yangxu 02965
-- ==========================================================================
HPN-ICF-LOCAL-AAA-SERVER-MIB DEFINITIONS ::= BEGIN

IMPORTS
    MODULE-IDENTITY, NOTIFICATION-TYPE
        FROM SNMPv2-SMI
    hpnicfCommon
        FROM HPN-ICF-OID-MIB;

hpnicfLocAAASvr MODULE-IDENTITY
    LAST-UPDATED "201307060945Z"
    ORGANIZATION
        ""
    CONTACT-INFO
        ""
    DESCRIPTION
        "This MIB provides the definition of the local AAA Server."
    REVISION "201307060945Z"
    DESCRIPTION
        "The initial revision of this MIB module."
    ::= { hpnicfCommon 141 }

-- definition of textual conventions

--
-- nodes defined
--

hpnicfLocAAASvrControl OBJECT IDENTIFIER ::= { hpnicfLocAAASvr 1 }

--
-- tables defined
--

hpnicfLocAAASvrTables OBJECT IDENTIFIER ::= { hpnicfLocAAASvr 2 }

--
-- traps defined
--

hpnicfLocAAASvrTrap OBJECT IDENTIFIER ::= { hpnicfLocAAASvr 3 }

hpnicfLocAAASvrTrapPrex OBJECT IDENTIFIER ::= { hpnicfLocAAASvrTrap 0 }

hpnicfLocAAASvrBillExportFailed NOTIFICATION-TYPE
    STATUS current
    DESCRIPTION
        "This trap is generated when local AAA bills
        cannot be exported to a bill server."
    ::= { hpnicfLocAAASvrTrapPrex 1 }

END
