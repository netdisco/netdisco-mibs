-- ============================================================================
-- Copyright (c) 2010-2013 Hewlett-Packard Development Company, L.P.
-- Description: This MIB describes OID of HPN products.
--
-- Reference:
-- Version: V1.01
-- History:
--   V1.00 2013-01-16 Created by songhao
--   V1.01 2013-10-09  by songhao
--      Added OID 11 to 16 under hpnWireless
-- ============================================================================
HPN-ICF-PRODUCT-ID-MIB DEFINITIONS ::= BEGIN
    IMPORTS
        nm
            FROM HPN-ICF-OID-MIB;

-- Objects under .enterprises.hp(11).nm(2)
hpSystem         OBJECT IDENTIFIER ::= { nm 3 }
netElement       OBJECT IDENTIFIER ::= { hpSystem 7 }
hpn              OBJECT IDENTIFIER ::= { netElement 15 }
hpnProducts      OBJECT IDENTIFIER ::= { hpn 1 }

-- Objects under .enterprises.hp(11).nm(2).hpSystem(3).netElement(7).hpn(15).hpnProducts(1)
hpnSwitch        OBJECT IDENTIFIER ::= { hpnProducts 1 }
hpnRouter        OBJECT IDENTIFIER ::= { hpnProducts 2 }
hpnWireless      OBJECT IDENTIFIER ::= { hpnProducts 3 }
hpnSecurity      OBJECT IDENTIFIER ::= { hpnProducts 4 }

-- Objects under .enterprises.hp(11).nm(2).hpSystem(3).netElement(7).hpn(15).hpnProducts(1).hpnWireless(3)
hpnLSU3WCMD0                    OBJECT IDENTIFIER ::= { hpnWireless 1 }
hpn83024P                       OBJECT IDENTIFIER ::= { hpnWireless 2 }
hpn83024PLSW                    OBJECT IDENTIFIER ::= { hpnWireless 3 }
hpn8308P                        OBJECT IDENTIFIER ::= { hpnWireless 4 }
hpn8308PLSW                     OBJECT IDENTIFIER ::= { hpnWireless 5 }
hpnLSU3WCMD0TAA                 OBJECT IDENTIFIER ::= { hpnWireless 6 }
hpn83024PTAA                    OBJECT IDENTIFIER ::= { hpnWireless 7 }
hpn83024PTAALSW                 OBJECT IDENTIFIER ::= { hpnWireless 8 }
hpn8308PTAA                     OBJECT IDENTIFIER ::= { hpnWireless 9 }
hpn8308PTAALSW                  OBJECT IDENTIFIER ::= { hpnWireless 10 }
hpn870WCM                       OBJECT IDENTIFIER ::= { hpnWireless 11 }
hpn870LSW                       OBJECT IDENTIFIER ::= { hpnWireless 12 }
hpn850                          OBJECT IDENTIFIER ::= { hpnWireless 13 }
hpn870TAAWCM                    OBJECT IDENTIFIER ::= { hpnWireless 14 }
hpn870TAALSW                    OBJECT IDENTIFIER ::= { hpnWireless 15 }
hpn850TAA                       OBJECT IDENTIFIER ::= { hpnWireless 16 }

END
