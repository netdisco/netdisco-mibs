-- =================================================================
-- Copyright (c) 2010-2014 Hewlett-Packard Development Company, L.P.
--
-- Description: This file describes the enterprise mib implementation
--              of sending some traps.
-- Reference:
-- Version: V1.6
-- History:
--   V1.0 created by Huang Yang
--     Initial version 2005-01-25
--   V1.1 2005-10-27  added hpnicfArpPortDynamicEntryFullTrap by ZhangLin
--   V1.2 2007-02-06  added hpnicfNdTabTrapEnable, hpnicfNdTabTrapInterval,
--                    hpnicfNdTabLen and hpnicfNdTabFullTrap by lizuxing04859
--   V1.3 2008-07-18  added hpnicfPeriodicalTrapGroup by songhao
--   V1.4 2009-10-09  modified hpnicfPeriodicalTrapInterval by lisong
--   V1.5 2010-03-06  added hpnicfPeriodicalTrapSwitch, hpnicfTrapDesInfoTable
--                    hpnicfTrapConfigTable by haoyan
--        2010-04-29  added hpnicfDefaultRtDelTrap by wenchenhua
--        2010-06-05  added hpnicfTrapDesAddrTAddress by jinyi
--   V1.6 2013-09-13  added hpnicfPeriodicalTrapSwitch2 and
--                    hpnicfTrapConfigSwitch2 by duyanbing
-- =================================================================
HPN-ICF-TRAP-MIB DEFINITIONS ::= BEGIN

    IMPORTS
        IpAddress
            FROM SNMPv2-SMI
        SnmpAdminString
            FROM SNMP-FRAMEWORK-MIB
        ifIndex, ifDescr, InterfaceIndex
            FROM IF-MIB
        RowStatus, TAddress, TruthValue
            FROM SNMPv2-TC
        Integer32, OBJECT-TYPE,
        MODULE-IDENTITY, NOTIFICATION-TYPE
            FROM SNMPv2-SMI
        InetAddressType, InetAddress
            FROM INET-ADDRESS-MIB
        hpnicfCommon
            FROM HPN-ICF-OID-MIB;

    hpnicfTrap MODULE-IDENTITY
        LAST-UPDATED "201006051050Z"
        ORGANIZATION
            ""
        CONTACT-INFO
            ""
        DESCRIPTION
            "This MIB is applicable to routers, switches and other products.

            Some objects in this may be used only for some specific products,
            so users should refer to the related documents to acquire more
            detail information.
            "
        REVISION "201006051050Z"
        DESCRIPTION
            "The initial revision of this MIB module."
        ::= { hpnicfCommon 38 }


--
-- Node definitions
--
    hpnicfTableGroup OBJECT IDENTIFIER ::= { hpnicfTrap 1 }

-- Describe objects for MAC table
    hpnicfMacTabStatGroup OBJECT IDENTIFIER ::= { hpnicfTableGroup 1 }

    hpnicfMacTabTrapEnable OBJECT-TYPE
        SYNTAX INTEGER{
                        enable(1),
                        disable(2)
                        }
        MAX-ACCESS read-write
        STATUS current
        DESCRIPTION
            "Indicates whether hpnicfMacTabFullTrap and
            hpnicfMacTabAlmostFullTrap traps should be generated
            when the MAC table is filled."
        DEFVAL { enable }
        ::= { hpnicfMacTabStatGroup 1 }

    hpnicfMacTabTrapInterval OBJECT-TYPE
        SYNTAX Integer32 (30..3600)
        UNITS "seconds"
        MAX-ACCESS read-write
        STATUS current
        DESCRIPTION
            "Definition of the minimum interval between two
            traps which occur when the MAC table is full or
            two traps which occur when the MAC table is almost full."
        DEFVAL { 30 }
        ::= { hpnicfMacTabStatGroup 2 }

    hpnicfMacTabTrapInfo OBJECT IDENTIFIER ::= { hpnicfMacTabStatGroup 3 }

    hpnicfMacTabLen OBJECT-TYPE
        SYNTAX Integer32
        MAX-ACCESS accessible-for-notify
        STATUS current
        DESCRIPTION
            "The length of the MAC table."
        ::= { hpnicfMacTabTrapInfo 1 }

    hpnicfMacTabTrap OBJECT IDENTIFIER ::= { hpnicfMacTabStatGroup 4 }

    hpnicfMacTabFullTrap NOTIFICATION-TYPE
            OBJECTS { hpnicfMacTabLen }
            STATUS current
            DESCRIPTION
                "Send this trap when the MAC table is filled.  The
                interval between two traps generated should be longer
                than hpnicfMacTabTrapInterval."
            ::= { hpnicfMacTabTrap 1 }

    hpnicfMacTabAlmostFullTrap NOTIFICATION-TYPE
            STATUS current
            DESCRIPTION
                "Send this trap when the MAC table is almost full.  The
                interval between two traps generated should be longer
                than hpnicfMacTabTrapInterval."
            ::= { hpnicfMacTabTrap 2 }

-- Describe objects for ARP table
    hpnicfArpTabStatGroup OBJECT IDENTIFIER ::= { hpnicfTableGroup 2 }

    hpnicfArpTabTrapEnable OBJECT-TYPE
        SYNTAX INTEGER {
                        enable(1),
                        disable(2)
                        }
        MAX-ACCESS read-write
        STATUS current
        DESCRIPTION
            "Indicates whether hpnicfArpTabFullTrap traps
            should be generated when the ARP table is filled."
        DEFVAL { enable }
        ::= { hpnicfArpTabStatGroup 1 }

    hpnicfArpTabTrapInterval OBJECT-TYPE
        SYNTAX Integer32 (30..3600)
        UNITS "seconds"
        MAX-ACCESS read-write
        STATUS current
        DESCRIPTION
            "Definition of the minimum interval between two traps
            which occur when the ARP table is filled."
        DEFVAL { 30 }
        ::= { hpnicfArpTabStatGroup 2 }

    hpnicfArpTabTrapInfo OBJECT IDENTIFIER ::= { hpnicfArpTabStatGroup 3 }

    hpnicfArpTabLen OBJECT-TYPE
        SYNTAX Integer32
        MAX-ACCESS accessible-for-notify
        STATUS current
        DESCRIPTION
            "The length of the ARP table."
        ::= { hpnicfArpTabTrapInfo 1 }

    hpnicfArpTabTrap OBJECT IDENTIFIER ::= { hpnicfArpTabStatGroup 4 }

    hpnicfArpTabFullTrap NOTIFICATION-TYPE
            OBJECTS { hpnicfArpTabLen }
            STATUS current
            DESCRIPTION
                "Send this trap when the ARP table is filled.  The
                interval between two traps generated should be longer
                than hpnicfArpTabTrapInterval."
            ::= { hpnicfArpTabTrap 1 }

    hpnicfArpPortDynamicEntryFullTrap NOTIFICATION-TYPE
            OBJECTS { hpnicfArpTabLen, ifIndex, ifDescr }
            STATUS current
            DESCRIPTION
                 "Send this trap when the dynamic ARP number of the
                port exceeds the limitation. The object hpnicfArpTabLen
                describes the limitation of the max dynamic ARP number
                of this port. The interval between two traps should be
                longer than hpnicfArpTabTrapInterval."
            ::= { hpnicfArpTabTrap 2 }

-- Describe objects for routing table
    hpnicfRtTabStatGroup OBJECT IDENTIFIER ::= { hpnicfTableGroup 3 }

    hpnicfDetailRtTrapTable OBJECT-TYPE
        SYNTAX SEQUENCE OF HpnicfDetailRtTrapEntry
        MAX-ACCESS not-accessible
        STATUS current
        DESCRIPTION
            "This table contains objects to decide what kind of
            trap should be sent."
        ::= { hpnicfRtTabStatGroup 1 }

    hpnicfDetailRtTrapEntry OBJECT-TYPE
        SYNTAX HpnicfDetailRtTrapEntry
        MAX-ACCESS not-accessible
        STATUS current
        DESCRIPTION
            "Entry items"
        INDEX { hpnicfDetailRtProType }
        ::= { hpnicfDetailRtTrapTable 1 }

    HpnicfDetailRtTrapEntry ::=
        SEQUENCE {
            hpnicfDetailRtProType
                INTEGER,
            hpnicfDetailRtEnable
                INTEGER
        }

    hpnicfDetailRtProType OBJECT-TYPE
        SYNTAX INTEGER {
            other(1),       -- none of the following

                            -- non-protocol information,
                            -- e.g., manually configured
            local(2),       -- entries
            rip(3),
            isis(4),
            ospf(5),
            bgp(6)
        }
        MAX-ACCESS accessible-for-notify
        STATUS current
        DESCRIPTION
            "The index value which uniquely identifies an entry
            in the hpnicfDetailRtTrapTable."
        ::= { hpnicfDetailRtTrapEntry 1 }

    hpnicfDetailRtEnable OBJECT-TYPE
        SYNTAX INTEGER {
                        enable(1),
                        disable(2)
                        }
        MAX-ACCESS read-write
        STATUS current
        DESCRIPTION
            "Indicates whether hpnicfDetailRtTabFullTrap traps
            should be generated when a specific routing table
            is filled."
        DEFVAL { enable }
        ::= { hpnicfDetailRtTrapEntry 2 }

    hpnicfRtTabTrapEnable OBJECT-TYPE
        SYNTAX INTEGER {
                        enable(1),
                        disable(2)
                        }
        MAX-ACCESS read-write
        STATUS current
        DESCRIPTION
            "Indicates whether hpnicfRtTabFullTrap traps should
            be generated when the routing table is filled."
        DEFVAL { enable }
        ::= { hpnicfRtTabStatGroup 2 }

    hpnicfRtTabTrapInterval OBJECT-TYPE
        SYNTAX Integer32 (30..3600)
        UNITS "seconds"
        MAX-ACCESS read-write
        STATUS current
        DESCRIPTION
            "Definition of the minimum interval between two
            traps which occur when the routing table is filled."
        DEFVAL { 30 }
        ::= { hpnicfRtTabStatGroup 3 }

    hpnicfRtTabTrapInfo OBJECT IDENTIFIER ::= { hpnicfRtTabStatGroup 4 }

    hpnicfRtTabLen OBJECT-TYPE
        SYNTAX Integer32
        MAX-ACCESS accessible-for-notify
        STATUS current
        DESCRIPTION
            "The length of the routing table.  The detail
            routing tables also use the same object."
        ::= { hpnicfRtTabTrapInfo 1 }

    hpnicfDefaultRtNextHopType OBJECT-TYPE
        SYNTAX InetAddressType
        MAX-ACCESS accessible-for-notify
        STATUS current
        DESCRIPTION
            "The IP address type of the next hop of the default route.
            The value must be ipv4 or ipv6"
        ::= { hpnicfRtTabTrapInfo 2 }

    hpnicfDefaultRtNextHop OBJECT-TYPE
        SYNTAX InetAddress
        MAX-ACCESS accessible-for-notify
        STATUS current
        DESCRIPTION
            "The IP address of the next hop of the default route."
        ::= { hpnicfRtTabTrapInfo 3 }

    hpnicfDefaultRtOutIf OBJECT-TYPE
        SYNTAX InterfaceIndex
        MAX-ACCESS accessible-for-notify
        STATUS current
        DESCRIPTION
            "The index value which uniquely identifies the
             local interface through which the next hop of this
             route should be reached.  The interface identified
             by a particular value of this index is the same
             interface as identified by the same value of
             ifIndex."
        ::= { hpnicfRtTabTrapInfo 4 }

    hpnicfRtTabTrap OBJECT IDENTIFIER ::= { hpnicfRtTabStatGroup 5 }

    hpnicfRtTabFullTrap NOTIFICATION-TYPE
            OBJECTS { hpnicfRtTabLen }
            STATUS current
            DESCRIPTION
                "Send this trap when the routing table is filled.  The
                interval between two traps generated should be longer
                than hpnicfRtTabTrapInterval."
            ::= { hpnicfRtTabTrap 1 }

    hpnicfDetailRtTabFullTrap NOTIFICATION-TYPE
            OBJECTS { hpnicfDetailRtProType, hpnicfRtTabLen }
            STATUS current
            DESCRIPTION
                "Send this trap when the detail routing table is filled.  The
                interval between two traps generated should be longer than
                hpnicfRtTabTrapInterval."
            ::= { hpnicfRtTabTrap 2 }

    hpnicfDefaultRtDelTrap NOTIFICATION-TYPE
            OBJECTS { hpnicfDetailRtProType, hpnicfDefaultRtNextHopType, hpnicfDefaultRtNextHop, hpnicfDefaultRtOutIf }
            STATUS current
            DESCRIPTION
                "Send this trap when the default route is deleted."
            ::= { hpnicfRtTabTrap 3 }

    hpnicfDefaultRtDelTrapEnable OBJECT-TYPE
        SYNTAX TruthValue
        MAX-ACCESS read-write
        STATUS current
        DESCRIPTION
            "Indicates whether hpnicfDefaultRtDelTrap traps should
            be generated when the default route is deleted."
        DEFVAL { false }
        ::= { hpnicfRtTabStatGroup 6 }

-- Describe objects for multicast table
    hpnicfMulticastTabStatGroup OBJECT IDENTIFIER ::= { hpnicfTableGroup 4 }

    hpnicfMulticastTabTrapEnable OBJECT-TYPE
        SYNTAX INTEGER {
                        enable(1),
                        disable(2)
                        }
        MAX-ACCESS read-write
        STATUS current
        DESCRIPTION
            "Indicates whether hpnicfMulticastTabFullTrap traps
            should be generated when the multicast table is filled."
        DEFVAL { enable }
        ::= { hpnicfMulticastTabStatGroup 1 }

    hpnicfMulticastTabTrapInterval OBJECT-TYPE
        SYNTAX Integer32 (30..3600)
        UNITS "seconds"
        MAX-ACCESS read-write
        STATUS current
        DESCRIPTION
            "Definition of the minimum interval between two traps
            which occur when the multicast table is filled."
        DEFVAL { 30 }
        ::= { hpnicfMulticastTabStatGroup 2 }

    hpnicfMulticastTabTrapInfo OBJECT IDENTIFIER ::= { hpnicfMulticastTabStatGroup 3 }

    hpnicfMulticastTabType OBJECT-TYPE
        SYNTAX INTEGER {
                        lay2(1),
                        lay3(2)
                        }
        MAX-ACCESS accessible-for-notify
        STATUS current
        DESCRIPTION
            "Defining the type of the multicast table, layer2 or layer3."
        ::= { hpnicfMulticastTabTrapInfo 1 }

    hpnicfMulticastTabLen OBJECT-TYPE
        SYNTAX Integer32
        MAX-ACCESS accessible-for-notify
        STATUS current
        DESCRIPTION
            "The length of the multicast table."
        ::= { hpnicfMulticastTabTrapInfo 2 }

    hpnicfMulticastTabTrap OBJECT IDENTIFIER ::= { hpnicfMulticastTabStatGroup 4 }

    hpnicfMulticastTabFullTrap NOTIFICATION-TYPE
            OBJECTS { hpnicfMulticastTabType, hpnicfMulticastTabLen }
            STATUS current
            DESCRIPTION
                "Send this trap when the multicast table is filled.  The
                interval between two traps generated should be longer
                than hpnicfMulticastTabTrapInterval."
            ::= { hpnicfMulticastTabTrap 1 }


-- Describe objects for Neighbor table
    hpnicfNdTabStatGroup OBJECT IDENTIFIER ::= { hpnicfTableGroup 5 }

    hpnicfNdTabTrapEnable OBJECT-TYPE
        SYNTAX INTEGER {
                        enable(1),
                        disable(2)
                        }
        MAX-ACCESS read-write
        STATUS current
        DESCRIPTION
            "Indicates whether hpnicfNdTabFullTrap traps
            should be generated when the ND table is filled."
        DEFVAL { enable }
        ::= { hpnicfNdTabStatGroup 1 }

    hpnicfNdTabTrapInterval OBJECT-TYPE
        SYNTAX Integer32 (30..3600)
        UNITS "seconds"
        MAX-ACCESS read-write
        STATUS current
        DESCRIPTION
            "Definition of the minimum interval between two traps
            which occur when the ND table is filled."
        DEFVAL { 30 }
        ::= { hpnicfNdTabStatGroup 2 }

    hpnicfNdTabTrapInfo OBJECT IDENTIFIER ::= { hpnicfNdTabStatGroup 3 }

    hpnicfNdTabLen OBJECT-TYPE
        SYNTAX Integer32
        MAX-ACCESS accessible-for-notify
        STATUS current
        DESCRIPTION
            "The length of the ND table."
        ::= { hpnicfNdTabTrapInfo 1 }

    hpnicfNdTabTrap OBJECT IDENTIFIER ::= { hpnicfNdTabStatGroup 4 }

    hpnicfNdTabFullTrap NOTIFICATION-TYPE
            OBJECTS { hpnicfNdTabLen }
            STATUS current
            DESCRIPTION
                "Send this trap when the ND table is filled.  The
                interval between two traps generated should be longer
                than hpnicfNdTabTrapInterval."
            ::= { hpnicfNdTabTrap 1 }

-- Describe SNMP periodical trap group
    hpnicfPeriodicalTrapGroup OBJECT IDENTIFIER ::= { hpnicfTableGroup 6 }

-- Describe objects for SNMP periodical trap
    hpnicfPeriodicalTrapObjects OBJECT IDENTIFIER
        ::= { hpnicfPeriodicalTrapGroup 1 }

    hpnicfPeriodicalTrapInterval OBJECT-TYPE
        SYNTAX Integer32 (0|10..3600)
        UNITS "seconds"
        MAX-ACCESS read-write
        STATUS current
        DESCRIPTION
            "Definition of the periodical interval.
            If no trap occurs during the certain interval, an hpnicfPeriodicalTrap
            will be generated.
            If the interval is set to 0, no hpnicfPeriodicalTrap will be generated."
        DEFVAL { 60 }
        ::= { hpnicfPeriodicalTrapObjects 1 }

    hpnicfPeriodicalTrapSwitch OBJECT-TYPE
        SYNTAX INTEGER {
                        enable(1),
                        disable(2)
                        }
        MAX-ACCESS read-write
        STATUS current
        DESCRIPTION
            "Definition of the periodical switch.
            If the value is off,the hpnicfPeriodicalTrap will not be generated.
            the hpnicfPeriodicalTrapInterval will be set to 0."
        DEFVAL { enable }
        ::= { hpnicfPeriodicalTrapObjects 2 }

    hpnicfPeriodicalTrapSwitch2 OBJECT-TYPE
        SYNTAX INTEGER {
                        off(0),
                        on(1)
                        }
        MAX-ACCESS read-write
        STATUS current
        DESCRIPTION
            "Periodical heartbeat trap sending switch.
            If the value is off, the hpnicfPeriodicalTrap will not be generated,
            and the hpnicfPeriodicalTrapInterval will be set to 0.  This node
            differs from hpnicfPeriodicalTrapSwitch in value."
        DEFVAL { on }
        ::= { hpnicfPeriodicalTrapObjects 3 }

-- Describe information for SNMP periodical trap
    hpnicfPeriodicalTrapInfo OBJECT IDENTIFIER
        ::= { hpnicfPeriodicalTrapGroup 2 }

-- Describe SNMP periodical trap
    hpnicfPeriodicalNotification OBJECT IDENTIFIER
        ::= { hpnicfPeriodicalTrapGroup 3 }

    hpnicfPeriodicalNotificationPrefix OBJECT IDENTIFIER
        ::= { hpnicfPeriodicalNotification 0 }

    hpnicfPeriodicalTrap NOTIFICATION-TYPE
            STATUS current
            DESCRIPTION
                "If no trap occurs during the interval spicified by
                hpnicfPeriodicalTrapInterval, an hpnicfPeriodicalTrap
                will be generated. If the interval is set to 0, no
                hpnicfPeriodicalTrap will be generated."
            ::= { hpnicfPeriodicalNotificationPrefix 1 }

-- Describe SNMP TrapDesInfo group
    hpnicfTrapDesInfo OBJECT IDENTIFIER ::= { hpnicfTableGroup 7 }

    hpnicfTrapDesInfoTable OBJECT-TYPE
            SYNTAX SEQUENCE OF HpnicfTrapDesInfoEntry
            MAX-ACCESS not-accessible
            STATUS current
            DESCRIPTION
                "A table of trap destination host address and port ."
            ::= { hpnicfTrapDesInfo 1 }

    hpnicfTrapDesInfoEntry OBJECT-TYPE
            SYNTAX HpnicfTrapDesInfoEntry
            MAX-ACCESS not-accessible
            STATUS current
            DESCRIPTION
                "The entry of trap destination host address and port."
            INDEX { hpnicfTrapDesInfoIndex }
            ::= { hpnicfTrapDesInfoTable 1 }

    HpnicfTrapDesInfoEntry ::=
            SEQUENCE {
                hpnicfTrapDesInfoIndex Integer32,
                hpnicfTrapDesIPAddress IpAddress,
                hpnicfTrapDesPort Integer32,
                hpnicfTrapDesRowStatus  RowStatus,
                hpnicfTrapDesAddrTAddress TAddress
            }

    hpnicfTrapDesInfoIndex OBJECT-TYPE
            SYNTAX Integer32 (1..20)
            MAX-ACCESS not-accessible
            STATUS current
            DESCRIPTION
                "The index of this table."
            ::= { hpnicfTrapDesInfoEntry 1 }

    hpnicfTrapDesIPAddress OBJECT-TYPE
            SYNTAX IpAddress
            MAX-ACCESS read-create
            STATUS current
            DESCRIPTION
                "The host IP address of the trap destination."
            ::= { hpnicfTrapDesInfoEntry 2 }

    hpnicfTrapDesPort OBJECT-TYPE
            SYNTAX Integer32 (0..65535)
            MAX-ACCESS read-create
            STATUS current
            DESCRIPTION
                "The port of the trap destination."
            ::= { hpnicfTrapDesInfoEntry 3 }

    hpnicfTrapDesRowStatus OBJECT-TYPE
            SYNTAX RowStatus
            MAX-ACCESS read-create
            STATUS current
            DESCRIPTION
                "The status of this table entry."
            ::= { hpnicfTrapDesInfoEntry 4 }

    hpnicfTrapDesAddrTAddress OBJECT-TYPE
            SYNTAX TAddress
            MAX-ACCESS read-create
            STATUS current
            DESCRIPTION
                "This object contains a transport address."
            ::= { hpnicfTrapDesInfoEntry 5 }

-- Describe SNMP TrapConfig group
    hpnicfTrapConfig OBJECT IDENTIFIER ::= { hpnicfTableGroup 8 }

    hpnicfTrapConfigTable OBJECT-TYPE
            SYNTAX SEQUENCE OF HpnicfTrapConfigEntry
            MAX-ACCESS not-accessible
            STATUS current
            DESCRIPTION
                "A table of trap configuration."
            ::= { hpnicfTrapConfig 1 }

    hpnicfTrapConfigEntry OBJECT-TYPE
            SYNTAX HpnicfTrapConfigEntry
            MAX-ACCESS not-accessible
            STATUS current
            DESCRIPTION
                "The entry of trap configuration."
            INDEX { hpnicfTrapConfigIndex }
            ::= { hpnicfTrapConfigTable 1 }

    HpnicfTrapConfigEntry ::=
            SEQUENCE {
                    hpnicfTrapConfigIndex Integer32,
                    hpnicfTrapConfigName SnmpAdminString,
                    hpnicfTrapConfigDescr SnmpAdminString,
                    hpnicfTrapConfigSwitch INTEGER,
                    hpnicfTrapConfigSwitch2 INTEGER
            }

    hpnicfTrapConfigIndex OBJECT-TYPE
            SYNTAX Integer32 (1..2147483647)
            MAX-ACCESS not-accessible
            STATUS current
            DESCRIPTION
                "The index of this table."
            ::= { hpnicfTrapConfigEntry 1 }

    hpnicfTrapConfigName OBJECT-TYPE
            SYNTAX SnmpAdminString (SIZE(0..127))
            MAX-ACCESS read-only
            STATUS current
            DESCRIPTION
                "The name of the appointed traps."
            ::= { hpnicfTrapConfigEntry 2 }

    hpnicfTrapConfigDescr OBJECT-TYPE
            SYNTAX SnmpAdminString (SIZE(0..127))
            MAX-ACCESS read-write
            STATUS current
            DESCRIPTION
                "The description of the appointed traps."
            ::= { hpnicfTrapConfigEntry 3 }

    hpnicfTrapConfigSwitch OBJECT-TYPE
            SYNTAX INTEGER {
                            enable(1),
                            disable(2)
                            }
            MAX-ACCESS read-write
            STATUS current
            DESCRIPTION
                "Indicates whether the specified traps
                should be generated."
            DEFVAL { enable }
            ::= { hpnicfTrapConfigEntry 4 }

    hpnicfTrapConfigSwitch2 OBJECT-TYPE
            SYNTAX INTEGER {
                            off(0),
                            on(1)
                            }
            MAX-ACCESS read-write
            STATUS current
            DESCRIPTION
                "Indicates whether the specified traps should be generated.
                This node differs from hpnicfTrapConfigSwitch in value."
            DEFVAL { on }
            ::= { hpnicfTrapConfigEntry 5 }

END
