-- ==========================================================================
-- Copyright (c) 2010-2014 Hewlett-Packard Development Company, L.P.
--
-- Description: The purpose of this MIB file is to provide object definition
--              of WLAN radio resource management (RRM).
-- Reference:
-- Version: V1.7
-- History:
-- V1.0 2008-07-16 Initial version, created by ChenWei
-- V1.1 2009-04-16 modified by WangChunsheng
-- Add new table of hpnicfDot11MonitorDetectedDevTable for hpnicfDot11MonitorDetectedGroup.
-- Add new table of hpnicfDot11RRMAPCfgTable for hpnicfDot11RRMConfigGroup.
-- V1.2 2009-05-07 modified by Wang Shaojie, wangchunsheng
--      Add hpnicfDot11APInterfNumThreshhd, hpnicfDot11StaInterfNumThreshhd
--      to hpnicfDot11GlobeConfigGroup.
--      Modify hpnicfDot11RRMCfgIntrvl
-- V1.3 2009-05-07 modified by Wang Shaojie
--      Add new node hpnicfDot11MonitorDevSNR to hpnicfDot11MonitorDetectedDevTable
-- V1.4 2010-02-22 modified by Wang Chunsheng
--      Add new table hpnicfDot11RRMSDRadioGroupTable to hpnicfDot11RRMConfigGroup
--      2010-03-18 Modified by Wang Lu
--      Add hpnicfDot11RRMAPCfg2Table
-- V1.5 2010-09-21 Modified by wu xiaopeng
--      Add new node hpnicfDot11RRMCoChlIntfTrapThhd, hpnicfDot11RRMAdjChlIntfTrapThhd
--      to hpnicfDot11RRMAPCfg2Table
--      2011-03-23 Modified by NiuJian
--      Add new node hpnicfDot11RrmNbrSSID
--      to hpnicfDot11RRMNbrInfoTable
-- V1.6 2013-03-23 Modified by GaoFei
--      Change SYNTAX of hpnicfDot11RRMCfgPERThres,hpnicfDot11RRMCfgToleranceFctr
-- V1.7 2013-09-02 Modified by Zhang Siyu
--      Add new table hpnicfDot11RRMRadioNbrInfoTable to hpnicfDot11RRMDetectGroup
--      2013-11-19 Modified by wubin
--      Add new node hpnicfDot11RRM11nMultiCastMcs
--      to hpnicfDot11RRMGlobalCfgPara
--      2013-12-21 Modified by wubin
--      Add new node hpnicfDot11RRM11acMadtMaxNss, hpnicfDot11RRM11acSuptMaxNss,
--      hpnicfDot11RRM11acMultiCastNss, hpnicfDot11RRM11acMultiCastVhtMcs
--      to hpnicfDot11RRMGlobalCfgPara
-- ==========================================================================
HPN-ICF-DOT11-RRM-MIB DEFINITIONS ::= BEGIN

IMPORTS
    HpnicfDot11RadioType, HpnicfDot11ChannelScopeType, HpnicfDot11RadioElementIndex,
    HpnicfDot11RadioScopeType, hpnicfDot11APElementIndex
        FROM HPN-ICF-DOT11-REF-MIB
    Integer32, Unsigned32, OBJECT-TYPE, MODULE-IDENTITY,
    NOTIFICATION-TYPE
        FROM SNMPv2-SMI
    TruthValue, MacAddress, DateAndTime, RowStatus
        FROM SNMPv2-TC
    hpnicfDot11,
    HpnicfDot11ObjectIDType,
    HpnicfDot11SSIDStringType
        FROM HPN-ICF-DOT11-REF-MIB;

hpnicfDot11RRM MODULE-IDENTITY
    LAST-UPDATED "201009251800Z"        -- Sep 25, 2010 at 18:00 GMT
    ORGANIZATION
        ""
    CONTACT-INFO
        ""
    DESCRIPTION
        "This MIB file is to provide the object definition of
        WLAN radio resource management (RRM)."

    REVISION "201009251800Z"        -- Sep 25, 2010 at 18:00 GMT
    DESCRIPTION
        "Modified to add new nodes."
    REVISION "201002231800Z"        -- Feb 23, 2010 at 18:00 GMT
    DESCRIPTION
        "Modified to add new nodes."
    REVISION "200908012000Z"        -- Aug 1, 2009 at 20:00 GMT
    DESCRIPTION
        "Modified to add new nodes and new table."
    REVISION "200905072000Z"        -- May 7, 2009 at 20:00 GMT
    DESCRIPTION
        "Modified to add new nodes and new table."
    REVISION "200904172000Z"        -- April 17, 2009 at 20:00 GMT
    DESCRIPTION
        "Modified to add new table and new group."
    REVISION "200807141429Z"
    DESCRIPTION
        "The initial revision of this MIB module."
    ::= { hpnicfDot11 8 }

--
-- Node definitions
--

hpnicfDot11RRMConfigGroup OBJECT IDENTIFIER ::= { hpnicfDot11RRM 1 }

hpnicfDot11RRMGlobalCfgPara OBJECT IDENTIFIER ::= { hpnicfDot11RRMConfigGroup 1 }

hpnicfDot11RRM11nMadtMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { hpnicfDot11RRMGlobalCfgPara 1 }

hpnicfDot11RRM11nSuptMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { hpnicfDot11RRMGlobalCfgPara 2 }

hpnicfDot11RRM11gProtect OBJECT-TYPE
    SYNTAX TruthValue
    MAX-ACCESS read-write
    STATUS current
    DESCRIPTION
        "Enable/Disable dot11g protection."
    DEFVAL { false }
    ::= { hpnicfDot11RRMGlobalCfgPara 3 }

hpnicfDot11RRM11aPwrConstrt OBJECT-TYPE
    SYNTAX Integer32
    UNITS "dBm"
    MAX-ACCESS read-write
    STATUS current
    DESCRIPTION
        "Configure the power constraint for all 802.11a radios.
        The configured power constraint is advertised in beacons if spectrum
        management is enabled.
        The range of power constraint is 0 to MAX-POWER-1 (where the MAX-POWER
        is defined by the regulatory domain)."
    DEFVAL { 0 }
    ::= { hpnicfDot11RRMGlobalCfgPara 4 }

hpnicfDot11RRM11aSpectrumManag OBJECT-TYPE
    SYNTAX TruthValue
    MAX-ACCESS read-write
    STATUS current
    DESCRIPTION
        "Enable/Disable spectrum management for 802.11a radios.
        When spectrum management is enabled, the WLAN sub-system advertises
        power capabilities of the AP and power constraints applicable to all
        devices in the BSS based on regulatory domain specification."
    DEFVAL { false }
    ::= { hpnicfDot11RRMGlobalCfgPara 5 }

hpnicfDot11RRMAutoChlAvoid11h OBJECT-TYPE
    SYNTAX TruthValue
    MAX-ACCESS read-write
    STATUS current
    DESCRIPTION
        "Configure the auto-channel set as non-dot11h channels, this is,
        only the non-dot11h channels belonging to the country code are scanned
        during initial channel selection and one of them is selected."
    DEFVAL { false }
    ::= { hpnicfDot11RRMGlobalCfgPara 6 }

hpnicfDot11RRMScanChl OBJECT-TYPE
    SYNTAX INTEGER
        {
        auto(1),
        all(2)
        }
    MAX-ACCESS read-write
    STATUS current
    DESCRIPTION
        "Set the scan mode.
        auto: When this option is set, all channels of the country code being
              set are scanned.
        all: When this option is set, all the channels of the radio band are
             scanned."
    DEFVAL { auto }
    ::= { hpnicfDot11RRMGlobalCfgPara 7 }

hpnicfDot11RRMScanRptIntvel OBJECT-TYPE
    SYNTAX Integer32 (5..120)
    UNITS "second"
    MAX-ACCESS read-write
    STATUS current
    DESCRIPTION
        "Set the scan report interval."
    DEFVAL { 10 }
    ::= { hpnicfDot11RRMGlobalCfgPara 8 }

hpnicfDot11APInterfNumThreshhd OBJECT-TYPE
    SYNTAX      Integer32
    MAX-ACCESS  read-write
    STATUS      current
    DESCRIPTION
        "Represents threshold of AP interference .
         If the value of AP interference exceeds this threshold,
         AP interference trap will be sent. If the value of this node
         is zero, AP interference trap will be sent immediately."

    DEFVAL      { 0 }
    ::= { hpnicfDot11RRMGlobalCfgPara 9 }

hpnicfDot11StaInterfNumThreshhd OBJECT-TYPE
    SYNTAX      Integer32
    MAX-ACCESS  read-write
    STATUS      current
    DESCRIPTION
        "Represents threshold of STA interference.
         If the value of STA interference exceeds this threshold,
         STA interference trap will be sent. If the value of this
         node is zero, STA interference trap will be sent immediately.
         "
    DEFVAL      { 0 }
    ::= { hpnicfDot11RRMGlobalCfgPara 10 }

hpnicfDot11RRM11nMultiCastMcs OBJECT-TYPE
    SYNTAX Unsigned32 (0..76 | 4294967295)
    MAX-ACCESS read-write
    STATUS current
    DESCRIPTION
        "Specify the modulation and coding scheme (MCS) index for 802.11n
        multicast rates.
        The value 4294967295 indicates that no MCS index is specified.
        No MCS index is specified for 802.11n multicast rates by default.
        Besides 4294967295, the specified MCS index for 802.11n multicast
        rates must be no less than the specified maximum MCS index for 802.11n
        mandatory rates.
        Before configure the MCS index for 802.11n multicast rates, the maximum
        MCS index for 802.11n mandatory rates must be configured"
    DEFVAL { 4294967295 }
    ::= { hpnicfDot11RRMGlobalCfgPara 11 }

hpnicfDot11RRM11acMadtMaxNss OBJECT-TYPE
    SYNTAX Integer32 (0..8)
    MAX-ACCESS read-write
    STATUS current
    DESCRIPTION
        "Specify the maximum NSS index for 802.11ac mandatory rates.
        The value 0 indicates that no maximum NSS index is specified.
        No maximum NSS index is specified for 802.11ac mandatory rates by default.
        The specified maximum NSS index for 802.11ac supported rates must be no less
        than the specified maximum NSS index for 802.11ac mandatory rates."
    DEFVAL { 0 }
    ::= { hpnicfDot11RRMGlobalCfgPara 12 }

hpnicfDot11RRM11acSuptMaxNss OBJECT-TYPE
    SYNTAX Integer32 (1..8)
    MAX-ACCESS read-write
    STATUS current
    DESCRIPTION
        "Specify the maximum NSS index for 802.11ac supported rates.
        The specified maximum NSS index for 802.11ac supported rates must be no
        less than the specified maximum NSS index for 802.11ac mandatory rates."
    DEFVAL { 8 }
    ::= { hpnicfDot11RRMGlobalCfgPara 13 }

hpnicfDot11RRM11acMultiCastNss OBJECT-TYPE
    SYNTAX Integer32 (0..8)
    MAX-ACCESS read-write
    STATUS current
    DESCRIPTION
        "Specify the NSS index for 802.11ac multicast rates.
        The value 0 indicates that no NSS index is specified.
        No NSS index is specified for 802.11ac multicast rates by default.
        The specified NSS index for 802.11ac multicast rates must be no less
        than the specified maximum NSS index for 802.11ac mandatory rates.
        Before configuring the NSS index for 802.11ac multicast rates, the maximum
        NSS index for 802.11ac mandatory rates must be configured.
        Besides, it must be configured together with the node below."
    DEFVAL { 0 }
    ::= { hpnicfDot11RRMGlobalCfgPara 14 }

hpnicfDot11RRM11acMultiCastVhtMcs OBJECT-TYPE
    SYNTAX Integer32 (0..9 | 255)
    MAX-ACCESS read-write
    STATUS current
    DESCRIPTION
        "Specify the MCS index for 802.11ac multicast rates.
        The value 255 indicates that no MCS index is specified.
        No MCS index is specified for 802.11ac multicast rates by default.
        Besides, it must be configured together with the node above."
    DEFVAL { 255 }
    ::= { hpnicfDot11RRMGlobalCfgPara 15 }

hpnicfDot11RRMRadioCfgTable OBJECT-TYPE
    SYNTAX SEQUENCE OF HpnicfDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    ::= { hpnicfDot11RRMConfigGroup 2 }

hpnicfDot11RRMRadioCfgEntry OBJECT-TYPE
    SYNTAX HpnicfDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    INDEX { hpnicfDot11RRMRadioType }
    ::= { hpnicfDot11RRMRadioCfgTable 1 }

HpnicfDot11RRMRadioCfgEntry ::=
    SEQUENCE {
        hpnicfDot11RRMRadioType
            HpnicfDot11RadioType,
        hpnicfDot11RRMCfgChlState
            TruthValue,
        hpnicfDot11RRMCfgChlMode
            INTEGER,
        hpnicfDot11RRMChlProntoRadioElmt
            Unsigned32,
        hpnicfDot11RRMCfgPwrState
            TruthValue,
        hpnicfDot11RRMCfgPwrMode
            INTEGER,
        hpnicfDot11RRMPwrProntoRadioElmt
            Unsigned32,
        hpnicfDot11RRMCfgIntrvl
            Integer32,
        hpnicfDot11RRMCfgIntrfThres
            Integer32,
        hpnicfDot11RRMCfgNoiseThres
            Integer32,
        hpnicfDot11RRMCfgPERThres
            Integer32,
        hpnicfDot11RRMCfgToleranceFctr
            Integer32,
        hpnicfDot11RRMCfgAdjacencyFctr
            Integer32
     }

hpnicfDot11RRMRadioType OBJECT-TYPE
    SYNTAX HpnicfDot11RadioType
    MAX-ACCESS not-accessible
    STATUS current
    DESCRIPTION
        "802.11 radio type."
    ::= { hpnicfDot11RRMRadioCfgEntry 1 }

hpnicfDot11RRMCfgChlState OBJECT-TYPE
    SYNTAX TruthValue
    MAX-ACCESS read-write
    STATUS current
    DESCRIPTION
        "Enable/Disable dynamic channel selection."
    DEFVAL { false }
    ::= { hpnicfDot11RRMRadioCfgEntry 2 }

hpnicfDot11RRMCfgChlMode OBJECT-TYPE
    SYNTAX INTEGER
        {
        selfDecisive(1),
        userTriggered(2)
        }
    MAX-ACCESS read-write
    STATUS current
    DESCRIPTION
        "Configure the mode of channel selection.
        This node can be configured only when dynamic channel selection
        is enabled."
    DEFVAL { userTriggered }
    ::= { hpnicfDot11RRMRadioCfgEntry 3 }

hpnicfDot11RRMChlProntoRadioElmt OBJECT-TYPE
    SYNTAX Unsigned32
    MAX-ACCESS read-write
    STATUS current
    DESCRIPTION
        "Specify the AP and radio that will change channel at next
        calibration cycle.
        0 is returned when getting the value of this node.
        This node can be configured only when the mode of channel selection
        control is user-triggered.
        When configuring, the higher 24 bits stand for the AP index,
        and the last 8 bits stand for the radio index.
        4294967295 stand for configuring each radio on all APs."
    DEFVAL { 0 }
    ::= { hpnicfDot11RRMRadioCfgEntry 4 }

hpnicfDot11RRMCfgPwrState OBJECT-TYPE
    SYNTAX TruthValue
    MAX-ACCESS read-write
    STATUS current
    DESCRIPTION
        "Enable/Disable dynamic power selection for the band."
    DEFVAL { false }
    ::= { hpnicfDot11RRMRadioCfgEntry 5 }

hpnicfDot11RRMCfgPwrMode OBJECT-TYPE
    SYNTAX INTEGER
        {
        selfDecisive(1),
        userTriggered(2)
        }
    MAX-ACCESS read-write
    STATUS current
    DESCRIPTION
        "Configure the mode of transmit power control.
        This node can be configured only when dynamic power selection
        is enabled."
    DEFVAL { userTriggered }
    ::= { hpnicfDot11RRMRadioCfgEntry 6 }

hpnicfDot11RRMPwrProntoRadioElmt OBJECT-TYPE
    SYNTAX Unsigned32
    MAX-ACCESS read-write
    STATUS current
    DESCRIPTION
        "Specify the AP and radio that will change power at next
        calibration cycle.
        0 is returned when getting the value of this node.
        This node can be configured only when the mode of transmit power
        control is user-triggered.
        When configuring, the higher 24 bits stand for the AP index,
        and the last 8 bits stand for the radio index.
        4294967295 stand for configuring each radio on all APs."
    DEFVAL { 0 }
    ::= { hpnicfDot11RRMRadioCfgEntry 7 }

hpnicfDot11RRMCfgIntrvl OBJECT-TYPE
    SYNTAX Integer32
    UNITS "minute"
    MAX-ACCESS read-write
    STATUS current
    DESCRIPTION
        "Configure the calibration interval."
    DEFVAL { 8 }
    ::= { hpnicfDot11RRMRadioCfgEntry 8 }

hpnicfDot11RRMCfgIntrfThres OBJECT-TYPE
    SYNTAX Integer32 (40..100)
    UNITS "percent"
    MAX-ACCESS read-write
    STATUS current
    DESCRIPTION
        "Configure the interface threshold.
        By default, interference observed on an operating channel is considered
        during dynamic frequency selection and transmit power control.  If the
        interference percentage on the channel reaches the set threshold, RRM
        will perform resource adjustment to control the situation."
    DEFVAL { 50 }
    ::= { hpnicfDot11RRMRadioCfgEntry 9 }

hpnicfDot11RRMCfgNoiseThres OBJECT-TYPE
    SYNTAX Integer32 (-127..127)
    MAX-ACCESS read-write
    STATUS current
    DESCRIPTION
        "Configure the noise threshold."
    DEFVAL { -70 }
    ::= { hpnicfDot11RRMRadioCfgEntry 10 }

hpnicfDot11RRMCfgPERThres OBJECT-TYPE
    SYNTAX Integer32 (1..100)
    UNITS "percent"
    MAX-ACCESS read-write
    STATUS current
    DESCRIPTION
        "Configure the CRC error threshold.
        If the percentage of CRC errors reaches the threshold, RRM will perform
        resource adjustment to control the situation."
    DEFVAL { 20 }
    ::= { hpnicfDot11RRMRadioCfgEntry 11 }

hpnicfDot11RRMCfgToleranceFctr OBJECT-TYPE
    SYNTAX Integer32 (1..45)
    UNITS "percent"
    MAX-ACCESS read-write
    STATUS current
    DESCRIPTION
        "Configure the tolerance level.
        During dynamic frequency selection (DFS), the channel will be changed
        only if there is a better channel having lesser interference and packet
        error rate than those specified by the user."
    DEFVAL { 20 }
    ::= { hpnicfDot11RRMRadioCfgEntry 12 }

hpnicfDot11RRMCfgAdjacencyFctr OBJECT-TYPE
    SYNTAX Integer32 (1..16)
    MAX-ACCESS read-write
    STATUS current
    DESCRIPTION
        "Configure the adjacency factor for the band.
        If transmit power control (TPC) is configured, power will be adjusted
        when the nth neighbor is detected.  The value n is the adjacency factor."
    DEFVAL { 3 }
    ::= { hpnicfDot11RRMRadioCfgEntry 13 }

hpnicfDot11RRMAPCfgTable OBJECT-TYPE
    SYNTAX SEQUENCE OF HpnicfDot11RRMAPCfgEntry
    MAX-ACCESS not-accessible
    STATUS current
    DESCRIPTION
        "This table defines the RRM parameters for AP."
    ::= { hpnicfDot11RRMConfigGroup 3 }

hpnicfDot11RRMAPCfgEntry OBJECT-TYPE
    SYNTAX HpnicfDot11RRMAPCfgEntry
    MAX-ACCESS not-accessible
    STATUS current
    DESCRIPTION
        "Each entry contains information of RRM parameters for AP."
    INDEX { hpnicfDot11APElementIndex }
    ::= { hpnicfDot11RRMAPCfgTable 1 }

HpnicfDot11RRMAPCfgEntry ::=
    SEQUENCE {
        hpnicfDot11RRMAPWorkMode
          INTEGER
    }

hpnicfDot11RRMAPWorkMode OBJECT-TYPE
    SYNTAX INTEGER
        {
        normal(1),
        monitor(2),
        hybrid(3)
        }
    MAX-ACCESS read-write
    STATUS current
    DESCRIPTION
        "AP work mode."
    ::= { hpnicfDot11RRMAPCfgEntry 1 }

hpnicfDot11RRMSDRadioGroupTable OBJECT-TYPE
    SYNTAX SEQUENCE OF HpnicfDot11RRMSDRadioGroupEntry
    MAX-ACCESS not-accessible
    STATUS current
    DESCRIPTION
        "This table defines RRM self-decisive radio group."
    ::= { hpnicfDot11RRMConfigGroup 4 }

hpnicfDot11RRMSDRadioGroupEntry OBJECT-TYPE
    SYNTAX      HpnicfDot11RRMSDRadioGroupEntry
    MAX-ACCESS  not-accessible
    STATUS      current
    DESCRIPTION
        "Each entry contains information of one RRM self-decisive radio group."
    INDEX
        {
            hpnicfDot11RRMSDRadioGroupId
        }
    ::= { hpnicfDot11RRMSDRadioGroupTable 1 }

HpnicfDot11RRMSDRadioGroupEntry ::= SEQUENCE
    {
        hpnicfDot11RRMSDRadioGroupId             Unsigned32,
        hpnicfDot11RRMSDRadioGroupDesc           OCTET STRING,
        hpnicfDot11RRMSDRdGrpChlHolddownTm       Unsigned32,
        hpnicfDot11RRMSDRdGrpPwrHolddownTm       Unsigned32,
        hpnicfDot11RRMSDRdGroupRowStatus         RowStatus
    }

hpnicfDot11RRMSDRadioGroupId OBJECT-TYPE
    SYNTAX      Unsigned32
    MAX-ACCESS  not-accessible
    STATUS      current
    DESCRIPTION
        "Represents RRM self-decisive radio group ID."
    ::= { hpnicfDot11RRMSDRadioGroupEntry 1 }

hpnicfDot11RRMSDRadioGroupDesc OBJECT-TYPE
    SYNTAX      OCTET STRING
    MAX-ACCESS  read-create
    STATUS      current
    DESCRIPTION
        "Represents the description of RRM self-decisive radio group."
    ::= { hpnicfDot11RRMSDRadioGroupEntry 2 }

hpnicfDot11RRMSDRdGrpChlHolddownTm OBJECT-TYPE
    SYNTAX      Unsigned32
    UNITS       "minute"
    MAX-ACCESS  read-create
    STATUS      current
    DESCRIPTION
        "Represents the channel holddown time of RRM self-decisive radio group."
    ::= { hpnicfDot11RRMSDRadioGroupEntry 3 }

hpnicfDot11RRMSDRdGrpPwrHolddownTm OBJECT-TYPE
    SYNTAX      Unsigned32
    UNITS       "minute"
    MAX-ACCESS  read-create
    STATUS      current
    DESCRIPTION
        "Represents the power holddown time of RRM self-decisive radio group."
    ::= { hpnicfDot11RRMSDRadioGroupEntry 4 }

hpnicfDot11RRMSDRdGroupRowStatus OBJECT-TYPE
    SYNTAX      RowStatus
    MAX-ACCESS  read-create
    STATUS      current
    DESCRIPTION
        "The row status of this table entry."
    ::= { hpnicfDot11RRMSDRadioGroupEntry 5 }

hpnicfDot11RRMAPCfg2Table OBJECT-TYPE
    SYNTAX SEQUENCE OF HpnicfDot11RRMAPCfg2Entry
    MAX-ACCESS not-accessible
    STATUS current
    DESCRIPTION
        "This table defines the RRM parameters for AP."
    ::= { hpnicfDot11RRMConfigGroup 5 }

hpnicfDot11RRMAPCfg2Entry OBJECT-TYPE
    SYNTAX HpnicfDot11RRMAPCfg2Entry
    MAX-ACCESS not-accessible
    STATUS current
    DESCRIPTION
        "Each entry contains information of RRM parameters for AP."
    INDEX { hpnicfDot11RRMAPSerialID }
    ::= { hpnicfDot11RRMAPCfg2Table 1 }

HpnicfDot11RRMAPCfg2Entry ::=
    SEQUENCE {
        hpnicfDot11RRMAPSerialID
            HpnicfDot11ObjectIDType,
        hpnicfDot11RRMAPIntfThreshold
            Integer32,
        hpnicfDot11RRMStaIntfThreshold
            Integer32,
        hpnicfDot11RRMCoChlIntfTrapThhd
            Integer32,
        hpnicfDot11RRMAdjChlIntfTrapThhd
            Integer32
    }

hpnicfDot11RRMAPSerialID OBJECT-TYPE
    SYNTAX HpnicfDot11ObjectIDType
    MAX-ACCESS not-accessible
    STATUS current
    DESCRIPTION
        "Serial ID of the AP."
    ::= { hpnicfDot11RRMAPCfg2Entry 1 }

hpnicfDot11RRMAPIntfThreshold OBJECT-TYPE
    SYNTAX Integer32
    MAX-ACCESS read-write
    STATUS current
    DESCRIPTION
        "Represents threshold of AP interference .
         If the number of AP interference exceeds this threshold,
         AP interference trap will be sent."
    ::= { hpnicfDot11RRMAPCfg2Entry 2 }

hpnicfDot11RRMStaIntfThreshold OBJECT-TYPE
    SYNTAX Integer32
    MAX-ACCESS read-write
    STATUS current
    DESCRIPTION
        "Represents threshold of STA interference.
         If the number of STA interference exceeds this threshold,
         station interference trap will be sent."
    ::= { hpnicfDot11RRMAPCfg2Entry 3 }

hpnicfDot11RRMCoChlIntfTrapThhd OBJECT-TYPE
    SYNTAX      Integer32
    UNITS       "dbm"
    MAX-ACCESS  read-write
    STATUS      current
    DESCRIPTION
        "Represents threshold of interference trap with current ap.
        If signal strength of the device exceeds this threshold,
        corresponding trap will be sent."
    ::= { hpnicfDot11RRMAPCfg2Entry 4 }


hpnicfDot11RRMAdjChlIntfTrapThhd OBJECT-TYPE
    SYNTAX      Integer32
    UNITS       "dbm"
    MAX-ACCESS  read-write
    STATUS      current
    DESCRIPTION
        "Represents threshold of adjacent interference trap with current ap.
        If signal strength of the device exceeds this threshold,
        corresponding trap will be sent."
    ::= { hpnicfDot11RRMAPCfg2Entry 5 }

hpnicfDot11RRMDetectGroup OBJECT IDENTIFIER ::= { hpnicfDot11RRM 2 }

hpnicfDot11RRMChlRptTable OBJECT-TYPE
    SYNTAX SEQUENCE OF HpnicfDot11RRMChlRptEntry
    MAX-ACCESS not-accessible
    STATUS current
    DESCRIPTION
        "This table shows the RRM channel information of each radio
        on all APs."
    ::= { hpnicfDot11RRMDetectGroup 1 }

hpnicfDot11RRMChlRptEntry OBJECT-TYPE
    SYNTAX HpnicfDot11RRMChlRptEntry
    MAX-ACCESS not-accessible
    STATUS current
    DESCRIPTION
        "Each entry contains information of RRM channel information
        of the radio on the AP."
    INDEX { hpnicfDot11RRMRadioIndex, hpnicfDot11RRMChlRptChlNum }
    ::= { hpnicfDot11RRMChlRptTable 1 }

HpnicfDot11RRMChlRptEntry ::=
    SEQUENCE {
        hpnicfDot11RRMRadioIndex
            HpnicfDot11RadioElementIndex,
        hpnicfDot11RRMChlRptChlNum
            Integer32,
        hpnicfDot11RRMChlRptChlType
            INTEGER,
        hpnicfDot11RRMChlRptChlQlty
            INTEGER,
        hpnicfDot11RRMChlRptNbrCnt
            Integer32,
        hpnicfDot11RRMChlRptLoad
            Integer32,
        hpnicfDot11RRMChlRptUtlz
            Integer32,
        hpnicfDot11RRMChlRptIntrf
            Integer32,
        hpnicfDot11RRMChlRptPER
            Integer32,
        hpnicfDot11RRMChlRptRetryRate
            Integer32,
        hpnicfDot11RRMChlRptNoise
            Integer32,
        hpnicfDot11RRMChlRptRadarIndtcr
            INTEGER
     }

hpnicfDot11RRMRadioIndex OBJECT-TYPE
    SYNTAX HpnicfDot11RadioElementIndex
    MAX-ACCESS accessible-for-notify
    STATUS current
    DESCRIPTION
        "Represents index of the radio."
    ::= { hpnicfDot11RRMChlRptEntry 1 }

hpnicfDot11RRMChlRptChlNum OBJECT-TYPE
    SYNTAX Integer32
    MAX-ACCESS accessible-for-notify
    STATUS current
    DESCRIPTION
        "Channel number."
    ::= { hpnicfDot11RRMChlRptEntry 2 }

hpnicfDot11RRMChlRptChlType OBJECT-TYPE
    SYNTAX INTEGER
        {
        primeChannel(1),
        offChannel(2)
        }
    MAX-ACCESS read-only
    STATUS current
    DESCRIPTION
        "Channel type."
    ::= { hpnicfDot11RRMChlRptEntry 3 }

hpnicfDot11RRMChlRptChlQlty OBJECT-TYPE
    SYNTAX INTEGER
        {
        good(1),
        bad(2)
        }
    MAX-ACCESS read-only
    STATUS current
    DESCRIPTION
        "Channel quality."
    ::= { hpnicfDot11RRMChlRptEntry 4 }

hpnicfDot11RRMChlRptNbrCnt OBJECT-TYPE
    SYNTAX Integer32
    MAX-ACCESS read-only
    STATUS current
    DESCRIPTION
        "Number of neighbors found on the channel."
    ::= { hpnicfDot11RRMChlRptEntry 5 }

hpnicfDot11RRMChlRptLoad OBJECT-TYPE
    SYNTAX Integer32 (0..100)
    UNITS "percent"
    MAX-ACCESS read-only
    STATUS current
    DESCRIPTION
        "Load observed on the channel in percentage."
    ::= { hpnicfDot11RRMChlRptEntry 6 }

hpnicfDot11RRMChlRptUtlz OBJECT-TYPE
    SYNTAX Integer32 (0..100)
    UNITS "percent"
    MAX-ACCESS read-only
    STATUS current
    DESCRIPTION
        "Utilization of the channel in percentage."
    ::= { hpnicfDot11RRMChlRptEntry 7 }

hpnicfDot11RRMChlRptIntrf OBJECT-TYPE
    SYNTAX Integer32 (0..100)
    UNITS "percent"
    MAX-ACCESS read-only
    STATUS current
    DESCRIPTION
        "Interference observed on the channel in percentage."
    ::= { hpnicfDot11RRMChlRptEntry 8 }

hpnicfDot11RRMChlRptPER OBJECT-TYPE
    SYNTAX Integer32 (0..100)
    UNITS "percent"
    MAX-ACCESS read-only
    STATUS current
    DESCRIPTION
        "Packet error rate observed on the channel in percentage."
    ::= { hpnicfDot11RRMChlRptEntry 9 }

hpnicfDot11RRMChlRptRetryRate OBJECT-TYPE
    SYNTAX Integer32 (0..100)
    UNITS "percent"
    MAX-ACCESS read-only
    STATUS current
    DESCRIPTION
        "Percentage of retransmission happened on the channel."
    ::= { hpnicfDot11RRMChlRptEntry 10 }

hpnicfDot11RRMChlRptNoise OBJECT-TYPE
    SYNTAX Integer32
    MAX-ACCESS read-only
    STATUS current
    DESCRIPTION
        "Noise observed on the channel."
    ::= { hpnicfDot11RRMChlRptEntry 11 }

hpnicfDot11RRMChlRptRadarIndtcr OBJECT-TYPE
    SYNTAX INTEGER
        {
        detected(1),
        notDetected(2)
        }
    MAX-ACCESS read-write
    STATUS current
    DESCRIPTION
        "Radar detection status."
    ::= { hpnicfDot11RRMChlRptEntry 12 }

hpnicfDot11RRMNbrInfoTable OBJECT-TYPE
    SYNTAX SEQUENCE OF HpnicfDot11RRMNbrInfoEntry
    MAX-ACCESS not-accessible
    STATUS current
    DESCRIPTION
        "This table shows the RRM neighbor information of each radio
        on all APs."
    ::= { hpnicfDot11RRMDetectGroup 2 }

hpnicfDot11RRMNbrInfoEntry OBJECT-TYPE
    SYNTAX HpnicfDot11RRMNbrInfoEntry
    MAX-ACCESS not-accessible
    STATUS current
    DESCRIPTION
        "Each entry contains information of RRM neighbor information
        of the radio on an AP."
    INDEX { hpnicfDot11RRMRadioIndex, hpnicfDot11RrmNbrBSSID }
    ::= { hpnicfDot11RRMNbrInfoTable 1 }

HpnicfDot11RRMNbrInfoEntry ::=
    SEQUENCE {
        hpnicfDot11RrmNbrBSSID
            MacAddress,
        hpnicfDot11RrmNbrChl
            HpnicfDot11ChannelScopeType,
        hpnicfDot11RRMNbrIntrf
            Integer32,
        hpnicfDot11RrmNbrRSSI
            Integer32,
        hpnicfDot11RrmNbrType
            INTEGER,
        hpnicfDot11RrmNbrSSID
            HpnicfDot11SSIDStringType
     }

hpnicfDot11RrmNbrBSSID OBJECT-TYPE
    SYNTAX MacAddress
    MAX-ACCESS not-accessible
    STATUS current
    DESCRIPTION
        "MAC address of the AP."
    ::= { hpnicfDot11RRMNbrInfoEntry 1 }

hpnicfDot11RrmNbrChl OBJECT-TYPE
    SYNTAX HpnicfDot11ChannelScopeType
    MAX-ACCESS read-only
    STATUS current
    DESCRIPTION
        "Channel number on which the neighbor was found."
    ::= { hpnicfDot11RRMNbrInfoEntry 2 }

hpnicfDot11RRMNbrIntrf OBJECT-TYPE
    SYNTAX Integer32 (0..100)
    UNITS "percent"
    MAX-ACCESS read-only
    STATUS current
    DESCRIPTION
        "Interference observed on the channel in percentage by neighbor."
    ::= { hpnicfDot11RRMNbrInfoEntry 3 }

hpnicfDot11RrmNbrRSSI OBJECT-TYPE
    SYNTAX Integer32
    UNITS "dBm"
    MAX-ACCESS read-only
    STATUS current
    DESCRIPTION
        "Signal strength of the AP in dBm."
    ::= { hpnicfDot11RRMNbrInfoEntry 4 }

hpnicfDot11RrmNbrType OBJECT-TYPE
    SYNTAX INTEGER
        {
        managed(1),
        unmanaged(2)
        }
    MAX-ACCESS read-only
    STATUS current
    DESCRIPTION
        "Type of the AP, managed or unmanaged."
    ::= { hpnicfDot11RRMNbrInfoEntry 5 }

hpnicfDot11RrmNbrSSID OBJECT-TYPE
    SYNTAX HpnicfDot11SSIDStringType
    MAX-ACCESS read-only
    STATUS current
    DESCRIPTION
        "SSID of the Neighbor."
    ::= { hpnicfDot11RRMNbrInfoEntry 6 }

hpnicfDot11RRMHistoryTable OBJECT-TYPE
    SYNTAX SEQUENCE OF HpnicfDot11RRMHistoryEntry
    MAX-ACCESS not-accessible
    STATUS current
    DESCRIPTION
        "This table shows the details of the latest three channel changes
        and power changes applied on all APs, including time of change,
        reason of the change and the channel, power, interference parameters."
    ::= { hpnicfDot11RRMDetectGroup 3 }

hpnicfDot11RRMHistoryEntry OBJECT-TYPE
    SYNTAX HpnicfDot11RRMHistoryEntry
    MAX-ACCESS not-accessible
    STATUS current
    DESCRIPTION
        "Each entry shows the details of channel and power changes."
    INDEX { hpnicfDot11RRMRadioIndex,
            hpnicfDot11RRMHistoryId,
            hpnicfDot11RRMHistoryRecIndctr }
    ::= { hpnicfDot11RRMHistoryTable 1 }

HpnicfDot11RRMHistoryEntry ::=
    SEQUENCE {
        hpnicfDot11RRMHistoryId
            Integer32,
        hpnicfDot11RRMHistoryRecIndctr
            INTEGER,
        hpnicfDot11RRMHistoryChl
            HpnicfDot11ChannelScopeType,
        hpnicfDot11RRMHistoryPwr
            Integer32,
        hpnicfDot11RRMHistoryLoad
            Integer32,
        hpnicfDot11RRMHistoryUtlz
            Integer32,
        hpnicfDot11RRMHistoryIntrf
            Integer32,
        hpnicfDot11RRMHistoryNoise
            Integer32,
        hpnicfDot11RRMHistoryPER
            Integer32,
        hpnicfDot11RRMHistoryRetryRate
            Integer32,
        hpnicfDot11RRMHistoryChgReason
            BITS,
        hpnicfDot11RRMHistoryChgDateTime
            DateAndTime
     }

hpnicfDot11RRMHistoryId OBJECT-TYPE
    SYNTAX Integer32
    MAX-ACCESS not-accessible
    STATUS current
    DESCRIPTION
        "History number of the change."
    ::= { hpnicfDot11RRMHistoryEntry 1 }

hpnicfDot11RRMHistoryRecIndctr OBJECT-TYPE
    SYNTAX INTEGER
        {
        before(1),
        after(2)
        }
    MAX-ACCESS not-accessible
    STATUS current
    DESCRIPTION
        "History record type of the change."
    ::= { hpnicfDot11RRMHistoryEntry 2 }

hpnicfDot11RRMHistoryChl OBJECT-TYPE
    SYNTAX HpnicfDot11ChannelScopeType
    MAX-ACCESS read-only
    STATUS current
    DESCRIPTION
        "Channel on which the radio operates before/after the change
        of channel or power."
    ::= { hpnicfDot11RRMHistoryEntry 3 }

hpnicfDot11RRMHistoryPwr OBJECT-TYPE
    SYNTAX Integer32
    UNITS "dBm"
    MAX-ACCESS read-only
    STATUS current
    DESCRIPTION
        "Power of the radio before/after the change of channel or
        power."
    ::= { hpnicfDot11RRMHistoryEntry 4 }

hpnicfDot11RRMHistoryLoad OBJECT-TYPE
    SYNTAX Integer32 (0..100)
    UNITS "percent"
    MAX-ACCESS read-only
    STATUS current
    DESCRIPTION
        "Load observed on the radio in percentage before/after the
        change of channel or power."
    ::= { hpnicfDot11RRMHistoryEntry 5 }

hpnicfDot11RRMHistoryUtlz OBJECT-TYPE
    SYNTAX Integer32 (0..100)
    UNITS "percent"
    MAX-ACCESS read-only
    STATUS current
    DESCRIPTION
        "Utilization of the radio in percentage before/after the
        change of channel or power."
    ::= { hpnicfDot11RRMHistoryEntry 6 }

hpnicfDot11RRMHistoryIntrf OBJECT-TYPE
    SYNTAX Integer32 (0..100)
    UNITS "percent"
    MAX-ACCESS read-only
    STATUS current
    DESCRIPTION
        "Interference observed on the radio in percentage
        before/after the change of channel or power."
    ::= { hpnicfDot11RRMHistoryEntry 7 }

hpnicfDot11RRMHistoryNoise OBJECT-TYPE
    SYNTAX Integer32
    MAX-ACCESS read-only
    STATUS current
    DESCRIPTION
        "Noise observed on the radio before/after the change
        of channel or power."
    ::= { hpnicfDot11RRMHistoryEntry 8 }

hpnicfDot11RRMHistoryPER OBJECT-TYPE
    SYNTAX Integer32 (0..100)
    UNITS "percent"
    MAX-ACCESS read-only
    STATUS current
    DESCRIPTION
        "Packet error rate observed on the radio in percentage
        before/after the change of channel or power."
    ::= { hpnicfDot11RRMHistoryEntry 9 }

hpnicfDot11RRMHistoryRetryRate OBJECT-TYPE
    SYNTAX Integer32 (0..100)
    UNITS "percent"
    MAX-ACCESS read-only
    STATUS current
    DESCRIPTION
        "Percentage of retransmission happened on the radio
        before/after the change of channel or power."
    ::= { hpnicfDot11RRMHistoryEntry 10 }

hpnicfDot11RRMHistoryChgReason OBJECT-TYPE
    SYNTAX BITS
        {
        others(0),
        coverage(1),
        radar(2),
        retransmission(3),
        packetsDiscarded(4),
        interference(5)
        }
    MAX-ACCESS read-only
    STATUS current
    DESCRIPTION
        "Reason for the change of channel or power.
        The various bit positions are:
        |0        |Others                    |
        |1        |Coverage                  |
        |2        |Radar                     |
        |3        |Retransmission            |
        |4        |Packets discarded         |
        |5        |Interference              |
        0 is returned when the history record type is after."
    ::= { hpnicfDot11RRMHistoryEntry 11 }

hpnicfDot11RRMHistoryChgDateTime OBJECT-TYPE
    SYNTAX DateAndTime
    MAX-ACCESS read-only
    STATUS current
    DESCRIPTION
        "The time when the channel or power change occurred."
    ::= { hpnicfDot11RRMHistoryEntry 12 }

hpnicfDot11RRMRadioNbrInfoTable OBJECT-TYPE
    SYNTAX SEQUENCE OF HpnicfDot11RRMRadioNbrInfoEntry
    MAX-ACCESS not-accessible
    STATUS current
    DESCRIPTION
        "This table shows the RRM neighbor information of each radio
        on all APs."
    ::= { hpnicfDot11RRMDetectGroup 4 }

hpnicfDot11RRMRadioNbrInfoEntry OBJECT-TYPE
    SYNTAX HpnicfDot11RRMRadioNbrInfoEntry
    MAX-ACCESS not-accessible
    STATUS current
    DESCRIPTION
        "Each entry contains information of RRM neighbor information
        of the radio on an AP."
    INDEX { hpnicfDot11RRMRadioNbrAPID, hpnicfDot11RRMRadioNbrRadioID }
    ::= { hpnicfDot11RRMRadioNbrInfoTable 1 }

HpnicfDot11RRMRadioNbrInfoEntry ::=
    SEQUENCE {
        hpnicfDot11RRMRadioNbrAPID
            HpnicfDot11ObjectIDType,
        hpnicfDot11RRMRadioNbrRadioID
            HpnicfDot11RadioScopeType,
        hpnicfDot11RRMRadioNbrSSID
            OCTET STRING
     }

hpnicfDot11RRMRadioNbrAPID OBJECT-TYPE
    SYNTAX HpnicfDot11ObjectIDType
    MAX-ACCESS not-accessible
    STATUS current
    DESCRIPTION
        "AP serial id."
    ::= { hpnicfDot11RRMRadioNbrInfoEntry 1 }

hpnicfDot11RRMRadioNbrRadioID OBJECT-TYPE
    SYNTAX HpnicfDot11RadioScopeType
    MAX-ACCESS not-accessible
    STATUS current
    DESCRIPTION
        "Radio Id on AP."
    ::= { hpnicfDot11RRMRadioNbrInfoEntry 2 }

hpnicfDot11RRMRadioNbrSSID OBJECT-TYPE
    SYNTAX  OCTET STRING
    MAX-ACCESS read-only
    STATUS current
    DESCRIPTION
        "All neighbour SSIDs scanned by the selected radio."
    ::= { hpnicfDot11RRMRadioNbrInfoEntry 3 }

hpnicfDot11RRMNotifyGroup OBJECT IDENTIFIER ::= { hpnicfDot11RRM 3 }

hpnicfDot11RRMChlQltyNotifications OBJECT IDENTIFIER ::= { hpnicfDot11RRMNotifyGroup 1 }

hpnicfDot11RRMChlQltyNtfPrefix OBJECT IDENTIFIER ::= { hpnicfDot11RRMChlQltyNotifications 0 }

hpnicfDot11RRMIntrfLimit NOTIFICATION-TYPE
    OBJECTS { hpnicfDot11RRMChlRptIntrf }
    STATUS current
    DESCRIPTION
        "This notification will be sent when interference on the radio
        exceeds the limit."
    ::= { hpnicfDot11RRMChlQltyNtfPrefix 1 }

hpnicfDot11RRMPERLimit NOTIFICATION-TYPE
    OBJECTS { hpnicfDot11RRMChlRptPER }
    STATUS current
    DESCRIPTION
        "This notification will be sent when packet error rate on the
        radio exceeds the limit."
    ::= { hpnicfDot11RRMChlQltyNtfPrefix 2 }

hpnicfDot11RRMNoiseLimit NOTIFICATION-TYPE
    OBJECTS { hpnicfDot11RRMChlRptNoise }
    STATUS current
    DESCRIPTION
        "This notification will be sent when noise on the radio exceeds
        the limit."
    ::= { hpnicfDot11RRMChlQltyNtfPrefix 3 }

hpnicfDot11RRMResChgNotifications OBJECT IDENTIFIER ::= { hpnicfDot11RRMNotifyGroup 2 }

hpnicfDot11RRMResChgNtfPrefix OBJECT IDENTIFIER ::= { hpnicfDot11RRMResChgNotifications 0 }

hpnicfDot11RRMPowerChange NOTIFICATION-TYPE
    OBJECTS { hpnicfDot11RRMRadioIndex, hpnicfDot11NewPower, hpnicfDot11OldPower }
    STATUS current
    DESCRIPTION
        "This notification will be sent when power changed on the radio
        automatically."
    ::= { hpnicfDot11RRMResChgNtfPrefix 1 }

hpnicfDot11RRMNotificationsVar OBJECT IDENTIFIER ::= { hpnicfDot11RRMNotifyGroup 3 }

hpnicfDot11NewPower OBJECT-TYPE
    SYNTAX Integer32
    MAX-ACCESS accessible-for-notify
    STATUS current
    DESCRIPTION
        "Power of the radio after the change of power."
    ::= { hpnicfDot11RRMNotificationsVar 1 }

hpnicfDot11OldPower OBJECT-TYPE
    SYNTAX Integer32
    MAX-ACCESS accessible-for-notify
    STATUS current
    DESCRIPTION
        "Power of the radio before the change of power."
    ::= { hpnicfDot11RRMNotificationsVar 2 }

hpnicfDot11MonitorDetectedGroup OBJECT IDENTIFIER ::= { hpnicfDot11RRM 4 }

hpnicfDot11MonitorDetectedDevTable OBJECT-TYPE
    SYNTAX SEQUENCE OF HpnicfDot11MonitorDetectedDevEntry
    MAX-ACCESS not-accessible
    STATUS current
    DESCRIPTION
        "This table shows the devices of AP detected"
    ::= { hpnicfDot11MonitorDetectedGroup 1 }

hpnicfDot11MonitorDetectedDevEntry OBJECT-TYPE
    SYNTAX      HpnicfDot11MonitorDetectedDevEntry
    MAX-ACCESS  not-accessible
    STATUS      current
    DESCRIPTION
        "Each entry contains information of detected devices."
    INDEX
        {
            hpnicfDot11MonitorDevMAC, hpnicfDot11APElementIndex
        }
    ::= { hpnicfDot11MonitorDetectedDevTable 1 }

HpnicfDot11MonitorDetectedDevEntry ::=
    SEQUENCE {
        hpnicfDot11MonitorDevMAC
            MacAddress,
        hpnicfDot11MonitorDevType
            INTEGER,
        hpnicfDot11MonitorDevVendor
            OCTET STRING,
        hpnicfDot11MonitorDevSSID
            OCTET STRING,
        hpnicfDot11MonitorDevBSSID
            MacAddress,
        hpnicfDot11MonitorDevChannel
            HpnicfDot11ChannelScopeType,
        hpnicfDot11MonitorRadioId
            HpnicfDot11RadioScopeType,
        hpnicfDot11MonitorDevMaxRSSI
            Integer32,
        hpnicfDot11MonitorDevBeaconIntvl
            Integer32,
        hpnicfDot11MonitorDevFstDctTime
            DateAndTime,
        hpnicfDot11MonitorDevLstDctTime
            DateAndTime,
        hpnicfDot11MonitorDevClear
            TruthValue,
        hpnicfDot11MonitorDevSNR
            Integer32
     }

hpnicfDot11MonitorDevMAC OBJECT-TYPE
    SYNTAX      MacAddress
    MAX-ACCESS  not-accessible
    STATUS      current
    DESCRIPTION
        "Represents MAC address of the device detected."
    ::= { hpnicfDot11MonitorDetectedDevEntry 1 }

hpnicfDot11MonitorDevType OBJECT-TYPE
    SYNTAX      INTEGER
                {
                    client(1),
                    ap(2),
                    adhoc(3),
                    wirelessBridge(4),
                    unknown(5)
                }
    MAX-ACCESS  read-only
    STATUS      current
    DESCRIPTION
        "Represents type of the device detected."
    ::= { hpnicfDot11MonitorDetectedDevEntry 2 }

hpnicfDot11MonitorDevVendor OBJECT-TYPE
    SYNTAX      OCTET STRING
    MAX-ACCESS  read-only
    STATUS      current
    DESCRIPTION
        "Represents vendor of the detected device."
    ::= { hpnicfDot11MonitorDetectedDevEntry 3 }

hpnicfDot11MonitorDevSSID OBJECT-TYPE
    SYNTAX      OCTET STRING
    MAX-ACCESS  read-only
    STATUS      current
    DESCRIPTION
        "Represents the service set identifier for the ESS of the device which
         type is ap or adhoc."
    ::= { hpnicfDot11MonitorDetectedDevEntry 4 }

hpnicfDot11MonitorDevBSSID OBJECT-TYPE
    SYNTAX      MacAddress
    MAX-ACCESS  read-only
    STATUS      current
    DESCRIPTION
        "Represents the basic service set identifier of the detected device."
    ::= { hpnicfDot11MonitorDetectedDevEntry 5 }

hpnicfDot11MonitorDevChannel OBJECT-TYPE
    SYNTAX      HpnicfDot11ChannelScopeType
    MAX-ACCESS  read-only
    STATUS      current
    DESCRIPTION
        "Represents the channel in which the device was last detected. AP will
         choose the channel which has maximum signal strength as effective
         channel, as there is interference between adjacent channels."
    ::= { hpnicfDot11MonitorDetectedDevEntry 6 }

hpnicfDot11MonitorRadioId OBJECT-TYPE
    SYNTAX      HpnicfDot11RadioScopeType
    MAX-ACCESS  read-only
    STATUS      current
    DESCRIPTION
        "Represents the radio ID of the AP that detected the device."
    ::= { hpnicfDot11MonitorDetectedDevEntry 7 }

hpnicfDot11MonitorDevMaxRSSI OBJECT-TYPE
    SYNTAX      Integer32
    UNITS       "dbm"
    MAX-ACCESS  read-only
    STATUS      current
    DESCRIPTION
        "Represents the maximum detected RSSI of the device in a scan report cycle."
    ::= { hpnicfDot11MonitorDetectedDevEntry 8 }

hpnicfDot11MonitorDevBeaconIntvl OBJECT-TYPE
    SYNTAX      Integer32
    UNITS       "millisecond"
    MAX-ACCESS  read-only
    STATUS      current
    DESCRIPTION
        "Represents the beacon interval for the detected device(not include
         the device which type is client)."
    ::= { hpnicfDot11MonitorDetectedDevEntry 9 }

hpnicfDot11MonitorDevFstDctTime OBJECT-TYPE
    SYNTAX      DateAndTime
    MAX-ACCESS  read-only
    STATUS      current
    DESCRIPTION
        "Represents the time at which the device was first detected."
    ::= { hpnicfDot11MonitorDetectedDevEntry 10 }

hpnicfDot11MonitorDevLstDctTime OBJECT-TYPE
    SYNTAX      DateAndTime
    MAX-ACCESS  read-only
    STATUS      current
    DESCRIPTION
        "Represents the time at which the device was detected last time."
    ::= { hpnicfDot11MonitorDetectedDevEntry 11 }

hpnicfDot11MonitorDevClear OBJECT-TYPE
    SYNTAX      TruthValue
    MAX-ACCESS  read-write
    STATUS      current
    DESCRIPTION
        "This object is used to clear the information of the device detected
         in the WLAN.
         It will return false for get operation."
    ::= { hpnicfDot11MonitorDetectedDevEntry 12 }

hpnicfDot11MonitorDevSNR OBJECT-TYPE
    SYNTAX      Integer32
    MAX-ACCESS  read-only
    STATUS      current
    DESCRIPTION
        "Represents the SNR of the device in a scan report cycle."
    ::= { hpnicfDot11MonitorDetectedDevEntry 13 }

END
