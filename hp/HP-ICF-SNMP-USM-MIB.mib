--**MOD+***********************************************************************
--* Module:    hpicfSnmpUsm.mib
--*
--* Copyright (C) 2020 Hewlett-Packard Development Company, L.P.
--* All Rights Reserved.
--*
--* Purpose: This file contains MIB definition of HP-ICF-SNMP-USM  MIB
--*
--**MOD-***********************************************************************

HP-ICF-SNMP-USM-MIB DEFINITIONS ::= BEGIN

    IMPORTS
        hpSwitch
            FROM HP-ICF-OID
        MODULE-IDENTITY
            FROM SNMPv2-SMI;

    hpicfSnmpUsm  MODULE-IDENTITY
        LAST-UPDATED  "202008280000Z"  -- August 28, 2020
        ORGANIZATION  "HP Networking"
        CONTACT-INFO  "Hewlett-Packard Company
                       8000 Foothills Blvd.
                       Roseville, CA 95747"

        DESCRIPTION   "This MIB extends the OID's for SNMP-USM-MIB
                       specified in RFC 3414.
                       The Privacy protocol specified here will be used
                       as values for usmUserPrivProtocol while configuring
                       SNMPv3 user via snmpUsmMIB.
                       This MIB defines OID for 256 bit key size AES.
                       The OID for 128 bit key size AES is already defined
                       as per RFC 3826."

        REVISION      "202008280000Z"  -- August 28, 2020
        DESCRIPTION   "Initial version of this MIB module."
        ::= { hpSwitch 143 }

hpicfSnmpPrivProtocols
        OBJECT IDENTIFIER ::= { hpicfSnmpUsm 1 }

usmAESCfb256PrivProtocol
        OBJECT IDENTIFIER ::= { hpicfSnmpPrivProtocols 1 }

END
