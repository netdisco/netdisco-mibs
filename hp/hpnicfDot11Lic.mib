-- =============================================================================
-- Copyright (c) 2010-2013 Hewlett-Packard Development Company, L.P.
--
-- Description:
--   The file defines a MIB to provide WLAN license feature.
-- Reference:
-- Version: V1.0
-- History:
--   V1.0 created by luoguixing
--     Initial version 2012-04-25
-- =============================================================================
HPN-ICF-DOT11-LIC-MIB DEFINITIONS ::= BEGIN

IMPORTS
        MODULE-IDENTITY,
        OBJECT-TYPE,
        Integer32
    FROM SNMPv2-SMI
        TruthValue
    FROM SNMPv2-TC
        hpnicfDot11
    FROM HPN-ICF-DOT11-REF-MIB;

hpnicfDot11LIC MODULE-IDENTITY
    LAST-UPDATED "201204251800Z"        -- Apr 25, 2012 at 18:00 GMT
    ORGANIZATION
        ""
    CONTACT-INFO
        ""
    DESCRIPTION
        "This MIB provides information for WLAN license configuration in AC.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "201204251800Z"        -- Apr 25, 2012 at 18:00 GMT
    DESCRIPTION
        "The initial revision of this MIB module."
    ::= { hpnicfDot11 14 }

-- *****************************************************************************
-- *  Major sections
-- *****************************************************************************

--  License Configuration Group
--  DEFINED AS "The group to provide the license configuration information for AC"

hpnicfDot11LICConfigGroup OBJECT IDENTIFIER     ::= { hpnicfDot11LIC 1 }

--  License ap number Group
--  DEFINED AS "The group to provide the ap number information for AC."
hpnicfDot11LICApNumGroup OBJECT IDENTIFIER  ::= { hpnicfDot11LIC 2 }
--  AP Number Group has the following children:
--  hpnicfDot11LICApNumAttrTable          ::= { hpnicfDot11LICApNumGroup 1 }
--  hpnicfDot11LICApNumLicTable            ::= { hpnicfDot11LICApNumGroup 2 }

--  License wlan feature Group
--  DEFINED AS "The group to provide the wlan feature information for AC."
hpnicfDot11LICFeatureGroup OBJECT IDENTIFIER    ::= { hpnicfDot11LIC 3 }
--  License wlan feature Group has the following children:
--  hpnicfDot11LICFeatureAttrTable          ::= { hpnicfDot11LICFeatureGroup 1 }
--  hpnicfDot11LICFeatureLicTable            ::= { hpnicfDot11LICFeatureGroup 2 }

-- *****************************************************************************
-- *  hpnicfDot11LICConfigGroup Definition
-- *****************************************************************************
hpnicfDot11LICSerialNumber OBJECT-TYPE
    SYNTAX    OCTET STRING (SIZE(0..255))
    MAX-ACCESS    read-only
    STATUS    current
    DESCRIPTION
        "The device serial number."
    ::= { hpnicfDot11LICConfigGroup 1 }

hpnicfDot11LicApNumGroupSupport OBJECT-TYPE
    SYNTAX      TruthValue
    MAX-ACCESS  read-only
    STATUS      current
    DESCRIPTION
        "Represents support hpnicfDot11LicApNumGroup
        'ture': device spport hpnicfDot11LicApNumGroup.
        'false': device not spport hpnicfDot11LicApNumGroupp."
    DEFVAL       { false }
    ::= { hpnicfDot11LICConfigGroup 2 }

-- *****************************************************************************
-- *  End of hpnicfDot11LICConfigGroup Definition
-- *****************************************************************************


-- *****************************************************************************
-- *  hpnicfDot11LICApNumTable Definition
-- *****************************************************************************

hpnicfDot11LICApNumAttrTable OBJECT IDENTIFIER     ::= { hpnicfDot11LICApNumGroup 1 }

hpnicfDot11LICDefautAPNumPermit OBJECT-TYPE
    SYNTAX      Integer32
    MAX-ACCESS  read-only
    STATUS      current
    DESCRIPTION
        "Represents the number of AP connection permitted
        for one AC without license."
    ::= { hpnicfDot11LICApNumAttrTable 1 }

hpnicfDot11LICCurrentAPNumPermit OBJECT-TYPE
    SYNTAX      Integer32
    MAX-ACCESS  read-only
    STATUS      current
    DESCRIPTION
        "Represents the total number of AP connection permitted
        for one AC, include default number and the licenses
        that installed."
    ::= { hpnicfDot11LICApNumAttrTable 2 }

hpnicfDot11LICMaxAPNumPermit OBJECT-TYPE
    SYNTAX      Integer32
    MAX-ACCESS  read-only
    STATUS      current
    DESCRIPTION
        "Represents the maximum number of AP to support connection permitted
        for one AC, include default number and full licenses."
    ::= { hpnicfDot11LICApNumAttrTable 3 }


hpnicfDot11LICApNumLicTable OBJECT-TYPE
    SYNTAX      SEQUENCE OF HpnicfDot11LICApNumLicEntry
    MAX-ACCESS  not-accessible
    STATUS      current
    DESCRIPTION
        "Each entry contains license information of ap number."
    ::= { hpnicfDot11LICApNumGroup 2 }

hpnicfDot11LICApNumLicEntry OBJECT-TYPE
    SYNTAX      HpnicfDot11LICApNumLicEntry
    MAX-ACCESS  not-accessible
    STATUS      current
    DESCRIPTION
        "Each entry contains association information of each station."
   INDEX
        { hpnicfDot11LICLicenseKeyIndex }
    ::= { hpnicfDot11LICApNumLicTable 1 }

HpnicfDot11LICApNumLicEntry ::= SEQUENCE
    {
        hpnicfDot11LICLicenseKeyIndex   Integer32,
        hpnicfDot11LICLicenseKey        OCTET STRING,
        hpnicfDot11LICActivationKey     OCTET STRING,
        hpnicfDot11LICApNum          Integer32
    }

hpnicfDot11LICLicenseKeyIndex OBJECT-TYPE
    SYNTAX      Integer32 (0..2147483647)
    MAX-ACCESS  read-only
    STATUS      current
    DESCRIPTION
        "Licensed key index value."
    ::= { hpnicfDot11LICApNumLicEntry 1 }

hpnicfDot11LICLicenseKey OBJECT-TYPE
    SYNTAX      OCTET STRING
    MAX-ACCESS  read-only
    STATUS      current
    DESCRIPTION
        "Specifies a certain license key."
    ::= { hpnicfDot11LICApNumLicEntry 2 }

hpnicfDot11LICActivationKey OBJECT-TYPE
    SYNTAX      OCTET STRING
    MAX-ACCESS  read-only
    STATUS      current
    DESCRIPTION
        "Specifies a certain activation key."
    ::= { hpnicfDot11LICApNumLicEntry 3 }

hpnicfDot11LICApNum OBJECT-TYPE
    SYNTAX      Integer32
    MAX-ACCESS  read-only
    STATUS      current
    DESCRIPTION
        "Represents support connect ap number of the license."
    ::= { hpnicfDot11LICApNumLicEntry 4 }

-- *****************************************************************************
-- *  End of hpnicfDot11LICApNumTable Definition
-- *****************************************************************************


-- *****************************************************************************
-- *  hpnicfDot11LICFeatureTable Definition
-- *****************************************************************************
hpnicfDot11LICFeatureAttrTable OBJECT-TYPE
    SYNTAX      SEQUENCE OF HpnicfDot11LICFeatureAttrEntry
    MAX-ACCESS  not-accessible
    STATUS      current
    DESCRIPTION
        "Each entry contains attribute information of wlan feature."
    ::= { hpnicfDot11LICFeatureGroup 1 }

hpnicfDot11LICFeatureAttrEntry OBJECT-TYPE
    SYNTAX      HpnicfDot11LICFeatureAttrEntry
    MAX-ACCESS  not-accessible
    STATUS      current
    DESCRIPTION
        "Each entry contains feature attribute information of licensetypename."
   INDEX
        {
            hpnicfDot11LICAttrIndex
        }
    ::= { hpnicfDot11LICFeatureAttrTable 1 }

HpnicfDot11LICFeatureAttrEntry ::= SEQUENCE
    {
        hpnicfDot11LICAttrIndex     Integer32,
        hpnicfDot11LICAttrTypeName  OCTET STRING,
        hpnicfDot11LICAttrDefVal    Integer32,
        hpnicfDot11LICAttrMaxVal    Integer32
    }

hpnicfDot11LICAttrIndex OBJECT-TYPE
    SYNTAX      Integer32 (0..2147483647)
    MAX-ACCESS  read-only
    STATUS      current
    DESCRIPTION
        "Attribute index value."
    ::= { hpnicfDot11LICFeatureAttrEntry 1 }

hpnicfDot11LICAttrTypeName OBJECT-TYPE
    SYNTAX      OCTET STRING
    MAX-ACCESS  read-only
    STATUS      current
    DESCRIPTION
        "Represents attribute type name"
    ::= { hpnicfDot11LICFeatureAttrEntry 2 }

hpnicfDot11LICAttrDefVal OBJECT-TYPE
    SYNTAX      Integer32
    MAX-ACCESS  read-only
    STATUS      current
    DESCRIPTION
        "Represents the default value of the license type."
    ::= { hpnicfDot11LICFeatureAttrEntry 3 }

hpnicfDot11LICAttrMaxVal OBJECT-TYPE
    SYNTAX      Integer32
    MAX-ACCESS  read-only
    STATUS      current
    DESCRIPTION
        "Represents the maximum value of the license type."
    ::= { hpnicfDot11LICFeatureAttrEntry 4 }

hpnicfDot11LICFeatureLicTable OBJECT-TYPE
    SYNTAX      SEQUENCE OF HpnicfDot11LICFeatureLicEntry
    MAX-ACCESS  not-accessible
    STATUS      current
    DESCRIPTION
        "Each entry contains license information of wlan feature."
    ::= { hpnicfDot11LICFeatureGroup 2 }

hpnicfDot11LICFeatureLicEntry OBJECT-TYPE
    SYNTAX      HpnicfDot11LICFeatureLicEntry
    MAX-ACCESS  not-accessible
    STATUS      current
    DESCRIPTION
        "Each entry contains wlan feature information of license."
   INDEX
        {
            hpnicfDot11LICKeyIndex
        }
    ::= { hpnicfDot11LICFeatureLicTable 1 }

HpnicfDot11LICFeatureLicEntry ::= SEQUENCE
    {
        hpnicfDot11LICKeyIndex   Integer32,
        hpnicfDot11LICTypeName   OCTET STRING,
        hpnicfDot11LICKey        OCTET STRING,
        hpnicfDot11LICTimeLimit  Integer32,
        hpnicfDot11LICValue      Integer32
    }

hpnicfDot11LICKeyIndex OBJECT-TYPE
    SYNTAX      Integer32 (0..2147483647)
    MAX-ACCESS  read-only
    STATUS      current
    DESCRIPTION
        "Licensed key index value."
    ::= { hpnicfDot11LICFeatureLicEntry 1 }

hpnicfDot11LICTypeName OBJECT-TYPE
    SYNTAX      OCTET STRING
    MAX-ACCESS  read-only
    STATUS      current
    DESCRIPTION
        "Represents the type name of the license entry."
    ::= { hpnicfDot11LICFeatureLicEntry 2 }

hpnicfDot11LICKey OBJECT-TYPE
    SYNTAX      OCTET STRING
    MAX-ACCESS  read-only
    STATUS      current
    DESCRIPTION
        "Specifies a certain license key."
    ::= { hpnicfDot11LICFeatureLicEntry 3 }

hpnicfDot11LICTimeLimit OBJECT-TYPE
    SYNTAX      Integer32
    MAX-ACCESS  read-only
    STATUS      current
    DESCRIPTION
        "Represents available time left of the license entry."
    ::= { hpnicfDot11LICFeatureLicEntry 4 }

hpnicfDot11LICValue OBJECT-TYPE
    SYNTAX      Integer32
    MAX-ACCESS  read-only
    STATUS      current
    DESCRIPTION
        "Represents the value of the license entry.
        If hpnicfDot11LICFeatureTypeName is 'AP',
        this meaning of ap number, and so no."
    ::= { hpnicfDot11LICFeatureLicEntry 5 }

-- *****************************************************************************
-- *  End of hpnicfDot11LICFeatureTable Definition
-- *****************************************************************************

END
