-- =============================================================================
-- Copyright (c) 2010-2014 Hewlett-Packard Development Company, L.P.
--
-- Description:
--   The file defines a MIB to provide wireless switch object and CAPWAP
--   tunnel information.
-- Reference:
-- Version: V2.4
-- History:
--   V1.0 created by shiyang (Richard)
--     Initial version 2006-05-10
--   V1.1 2007-04-27 modified by shiyang(Richard)
--        Add apCfgChange(6) for hpnicfDot11ACMtTrapTunlDwnInfo.
--        Delete hpnicfDot11ACPhysicalIndex,hpnicfDot11ACGlobalCountryCode,
--        hpnicfDot11ACCtrlTunnelSecSupport and hpnicfDot11ACDataTunnelSecSupport
--        nodes.
--   V1.2 2007-06-19 modified by Vikas K.
--        Add hpnicfDot11WLANAssocStatisInfo for hpnicfDot11ACObjectGroup.
--        Add hpnicfDot11MaxAPNumPermitted and hpnicfDot11MaxStationNumPermitted
--        nodes.
--   V1.3 2007-12-21 modified by wanghao (Kumar)
--        Add hpnicfDot11StationExDeAuthenSum and hpnicfDot11StationCurAssocSum
--        for hpnicfDot11WLANAssocStatisInfo.
--   V1.4 2008-07-09 modified by ChangHuifeng
--        Add hpnicfDot11ACMtBackupSwtTrap and hpnicfDot11ACMtTrapBackupSwitchInfo
--        for hpnicfDot11ACMtNotifyGroup.
--        Change description of hpnicfDot11ACMtTunnelSetupTrap.
--   V1.5 2008-12-03 modified by Wang Lu
--        Add new variable bindings hpnicfDot11ACMtTrapTnlAPName and
--        hpnicfDot11ACMtTrapTnlAPIPAddr to hpnicfDot11ACMtTunnelSetupTrap and
--        hpnicfDot11ACMtTunnelDownTrap.
--   V1.6 2009-05-07 modified by Wang Shaojie
--        Add new trap hpnicfDot11ACLoadBalanceTrap.
--        Add new variable bindings hpnicfDot11LoadBalanceType,
--        hpnicfDot11LoadBalanceThreshold for hpnicfDot11ACLoadBalanceTrap.
--        Add hpnicfDot11ACIFLoadInfoTable to hpnicfDot11ACIFLoadInfoTable.
--   V1.7 2009-07-29 modified by Heziqi
--        Add new variable bindings hpnicfDot11ACMtTrapAPIPv6Addr
--        to hpnicfDot11ACMtTunnelSetupTrap and hpnicfDot11ACMtTunnelDownTrap.
--        Add hpnicfDot11MasterAPCount, hpnicfDot11SlaveAPCount,
--        hpnicfDot11ConnectAutoAPCount and hpnicfDot11PersistentAPCount to
--        hpnicfDot11ACLoadInfo.
--   V1.8 2009-08-07 modified by Wang Shaojie, Qi Kai
--        Add new variable bindings hpnicfDot11ACMtTrapTunlDwnCount
--        to hpnicfDot11ACMtTrapVarObjects
--        Add hpnicfDot11ACIfStaNum, hpnicfDot11ACIfName to hpnicfDot11ACIFLoadInfoTable
--   V1.9 2009-12-01 modified by Wang Shaojie
--        Add hpnicfDot11ACStaFullTrap to hpnicfDot11ACMtTraps and variable bindings
--        hpnicfDot11ACMaxStaNum for hpnicfDot11ACStaFullTrap.
--        Add hpnicfDot11CtrlTunnelUpTimeTicks to hpnicfDot11CAPWAPTunnelTable
--        Add hpnicfDot11AcDownloadFrameCnt, hpnicfDot11AcUploadFrameCnt,
--        hpnicfDot11AcDownloadFrameBytes, hpnicfDot11AcUploadFrameBytes to
--        hpnicfDot11ACLoadInfo.
--        2010-06-10 added hpnicfDot11ACBASIfTable by jinyi
--        2010-08-04 modified by yin junjie
--        Add new table hpnicfDot11ACStaUserSecAuthStatis
--        Add hpnicfDot11ACStaUserAuthCurNumber, hpnicfDot11ACStaUserConnFailCnt,
--        hpnicfDot11ACStaUserAuthReqCnt, hpnicfDot11ACStaUserAuthSuccCnt,
--        hpnicfDot11ACStaUserAuthFailCnt to hpnicfDot11ACStaUserSecAuthStatis.
--   V2.0 2011-09-30 modified by Dong Laqi
--        Add hpnicfDot11ACMtTrapTnlAPSysName,hpnicfDot11ACMtFirstTrapTime
--        to hpnicfDot11ACMtTrapVarObjects
--        and variable bindings hpnicfDot11ACMtFirstTrapTime for
--        hpnicfDot11ACMtTunnelSetupTrap,hpnicfDot11ACMtTunnelDownTrap,
--        hpnicfDot11ACMtBackupSwtTrap.
--        2012-02-14 modified by Dong Laqi
--        Add hpnicfDot11BackupACRole,hpnicfDot11BackupACNMSIP,hpnicfDot11ACBackupMode,
--        hpnicfDot11ACBackupStatus and hpnicfDot11ACSwitchCnt to hpnicfDot11ACLoadInfo
--        Add hpnicfDot11ACStatusSwitchTrap to hpnicfDot11ACMtTraps
--        and binding hpnicfDot11ACMtTrapACStatusSwitchInfo and hpnicfDot11MasterACNmsIP
--        for hpnicfDot11ACMtTrapVarObjects
--   V2.1 2012-05-08 modified by Liu Xuping
--        Add new table hpnicfDot11ACStaSecAuthTypeStatis
--        Add hpnicfDot11ACStaUserPortalOnlineNum,hpnicfDot11ACStaUserFreeAuthOnlineNum,
--        hpnicfDot11ACStaUserAssociateAuthOnlineNum,hpnicfDot11ACStaUserMacAuthOnlineNum,
--        hpnicfDot11ACStaUserPortalLostConnectionCnt,
--        hpnicfDot11ACStaUserFreeAuthLostConnectionCnt,
--        hpnicfDot11ACStaUserAssociateAuthLostConnectionCnt,
--        hpnicfDot11ACStaUserMacAuthLostConnectionCnt,
--        hpnicfDot11ACStaPortalAuthReqCnt,hpnicfDot11ACStaAssociateAuthReqCnt,
--        hpnicfDot11ACStaMacAuthReqCnt,
--        hpnicfDot11ACStaPortalAuthSuccCnt,hpnicfDot11ACStaAssociateAuthSuccCnt,
--        hpnicfDot11ACStaMacAuthSuccCnt,
--        hpnicfDot11ACStaPortalAuthReqFailCnt,hpnicfDot11ACStaAssociateAuthReqFailCnt,
--        hpnicfDot11ACStaMacAuthReqFailCnt to hpnicfDot11ACStaSecAuthTypeStatis.
--        2012-05-16 modified by lihonghao
--        Add hpnicfDot11ACSouthifPacketOutputCount,hpnicfDot11ACSouthifPacketOutputBytes
--        hpnicfDot11ACSouthifPacketInputCount and hpnicfDot11ACSouthifPacketInputBytes
--        to hpnicfDot11ACLoadInfo
--        2012-08-17 modified Zhang Congcong & LiXin
--        Add new node   hpnicfDot11RunAPNumThreshold       to hpnicfDot11ACObject
--        Add new node   hpnicfDot11RunAPNumOverload        to hpnicfDot11ACMtTraps
--        Add new node   hpnicfDot11RunAPNumOverloadRecover to hpnicfDot11ACMtTraps
--        Add new object hpnicfDot11ACMtTrapAPMacAddress    to hpnicfDot11ACMtTunnelSetupTrap
--        Add new object hpnicfDot11ACMtTrapAPMacAddress    to hpnicfDot11ACMtTunnelDownTrap
--        Add new node   hpnicfDot11ACMtTrapAPMacAddress    to hpnicfDot11ACMtTrapVarObjects
--   V2.2 2013-07-08 modified by Chen Guoxi
--        Add new node   hpnicfDot11StationAssocReqSum      to hpnicfDot11WLANAssocStatisInfo
--        Add new node   hpnicfDot11StationReassocReqSum    to hpnicfDot11WLANAssocStatisInfo
--        Add new node   hpnicfDot11StationReassocFailSum   to hpnicfDot11WLANAssocStatisInfo
--   v2.3 2013-07-08 modified by Xiao Min
--        Add new node   hpnicfDot11TotalAPconnected        to hpnicfDot11ACLoadInfo
--        Add new node   hpnicfDot11RemainingAPcapacity     to hpnicfDot11ACLoadInfo
--   v2.4 2014-02-14 modified by Zhou Weichao
--        Add new node hpnicfDot11ACStaUserAutoAuthOnlineNumCM,
--        hpnicfDot11ACStaUserAutoAuthLostConnectionCntCM,
--        hpnicfDot11ACStaAutoAuthReqCntCM,
--        hpnicfDot11ACStaAutoAuthSuccCntCM,
--        hpnicfDot11ACStaAutoAuthReqFailCntCM to hpnicfDot11ACStaSecAuthTypeStatis
--        Modify node hpnicfDot11ACStaUserPortalOnlineNum,
--        hpnicfDot11ACStaUserAssociateAuthOnlineNum from hpnicfDot11ACStaSecAuthTypeStatis
--        Add hpnicfDot11ACStaUserAllAuthCntCM to hpnicfDot11ACStaUserSecAuthStatis
--        Add new table hpnicfDot11ACPortalStatisticCMTable
--        Add hpnicfDot11ACPortalStatisticCMEntry, hpnicfDot11PortalStatisticSSIDCM,
--        hpnicfACPortalStatAuthReqCM and
--        hpnicfACPortalStatAuthRespCM to hpnicfDot11ACPortalStatisticCMTable
-- =============================================================================
HPN-ICF-DOT11-ACMT-MIB DEFINITIONS ::= BEGIN

IMPORTS
        MODULE-IDENTITY,
        OBJECT-TYPE,
        NOTIFICATION-TYPE,
        Integer32,
        Counter32,
        IpAddress,
        Counter64,
        TimeTicks
    FROM SNMPv2-SMI
        IANAifType
    FROM IANAifType-MIB
        hpnicfDot11,
        HpnicfDot11MACModeType,
        HpnicfDot11TunnelSecSchemType,
        HpnicfDot11ObjectIDType
    FROM HPN-ICF-DOT11-REF-MIB
        MacAddress
    FROM SNMPv2-TC;

hpnicfDot11ACMT MODULE-IDENTITY
    LAST-UPDATED "201008041800Z"        -- Aug 04, 2009 at 18:00 GMT
    ORGANIZATION
        ""
    CONTACT-INFO
        ""
    DESCRIPTION
        "This MIB defines information as per wireless AC and tunnel between
        AP and AC.
        If NMS intends to get more detailed information for the AP and AC,
        it could refer entPhysicalIndex in the Entity MIB to get entity
        information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Radio
        The chip set to receive and send wireless signal.

        Fat AP
        Applied in the home, SOHO and so on, and it could
        independently work without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "201008041800Z"        -- Aug 04, 2010 at 18:00 GMT
    DESCRIPTION
        "Add new nodes."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new nodes."
    REVISION "200807091800Z"        -- July 09, 2008 at 18:00 GMT
    DESCRIPTION
        "Modified to add new nodes."
    REVISION "200712211800Z"        -- Dec 21, 2007 at 18:00 GMT
    DESCRIPTION
        "Modified to add new nodes."
    REVISION "200706191800Z"        -- June 19, 2007 at 18:00 GMT
    DESCRIPTION
        "Modified to add new table and new nodes."
    REVISION "200704272000Z"        -- Apr 27, 2007 at 20:00 GMT
    DESCRIPTION
        "Modified to fix some issue."
    REVISION "200605101900Z"        -- May 10, 2006 at 19:00 GMT
    DESCRIPTION
        "The initial revision of this MIB module."
    ::= { hpnicfDot11 1 }

-- *****************************************************************************
-- *  Major sections
-- *****************************************************************************

--  AC Object Group Attributes
--  DEFINED AS " The group provides AC information like MAC Mode and so on,
--  also could refer to software version and hardware version kept
--  by Entity MIB by Physical index"

hpnicfDot11ACObjectGroup OBJECT IDENTIFIER     ::= { hpnicfDot11ACMT 1 }
hpnicfDot11ACObject OBJECT IDENTIFIER          ::= { hpnicfDot11ACObjectGroup 1 }
hpnicfDot11ACLoadInfo OBJECT IDENTIFIER        ::= { hpnicfDot11ACObjectGroup 2 }
hpnicfDot11WLANAssocStatisInfo OBJECT IDENTIFIER  ::= { hpnicfDot11ACObjectGroup 3 }
hpnicfDot11ACBASInfo OBJECT IDENTIFIER  ::= { hpnicfDot11ACObjectGroup 4 }
hpnicfDot11ACStaUserSecAuthStatis OBJECT IDENTIFIER    ::= { hpnicfDot11ACObjectGroup 5 }
hpnicfDot11ACStaSecAuthTypeStatis OBJECT IDENTIFIER    ::= { hpnicfDot11ACObjectGroup 6 }

--  AC CAPWAP tunnel Group Attributes
--  DEFINED AS "The group provides CAPWAP tunnel information"

hpnicfDot11CAPWAPTunnelGroup OBJECT IDENTIFIER  ::= { hpnicfDot11ACMT 2 }

--  AC CAPWAP Notification
--  DEFINED AS "The notification for AC Management"

hpnicfDot11ACMtNotifyGroup OBJECT IDENTIFIER    ::= { hpnicfDot11ACMT 3 }

-- *****************************************************************************
-- *  hpnicfDot11ACObject element Definition
-- *****************************************************************************
hpnicfDot11CurrentACMACMode OBJECT-TYPE
    SYNTAX      HpnicfDot11MACModeType
    MAX-ACCESS  read-only
    STATUS      current
    DESCRIPTION
        "Represents which MAC mode defined in the CAPWAP draft is in use
        for the AC."
    DEFVAL      { split }
    ::= { hpnicfDot11ACObject 1 }

hpnicfDot11MaxAPNumPermitted OBJECT-TYPE
    SYNTAX      Integer32
    MAX-ACCESS  read-only
    STATUS      current
    DESCRIPTION
        "Represents the maximum number of AP connection permitted
        for one AC."
    ::= { hpnicfDot11ACObject 2 }

hpnicfDot11MaxStationNumPermitted OBJECT-TYPE
    SYNTAX      Integer32
    MAX-ACCESS  read-only
    STATUS      current
    DESCRIPTION
        "Represents the maximum number of station connection
        permitted for one AC."
    ::= { hpnicfDot11ACObject 3 }
hpnicfDot11RunAPNumThreshold OBJECT-TYPE
    SYNTAX      Integer32(30..100)
    UNITS       "percent"
    MAX-ACCESS  read-write
    STATUS      current
        DESCRIPTION
        "When the percentage of run AP number is larger than this
        threshold, a notification will be sent."
    DEFVAL      { 100 }
    ::= { hpnicfDot11ACObject 4 }
-- *****************************************************************************
-- *  End of hpnicfDot11ACObject element Definition
-- *****************************************************************************

-- *****************************************************************************
-- *  hpnicfDot11ACLoadInfo element Definition
-- *****************************************************************************
hpnicfDot11APConnectCount OBJECT-TYPE
    SYNTAX      Integer32
    MAX-ACCESS  read-only
    STATUS      current
    DESCRIPTION
        "Represents the total number of APs which are connecting to AC."
    ::= { hpnicfDot11ACLoadInfo 1 }

hpnicfDot11StationConnectCount OBJECT-TYPE
    SYNTAX      Integer32
    MAX-ACCESS  read-only
    STATUS      current
    DESCRIPTION
        "Represents the total number of stations which are accessing the
        WLAN service through AC."
    ::= { hpnicfDot11ACLoadInfo 2 }

-- *****************************************************************************
-- *  hpnicfDot11ACIFLoadInfoTable Definition
-- *****************************************************************************
hpnicfDot11ACIFLoadInfoTable OBJECT-TYPE
    SYNTAX      SEQUENCE OF HpnicfDot11ACIFLoadInfoEntry
    MAX-ACCESS  not-accessible
    STATUS      current
    DESCRIPTION
        "Represents AP number information of interface."
    ::= { hpnicfDot11ACLoadInfo 3 }

hpnicfDot11ACIFLoadInfoEntry OBJECT-TYPE
    SYNTAX      HpnicfDot11ACIFLoadInfoEntry
    MAX-ACCESS  not-accessible
    STATUS      current
    DESCRIPTION
        "Each entry represents AP number information of an interface"
    INDEX
        {
            hpnicfDot11ACIfIndex
        }
    ::= { hpnicfDot11ACIFLoadInfoTable 1 }

HpnicfDot11ACIFLoadInfoEntry ::= SEQUENCE
    {
        hpnicfDot11ACIfIndex       Integer32,
        hpnicfDot11ACIfApNum       Integer32,
        hpnicfDot11ACIfStaNum      Integer32,
        hpnicfDot11ACIfName        OCTET STRING
    }

hpnicfDot11ACIfIndex OBJECT-TYPE
    SYNTAX      Integer32
    MAX-ACCESS  accessible-for-notify
    STATUS      current
    DESCRIPTION
        "Represents index of AC interface."
    ::= { hpnicfDot11ACIFLoadInfoEntry 1 }

hpnicfDot11ACIfApNum OBJECT-TYPE
    SYNTAX      Integer32
    MAX-ACCESS  read-only
    STATUS      current
    DESCRIPTION
        "Represents AP number connected to the AC interface."
    ::= { hpnicfDot11ACIFLoadInfoEntry 2 }

hpnicfDot11ACIfStaNum OBJECT-TYPE
    SYNTAX      Integer32
    MAX-ACCESS  read-only
    STATUS      current
    DESCRIPTION
        "Represents Station number connected to the AC interface."
    ::= { hpnicfDot11ACIFLoadInfoEntry 3 }

hpnicfDot11ACIfName OBJECT-TYPE
    SYNTAX      OCTET STRING
    MAX-ACCESS  read-only
    STATUS      current
    DESCRIPTION
        "Represents InterfaceName AP number connected to AC interface."
    ::= { hpnicfDot11ACIFLoadInfoEntry 4 }

-- *****************************************************************************
-- *  End of hpnicfDot11ACIFLoadInfoTable element Definition
-- *****************************************************************************
hpnicfDot11MasterAPCount OBJECT-TYPE
    SYNTAX      Integer32
    MAX-ACCESS  read-only
    STATUS      current
    DESCRIPTION
        "Represents the total number of AP which have established the
        master tunnel with AC."
    ::= { hpnicfDot11ACLoadInfo 4 }

hpnicfDot11SlaveAPCount OBJECT-TYPE
    SYNTAX      Integer32
    MAX-ACCESS  read-only
    STATUS      current
    DESCRIPTION
        "Represents the total number of AP which have established the
        slave tunnel with AC."
    ::= { hpnicfDot11ACLoadInfo 5 }

hpnicfDot11ConnectAutoAPCount OBJECT-TYPE
    SYNTAX      Integer32
    MAX-ACCESS  read-only
    STATUS      current
    DESCRIPTION
        "Represents the total number of auto APs that are connecting to AC."
    ::= { hpnicfDot11ACLoadInfo 6 }

hpnicfDot11PersistentAPCount OBJECT-TYPE
    SYNTAX      Integer32
    MAX-ACCESS  read-only
    STATUS      current
    DESCRIPTION
        "Represents the total number of persistent AP."
    ::= { hpnicfDot11ACLoadInfo 7 }

hpnicfDot11AcUploadFrameCnt OBJECT-TYPE
    SYNTAX      Counter64
    MAX-ACCESS  read-only
    STATUS      current
    DESCRIPTION
        "Represents the number of frames that AP sends to AC through LWAPP tunnel."
    ::= { hpnicfDot11ACLoadInfo 8 }

hpnicfDot11AcDownloadFrameCnt OBJECT-TYPE
    SYNTAX      Counter64
    MAX-ACCESS  read-only
    STATUS      current
    DESCRIPTION
        "Represents the number of frames that AC sends to AP through LWAPP tunnel."
    ::= { hpnicfDot11ACLoadInfo 9 }

hpnicfDot11AcUploadFrameBytes OBJECT-TYPE
    SYNTAX      Counter64
    MAX-ACCESS  read-only
    STATUS      current
    DESCRIPTION
        "Represents the bytes of frames that AP sends to AC through LWAPP tunnel."
    ::= { hpnicfDot11ACLoadInfo 10 }

hpnicfDot11AcDownloadFrameBytes OBJECT-TYPE
    SYNTAX      Counter64
    MAX-ACCESS  read-only
    STATUS      current
    DESCRIPTION
        "Represents the bytes of frames that AC sends to AP through LWAPP tunnel."
    ::= { hpnicfDot11ACLoadInfo 11 }

hpnicfDot11BackupACRole OBJECT-TYPE
    SYNTAX      INTEGER
        {
            null(1),
            master(2),
            slave(3)
        }
    MAX-ACCESS  read-only
    STATUS      current
    DESCRIPTION
        "This object represents the Identity of the AC
         null:   Not configured
         master: Master AC
         slave:  Slave AC."
    DEFVAL      { null }
    ::= { hpnicfDot11ACLoadInfo 12 }

hpnicfDot11BackupACNMSIP OBJECT-TYPE
        SYNTAX      IpAddress
        MAX-ACCESS  read-only
        STATUS      current
        DESCRIPTION
            "This object represents the manger IP address of the slave ac."
    ::= { hpnicfDot11ACLoadInfo 13 }

hpnicfDot11ACBackupMode OBJECT-TYPE
        SYNTAX      INTEGER
        {
            null(1),
            hotBackup(2),
            coldBackup(3)
        }
        MAX-ACCESS  read-only
        STATUS      current
        DESCRIPTION
            "This object represents the ac backup mode."
        DEFVAL      { null }
    ::= { hpnicfDot11ACLoadInfo 14 }

hpnicfDot11ACBackupStatus OBJECT-TYPE
        SYNTAX      INTEGER
        {
            active(1),
            standby(2)
        }
        MAX-ACCESS  read-only
        STATUS      current
        DESCRIPTION
            "This object represents the ac backup status."
    ::= { hpnicfDot11ACLoadInfo 15 }

hpnicfDot11ACSwitchCnt OBJECT-TYPE
        SYNTAX      Integer32
        MAX-ACCESS  read-only
        STATUS      current
        DESCRIPTION
            "This object represents the ac switch times."
    ::= { hpnicfDot11ACLoadInfo 16 }

hpnicfDot11ACSouthifPacketOutputCount OBJECT-TYPE
        SYNTAX      Counter64
        MAX-ACCESS  read-only
        STATUS      current
        DESCRIPTION
            "Represents the count of output packets with the down-link interface."
    ::= { hpnicfDot11ACLoadInfo 17 }

hpnicfDot11ACSouthifPacketOutputBytes OBJECT-TYPE
        SYNTAX      Counter64
        MAX-ACCESS  read-only
        STATUS      current
        DESCRIPTION
            "Represents the bytes of output packets with the down-link interface."
    ::= { hpnicfDot11ACLoadInfo 18 }

hpnicfDot11ACSouthifPacketInputCount OBJECT-TYPE
        SYNTAX      Counter64
        MAX-ACCESS  read-only
        STATUS      current
        DESCRIPTION
            "Represents the count of input packets with the down-link interface."
    ::= { hpnicfDot11ACLoadInfo 19 }

hpnicfDot11ACSouthifPacketInputBytes OBJECT-TYPE
        SYNTAX      Counter64
        MAX-ACCESS  read-only
        STATUS      current
        DESCRIPTION
            "Represents the bytes of input packets with the down-link interface."
    ::= { hpnicfDot11ACLoadInfo 20 }

hpnicfDot11TotalAPconnected OBJECT-TYPE
    SYNTAX      Integer32
    MAX-ACCESS  read-only
    STATUS      current
    DESCRIPTION
        "Represents the total number of AP which are connected to AC."
    ::= { hpnicfDot11ACLoadInfo 21 }

hpnicfDot11RemainingAPcapacity OBJECT-TYPE
    SYNTAX      Integer32
    MAX-ACCESS  read-only
    STATUS      current
    DESCRIPTION
        "Represents the remaining AP capacity of the AC."
    ::= { hpnicfDot11ACLoadInfo 22 }

-- *****************************************************************************
-- *  End of hpnicfDot11ACLoad element Definition
-- *****************************************************************************

-- *****************************************************************************
-- *  hpnicfDot11WLANAssocStatisInfo Definition
-- *****************************************************************************
hpnicfDot11StationAssocSum OBJECT-TYPE
    SYNTAX      Counter32
    MAX-ACCESS  read-only
    STATUS      current
    DESCRIPTION
        "Represents the total number of station association."
    ::= { hpnicfDot11WLANAssocStatisInfo 1 }

hpnicfDot11StationAssocFailSum OBJECT-TYPE
    SYNTAX      Counter32
    MAX-ACCESS  read-only
    STATUS      current
    DESCRIPTION
        "Represents the total number of station association failure."
    ::= { hpnicfDot11WLANAssocStatisInfo 2 }

hpnicfDot11StationReassocSum OBJECT-TYPE
    SYNTAX      Counter32
    MAX-ACCESS  read-only
    STATUS      current
    DESCRIPTION
        "Represents the total number of station reassociation."
    ::= { hpnicfDot11WLANAssocStatisInfo 3 }

hpnicfDot11StationAssocRejectedSum OBJECT-TYPE
    SYNTAX      Counter32
    MAX-ACCESS  read-only
    STATUS      current
    DESCRIPTION
        "Represents the total number of station association rejected on
        account of resource limit."
    ::= { hpnicfDot11WLANAssocStatisInfo 4 }

hpnicfDot11StationExDeAuthenSum OBJECT-TYPE
    SYNTAX      Counter32
    MAX-ACCESS  read-only
    STATUS      current
    DESCRIPTION
        "Represents the total number of exceptional station deauthentication
        (Without sending a deauthentication to AP)."
    ::= { hpnicfDot11WLANAssocStatisInfo 5 }

hpnicfDot11StationCurAssocSum OBJECT-TYPE
    SYNTAX      Integer32
    MAX-ACCESS  read-only
    STATUS      current
    DESCRIPTION
        "Represents the total number of current associated stations."
    ::= { hpnicfDot11WLANAssocStatisInfo 6 }

hpnicfDot11StationAssocReqSum OBJECT-TYPE
    SYNTAX      Counter32
    MAX-ACCESS  read-only
    STATUS      current
    DESCRIPTION
        "Represents the total number of station association request."
    ::= { hpnicfDot11WLANAssocStatisInfo 7 }

hpnicfDot11StationReassocReqSum OBJECT-TYPE
    SYNTAX      Counter32
    MAX-ACCESS  read-only
    STATUS      current
    DESCRIPTION
        "Represents the total number of station reassociation request."
    ::= { hpnicfDot11WLANAssocStatisInfo 8 }

hpnicfDot11StationReassocFailSum OBJECT-TYPE
    SYNTAX      Counter32
    MAX-ACCESS  read-only
    STATUS      current
    DESCRIPTION
        "Represents the total number of station reassociation failure."
    ::= { hpnicfDot11WLANAssocStatisInfo 9 }
-- *****************************************************************************
-- *  End of hpnicfDot11WLANAssocStatisInfo Definition
-- *****************************************************************************

-- *****************************************************************************
-- * hpnicfDot11ACBASInfo Definition
-- *****************************************************************************
hpnicfDot11ACBASSysObjects OBJECT IDENTIFIER  ::= { hpnicfDot11ACBASInfo 1 }
hpnicfDot11ACBASTableObjects OBJECT IDENTIFIER  ::= { hpnicfDot11ACBASInfo 2 }

hpnicfDot11ACBASIfTable OBJECT-TYPE
    SYNTAX      SEQUENCE OF HpnicfDot11ACBASIfEntry
    MAX-ACCESS  not-accessible
    STATUS      current
    DESCRIPTION
        "Represents the BAS information of interfaces."
    ::= { hpnicfDot11ACBASTableObjects 3 }

hpnicfDot11ACBASIfEntry OBJECT-TYPE
    SYNTAX      HpnicfDot11ACBASIfEntry
    MAX-ACCESS  not-accessible
    STATUS      current
    DESCRIPTION
        "Each entry represents the BAS information of an interface"
    INDEX
        {
            hpnicfDot11ACBASIfIndex
        }
    ::= { hpnicfDot11ACBASIfTable 1 }

HpnicfDot11ACBASIfEntry ::= SEQUENCE
    {
        hpnicfDot11ACBASIfIndex       Integer32,
        hpnicfDot11ACBASIfDescr       OCTET STRING,
        hpnicfDot11ACBASIfType        IANAifType
    }

hpnicfDot11ACBASIfIndex OBJECT-TYPE
    SYNTAX      Integer32
    MAX-ACCESS  not-accessible
    STATUS      current
    DESCRIPTION
            "The ifIndex of the BAS interface. "
    ::= { hpnicfDot11ACBASIfEntry 1 }

hpnicfDot11ACBASIfDescr OBJECT-TYPE
    SYNTAX      OCTET STRING (SIZE (0..255))
    MAX-ACCESS  read-only
    STATUS      current
    DESCRIPTION
            "A textual string containing information about the BAS interface. "
    ::= { hpnicfDot11ACBASIfEntry 2 }

hpnicfDot11ACBASIfType OBJECT-TYPE
    SYNTAX      IANAifType
    MAX-ACCESS  read-only
    STATUS      current
    DESCRIPTION
            "The type of the BAS interface. "
    ::= { hpnicfDot11ACBASIfEntry 3 }

-- *****************************************************************************
-- *  End of hpnicfDot11ACBASInfo Definition
-- *****************************************************************************

-- *****************************************************************************
-- *  hpnicfDot11ACStaUserSecAuthStatis element Definition
-- *****************************************************************************
hpnicfDot11ACStaUserAuthCurNumber OBJECT-TYPE
    SYNTAX      Integer32
    MAX-ACCESS  read-only
    STATUS      current
    DESCRIPTION
        "Represents the current number of user authenticated with this AC."
    ::= { hpnicfDot11ACStaUserSecAuthStatis 1 }

hpnicfDot11ACStaUserConnFailCnt OBJECT-TYPE
    SYNTAX      Counter32
    MAX-ACCESS  read-only
    STATUS      current
    DESCRIPTION
        "Represents the total number of user disconnected with this AC."
    ::= { hpnicfDot11ACStaUserSecAuthStatis 2 }

hpnicfDot11ACStaUserAuthReqCnt OBJECT-TYPE
    SYNTAX      Counter32
    MAX-ACCESS  read-only
    STATUS      current
    DESCRIPTION
        "Represents the total number of user authenticate request with this AC."
    ::= { hpnicfDot11ACStaUserSecAuthStatis 3 }

hpnicfDot11ACStaUserAuthSuccCnt OBJECT-TYPE
    SYNTAX      Counter32
    MAX-ACCESS  read-only
    STATUS      current
    DESCRIPTION
        "Represents the total number of users authenticated successful with this AC."
    ::= { hpnicfDot11ACStaUserSecAuthStatis 4 }

hpnicfDot11ACStaUserAuthFailCnt OBJECT-TYPE
    SYNTAX      Counter32
    MAX-ACCESS  read-only
    STATUS      current
    DESCRIPTION
        "Represents the total number of user authenticated failed with this AC."
    ::= { hpnicfDot11ACStaUserSecAuthStatis 5 }

hpnicfDot11ACStaUserAllAuthCntCM OBJECT-TYPE
    SYNTAX      Counter32
    MAX-ACCESS  read-only
    STATUS      current
    DESCRIPTION
        "Represents the total number of users authenticated with this AC."
    ::= { hpnicfDot11ACStaUserSecAuthStatis 6 }

-- *****************************************************************************
-- *  End of hpnicfDot11StaUserSecAuthStatis element Definition
-- *****************************************************************************

-- *****************************************************************************
-- *  hpnicfDot11ACStaSecAuthTypeStatis element Definition
-- *****************************************************************************
hpnicfDot11ACStaUserPortalOnlineNum OBJECT-TYPE
    SYNTAX      Integer32
    MAX-ACCESS  read-only
    STATUS      current
    DESCRIPTION
        "Represents the number of online portal users authenticated by RADIUS,
        including MAC-trigger and IMSIAuth users."
    ::= { hpnicfDot11ACStaSecAuthTypeStatis 1 }

hpnicfDot11ACStaUserFreeAuthOnlineNum OBJECT-TYPE
    SYNTAX      Integer32
    MAX-ACCESS  read-only
    STATUS      current
    DESCRIPTION
        "Numbers of online user is no need authenticated."
    ::= { hpnicfDot11ACStaSecAuthTypeStatis 2 }

hpnicfDot11ACStaUserAssociateAuthOnlineNum OBJECT-TYPE
    SYNTAX      Integer32
    MAX-ACCESS  read-only
    STATUS      current
    DESCRIPTION
        "Represents the number of online users authenticated by associated authentication,
        excluding AutoAuth users."
    ::= { hpnicfDot11ACStaSecAuthTypeStatis 3 }

hpnicfDot11ACStaUserMacAuthOnlineNum OBJECT-TYPE
    SYNTAX      Integer32
    MAX-ACCESS  read-only
    STATUS      current
    DESCRIPTION
        "The numbers of online user which is launched authentication by MAC address and
        authenticated by Radius."
    ::= { hpnicfDot11ACStaSecAuthTypeStatis 4 }

hpnicfDot11ACStaUserPortalLostConnectionCnt OBJECT-TYPE
    SYNTAX      Counter32
    MAX-ACCESS  read-only
    STATUS      current
    DESCRIPTION
        "For PortalAuth user, represents disconnection count but voluntarily disconnect,
        it should not delete authenticated user when client roamed."
    ::= { hpnicfDot11ACStaSecAuthTypeStatis 5 }

hpnicfDot11ACStaUserFreeAuthLostConnectionCnt OBJECT-TYPE
    SYNTAX      Counter32
    MAX-ACCESS  read-only
    STATUS      current
    DESCRIPTION
        "For FreeAuth user, represents disconnection count but voluntarily disconnect,
        it should not delete authenticated user when client roamed."
    ::= { hpnicfDot11ACStaSecAuthTypeStatis 6 }

hpnicfDot11ACStaUserAssociateAuthLostConnectionCnt OBJECT-TYPE
    SYNTAX      Counter32
    MAX-ACCESS  read-only
    STATUS      current
    DESCRIPTION
        "For AssociateAuth user, represents disconnection count but voluntarily disconnect,
        it should not delete authenticated user when client roamed."
    ::= { hpnicfDot11ACStaSecAuthTypeStatis 7 }

hpnicfDot11ACStaUserMacAuthLostConnectionCnt OBJECT-TYPE
    SYNTAX      Counter32
    MAX-ACCESS  read-only
    STATUS      current
    DESCRIPTION
        "For MacAuth user, represents disconnection count but voluntarily disconnect,
        it should not delete authenticated user when client roamed."
    ::= { hpnicfDot11ACStaSecAuthTypeStatis 8 }

hpnicfDot11ACStaPortalAuthReqCnt OBJECT-TYPE
    SYNTAX      Counter32
    MAX-ACCESS  read-only
    STATUS      current
    DESCRIPTION
        "Represents PortalAuth request count after AP up."
    ::= { hpnicfDot11ACStaSecAuthTypeStatis 9 }

hpnicfDot11ACStaAssociateAuthReqCnt OBJECT-TYPE
    SYNTAX      Counter32
    MAX-ACCESS  read-only
    STATUS      current
    DESCRIPTION
        "Represents AssociateAuth request count after AP up."
    ::= { hpnicfDot11ACStaSecAuthTypeStatis 10 }

hpnicfDot11ACStaMacAuthReqCnt OBJECT-TYPE
    SYNTAX      Counter32
    MAX-ACCESS  read-only
    STATUS      current
    DESCRIPTION
        "Represents MacAuth request count after AP up."
    ::= { hpnicfDot11ACStaSecAuthTypeStatis 11 }

hpnicfDot11ACStaPortalAuthSuccCnt OBJECT-TYPE
    SYNTAX      Counter32
    MAX-ACCESS  read-only
    STATUS      current
    DESCRIPTION
        "Represents count of PortalAuth authenticated successfully after AP up."
    ::= { hpnicfDot11ACStaSecAuthTypeStatis 12 }

hpnicfDot11ACStaAssociateAuthSuccCnt OBJECT-TYPE
    SYNTAX      Counter32
    MAX-ACCESS  read-only
    STATUS      current
    DESCRIPTION
        "Represents count of AssociateAuth authenticated successfully after AP up."
    ::= { hpnicfDot11ACStaSecAuthTypeStatis 13 }

hpnicfDot11ACStaMacAuthSuccCnt OBJECT-TYPE
    SYNTAX      Counter32
    MAX-ACCESS  read-only
    STATUS      current
    DESCRIPTION
        "Represents count of MacAuth authenticated successfully after AP up."
    ::= { hpnicfDot11ACStaSecAuthTypeStatis 14 }

hpnicfDot11ACStaPortalAuthReqFailCnt OBJECT-TYPE
    SYNTAX      Counter32
    MAX-ACCESS  read-only
    STATUS      current
    DESCRIPTION
        "Represents count of PortalAuth failure in request after AP up."
    ::= { hpnicfDot11ACStaSecAuthTypeStatis 15 }

hpnicfDot11ACStaAssociateAuthReqFailCnt OBJECT-TYPE
    SYNTAX      Counter32
    MAX-ACCESS  read-only
    STATUS      current
    DESCRIPTION
        "Represents count of AssociateAuth failure in request after AP up."
    ::= { hpnicfDot11ACStaSecAuthTypeStatis 16 }

hpnicfDot11ACStaMacAuthReqFailCnt OBJECT-TYPE
    SYNTAX      Counter32
    MAX-ACCESS  read-only
    STATUS      current
    DESCRIPTION
        "Represents count of MacAuth failure in request after AP up."
    ::= { hpnicfDot11ACStaSecAuthTypeStatis 17 }

hpnicfDot11ACStaUserAutoAuthOnlineNumCM OBJECT-TYPE
    SYNTAX      Integer32
    MAX-ACCESS  read-only
    STATUS      current
    DESCRIPTION
        "Represents the number of online users authenticated by auto authentication."
    ::= { hpnicfDot11ACStaSecAuthTypeStatis 18 }

hpnicfDot11ACStaUserAutoAuthLostConnectionCntCM OBJECT-TYPE
    SYNTAX      Counter32
    MAX-ACCESS  read-only
    STATUS      current
    DESCRIPTION
        "Represents the disconnection count of AutoAuth users, excluding the ones
        who disconnect AP by themselves."
    ::= { hpnicfDot11ACStaSecAuthTypeStatis 19 }

hpnicfDot11ACStaAutoAuthReqCntCM OBJECT-TYPE
    SYNTAX      Counter32
    MAX-ACCESS  read-only
    STATUS      current
    DESCRIPTION
        "Represents the count of AutoAuth requests after AP up."
    ::= { hpnicfDot11ACStaSecAuthTypeStatis 20 }

hpnicfDot11ACStaAutoAuthSuccCntCM OBJECT-TYPE
    SYNTAX      Counter32
    MAX-ACCESS  read-only
    STATUS      current
    DESCRIPTION
        "Represents the count of successful AutoAuth authentications after AP up."
    ::= { hpnicfDot11ACStaSecAuthTypeStatis 21 }

hpnicfDot11ACStaAutoAuthReqFailCntCM OBJECT-TYPE
    SYNTAX      Counter32
    MAX-ACCESS  read-only
    STATUS      current
    DESCRIPTION
        "Represents the count of failed AutoAuth requests after AP is up."
    ::= { hpnicfDot11ACStaSecAuthTypeStatis 22 }
-- *****************************************************************************
-- *  End of hpnicfDot11ACStaSecAuthTypeStatis element Definition
-- *****************************************************************************

-- *****************************************************************************
-- *  hpnicfDot11ACPortalStatisticCMTable Definition
-- *****************************************************************************
hpnicfDot11ACPortalStatisticCMTable OBJECT-TYPE
    SYNTAX      SEQUENCE OF HpnicfDot11ACPortalStatisticCMEntry
    MAX-ACCESS  not-accessible
    STATUS      current
    DESCRIPTION
        "The table describes portal statistics information."
    ::= { hpnicfDot11ACObjectGroup 7 }

hpnicfDot11ACPortalStatisticCMEntry OBJECT-TYPE
    SYNTAX      HpnicfDot11ACPortalStatisticCMEntry
    MAX-ACCESS  not-accessible
    STATUS      current
    DESCRIPTION
        "Each entry contains the portal statistics information of an SSID."
    INDEX
        {
            hpnicfDot11ACPortalStatisticSSIDCM
        }
    ::= { hpnicfDot11ACPortalStatisticCMTable 1 }

HpnicfDot11ACPortalStatisticCMEntry ::= SEQUENCE
    {
        hpnicfDot11ACPortalStatisticSSIDCM             OCTET STRING,
        hpnicfDot11ACPortalStatAuthReqCM                  Counter32,
        hpnicfDot11ACPortalStatAuthRespCM                 Counter32
    }

hpnicfDot11ACPortalStatisticSSIDCM OBJECT-TYPE
    SYNTAX      OCTET STRING (SIZE (1..32))
    MAX-ACCESS  not-accessible
    STATUS      current
    DESCRIPTION
        "Represents the service policy name."
    ::= { hpnicfDot11ACPortalStatisticCMEntry 1 }

hpnicfDot11ACPortalStatAuthReqCM OBJECT-TYPE
    SYNTAX      Counter32
    MAX-ACCESS  read-only
    STATUS      current
    DESCRIPTION
        "Represents the total number of portal authentication requests from
        portal server to AC."
    ::= { hpnicfDot11ACPortalStatisticCMEntry 2 }

hpnicfDot11ACPortalStatAuthRespCM OBJECT-TYPE
    SYNTAX      Counter32
    MAX-ACCESS  read-only
    STATUS      current
    DESCRIPTION
        "Represents the total number of portal authentication responses from
        AC to portal server."
    ::= { hpnicfDot11ACPortalStatisticCMEntry 3 }

-- *****************************************************************************
-- *  End of hpnicfDot11ACPortalStatisticCMTable Definition
-- *****************************************************************************

-- *****************************************************************************
-- *  hpnicfDot11CAPWAPTunnelTable Definition
-- *****************************************************************************
hpnicfDot11CAPWAPTunnelTable OBJECT-TYPE
    SYNTAX      SEQUENCE OF HpnicfDot11CAPWAPTunnelEntry
    MAX-ACCESS  not-accessible
    STATUS      current
    DESCRIPTION
        "The table will list all the APs which are connecting to the AC
        by the CAPWAP tunnel protocol."
    ::= { hpnicfDot11CAPWAPTunnelGroup 1 }

hpnicfDot11CAPWAPTunnelEntry OBJECT-TYPE
    SYNTAX      HpnicfDot11CAPWAPTunnelEntry
    MAX-ACCESS  not-accessible
    STATUS      current
    DESCRIPTION
        "Each entry contains information of data tunnel and control
        tunnel of AP which is connecting to AC."
    INDEX
        {
            hpnicfDot11CurrTunnelAPID
        }
    ::= { hpnicfDot11CAPWAPTunnelTable 1 }

HpnicfDot11CAPWAPTunnelEntry ::= SEQUENCE
    {
        hpnicfDot11CurrTunnelAPID         HpnicfDot11ObjectIDType,
        hpnicfDot11CtrlTunnelCurrSec      HpnicfDot11TunnelSecSchemType,
        hpnicfDot11CtrlTunnelUpTime       Integer32,
        hpnicfDot11DataTunnelCurrSec      HpnicfDot11TunnelSecSchemType,
        hpnicfDot11DataTunnelUpTime       Integer32,
        hpnicfDot11CtrlTunnelUpTimeTicks  TimeTicks
    }

hpnicfDot11CurrTunnelAPID OBJECT-TYPE
    SYNTAX      HpnicfDot11ObjectIDType
    MAX-ACCESS  accessible-for-notify
    STATUS      current
    DESCRIPTION
        "To uniquely identify the CAPWAP tunnel set up between the AP
        identified by APID and a specific AC."
    ::= { hpnicfDot11CAPWAPTunnelEntry 1 }

hpnicfDot11CtrlTunnelCurrSec OBJECT-TYPE
    SYNTAX      HpnicfDot11TunnelSecSchemType
    MAX-ACCESS  read-only
    STATUS      current
    DESCRIPTION
        "Represents what security scheme is in use for
        control tunnel."
    DEFVAL      { cleartxt }
    ::= { hpnicfDot11CAPWAPTunnelEntry 2 }

hpnicfDot11CtrlTunnelUpTime OBJECT-TYPE
    SYNTAX      Integer32
    UNITS       "second"
    MAX-ACCESS  read-only
    STATUS      current
    DESCRIPTION
        "Represents how long for control tunnel up. If the value is zero,
        then tunnel is not set up."
    ::= { hpnicfDot11CAPWAPTunnelEntry 3 }

hpnicfDot11DataTunnelCurrSec OBJECT-TYPE
    SYNTAX      HpnicfDot11TunnelSecSchemType
    MAX-ACCESS  read-only
    STATUS      current
    DESCRIPTION
        "Represents what security scheme is in use for
        data tunnel."
    DEFVAL      { cleartxt }
    ::= { hpnicfDot11CAPWAPTunnelEntry 4 }

hpnicfDot11DataTunnelUpTime OBJECT-TYPE
    SYNTAX      Integer32
    UNITS       "second"
    MAX-ACCESS  read-only
    STATUS      current
    DESCRIPTION
        "Represents how long for data tunnel up.
        If the value is zero, then tunnel is not set up."
    ::= { hpnicfDot11CAPWAPTunnelEntry 5 }

hpnicfDot11CtrlTunnelUpTimeTicks OBJECT-TYPE
    SYNTAX      TimeTicks
    MAX-ACCESS  read-only
    STATUS      current
    DESCRIPTION
        "Represents how long control tunnel is up.
         If the value is zero, then tunnel is not set up."
    ::= { hpnicfDot11CAPWAPTunnelEntry 6 }
-- *****************************************************************************
-- *    End of hpnicfDot11CAPWAPTunnelTable  TABLE
-- *****************************************************************************

-- *****************************************************************************
-- *     Notifications OF hpnicfDot11ACMtNotifyGroup
-- *****************************************************************************
-- AC Management Notification

        hpnicfDot11ACMtTraps OBJECT IDENTIFIER
    ::= { hpnicfDot11ACMtNotifyGroup 0 }

hpnicfDot11ACMtTunnelSetupTrap NOTIFICATION-TYPE
    OBJECTS
        {
            hpnicfDot11CurrTunnelAPID,
            hpnicfDot11ACMtTrapTunlUpInfo,
            hpnicfDot11ACMtTrapTnlAPName,
            hpnicfDot11ACMtTrapTnlAPIPAddr,
            hpnicfDot11ACMtTrapAPIPv6Addr,
            hpnicfDot11ACMtFirstTrapTime,
            hpnicfDot11ACMtTrapAPMacAddress
        }
    STATUS      current
    DESCRIPTION
        "This notification is sent by AC when CAPWAP tunnel becomes up.
        By this way, NMS will immediately know tunnel up event.
        It is unnecessary to identify whether it is control or data
        tunnel."
    ::= { hpnicfDot11ACMtTraps 1 }

hpnicfDot11ACMtTunnelDownTrap NOTIFICATION-TYPE
    OBJECTS
        {
            hpnicfDot11CurrTunnelAPID,
            hpnicfDot11ACMtTrapTunlDwnInfo,
            hpnicfDot11ACMtTrapTnlAPName,
            hpnicfDot11ACMtTrapTnlAPIPAddr,
            hpnicfDot11ACMtTrapAPIPv6Addr,
            hpnicfDot11ACMtTrapTunlDwnCount,
            hpnicfDot11ACMtTrapTnlAPSysName,
            hpnicfDot11ACMtFirstTrapTime,
            hpnicfDot11ACMtTrapAPMacAddress
        }
    STATUS      current
    DESCRIPTION
        "This notification is sent by AC when CAPWAP tunnel becomes down.
        By this way, NMS will immediately know tunnel down event.
        It is unnecessary to identify whether it is control or data
        tunnel."
    ::= { hpnicfDot11ACMtTraps 2 }

hpnicfDot11ACMtBackupSwtTrap NOTIFICATION-TYPE
    OBJECTS
        {
            hpnicfDot11ACMtTrapBackupSwitchInfo,
            hpnicfDot11ACMtFirstTrapTime
        }
    STATUS      current
    DESCRIPTION
        "This trap is sent by AC when AC switches from master to slave
        or from slave to master."
    ::= { hpnicfDot11ACMtTraps 3 }

hpnicfDot11ACLoadBalanceTrap NOTIFICATION-TYPE
    OBJECTS
        {
            hpnicfDot11LoadBalanceType,
            hpnicfDot11LoadBalanceThreshold
        }
    STATUS      current
    DESCRIPTION
        "This trap is sent by AC when load-balance is enabled on AC."
    ::= { hpnicfDot11ACMtTraps 4 }

hpnicfDot11ACStaFullTrap NOTIFICATION-TYPE
    OBJECTS
        {
            hpnicfDot11ACMaxStaNum
        }
    STATUS current
    DESCRIPTION
        "This notification will be sent when STA is full on AC."
    ::={ hpnicfDot11ACMtTraps 5 }

hpnicfDot11ACStatusSwitchTrap NOTIFICATION-TYPE
    OBJECTS
        {
            hpnicfDot11ACStatusSwitchInfo,
            hpnicfDot11SourceACNmsIP
        }
    STATUS current
    DESCRIPTION
        "This notification will be sent when AC switches from standby to active
        or from standby to active."
    ::={ hpnicfDot11ACMtTraps 6}

hpnicfDot11RunAPNumOverload NOTIFICATION-TYPE
    OBJECTS
        {
            hpnicfDot11MaxAPNumPermitted,
            hpnicfDot11APConnectCount
        }
    STATUS current
    DESCRIPTION
        "The notification will be sent by AC when run AP number exceeds the threshold."
    ::= { hpnicfDot11ACMtTraps 7}

hpnicfDot11RunAPNumOverloadRecover NOTIFICATION-TYPE
    OBJECTS
        {
            hpnicfDot11MaxAPNumPermitted,
            hpnicfDot11APConnectCount
        }
    STATUS current
    DESCRIPTION
        "The notification will be sent by AC when run AP number
        recover normal from overload state."
    ::= { hpnicfDot11ACMtTraps 8 }


-- AC Management Notification Variable object

        hpnicfDot11ACMtTrapVarObjects OBJECT IDENTIFIER
    ::= { hpnicfDot11ACMtNotifyGroup 1 }

hpnicfDot11ACMtTrapTunlDwnInfo OBJECT-TYPE
    SYNTAX      INTEGER
        {
            tunnelTimeout(1),
            keyUpdateFailure(2),
            apReset(3),
            apCrash(4),
            apDeleted(5),
            apCfgChange(6)
        }
    MAX-ACCESS  accessible-for-notify
    STATUS      current
    DESCRIPTION
        "Represents the reason for tunnel down.
        The following values are supported:
        tunnelTimeout     - When AC detects the tunnel is broken,
        - it will notify NMS.
        keyUpdateFailure  - rekey process is failed, tunnel will be broken.
        apReset           - Administrator reset AP.
        apCrash           - AP reboot for system crash.
        apDeleted         - Delete AP from AC and trigger tunnel down.
        apCfgChange       - The configuration for AP was changed."
    ::= { hpnicfDot11ACMtTrapVarObjects 1 }

hpnicfDot11ACMtTrapTunlUpInfo OBJECT-TYPE
    SYNTAX      INTEGER
        {
            up(1)
        }
    MAX-ACCESS  accessible-for-notify
    STATUS      current
    DESCRIPTION
        "Represents the reason for tunnel up.
        The following values are supported:
        up(1)  - The AP joined AC.
        "
    ::= { hpnicfDot11ACMtTrapVarObjects 2 }

hpnicfDot11ACMtTrapBackupSwitchInfo OBJECT-TYPE
    SYNTAX      INTEGER
        {
            masterToSlave(1),
            slaveToMaster(2)
        }
    MAX-ACCESS  accessible-for-notify
    STATUS      current
    DESCRIPTION
        "Represents status which the AC switches to.
        The following values are supported:
        masterToSlave  - The AC switches from master to slave.
        slaveToMaster  - The AC switches from slave to master.
        "
    ::= { hpnicfDot11ACMtTrapVarObjects 3 }

hpnicfDot11ACMtTrapTnlAPName OBJECT-TYPE
    SYNTAX      OCTET STRING
    MAX-ACCESS  accessible-for-notify
    STATUS      current
    DESCRIPTION
        "Represents name of the AP which sets up the tunnel with the AC.
        "
    ::= { hpnicfDot11ACMtTrapVarObjects 4 }

hpnicfDot11ACMtTrapTnlAPIPAddr OBJECT-TYPE
    SYNTAX      IpAddress
    MAX-ACCESS  accessible-for-notify
    STATUS      current
    DESCRIPTION
        "Represents IP address of the AP which sets up the tunnel with the AC.
        "
    ::= { hpnicfDot11ACMtTrapVarObjects 5 }

hpnicfDot11LoadBalanceType OBJECT-TYPE
    SYNTAX      INTEGER
        {
            traffic(1),
            session(2)
        }
    MAX-ACCESS  accessible-for-notify
    STATUS      current
    DESCRIPTION
        "Represents which kind load balance is enabled by AC.
         The following values are supported:
         traffic mode load-balancing: traffic snapshot is considered.
         session mode load-balancing: the number of users associated
                                      with the AP/radio is considered.
        "
    ::= { hpnicfDot11ACMtTrapVarObjects 6 }

hpnicfDot11LoadBalanceThreshold OBJECT-TYPE
    SYNTAX      Integer32
    MAX-ACCESS  accessible-for-notify
    STATUS      current
    DESCRIPTION
        "Represents the value of load balance threshold.
        "
    ::= { hpnicfDot11ACMtTrapVarObjects 7 }

hpnicfDot11ACMtTrapAPIPv6Addr OBJECT-TYPE
    SYNTAX      OCTET STRING
    MAX-ACCESS  accessible-for-notify
    STATUS      current
    DESCRIPTION
        "Represents IPv6 address of the AP which sets up the tunnel with
        the AC."
    ::= { hpnicfDot11ACMtTrapVarObjects 8 }

hpnicfDot11ACMtTrapTunlDwnCount OBJECT-TYPE
    SYNTAX      Integer32
    MAX-ACCESS  accessible-for-notify
    STATUS      current
    DESCRIPTION
        "Represents how many times that the tunnel between AC and AP has down."
    ::= { hpnicfDot11ACMtTrapVarObjects 9 }

hpnicfDot11ACMaxStaNum OBJECT-TYPE
    SYNTAX      Integer32
    MAX-ACCESS  accessible-for-notify
    STATUS      current
    DESCRIPTION
        "Represents the max number of STA on AC."
    ::= { hpnicfDot11ACMtTrapVarObjects 10 }

hpnicfDot11ACMtTrapTnlAPSysName OBJECT-TYPE
    SYNTAX      OCTET STRING
    MAX-ACCESS  accessible-for-notify
    STATUS      current
    DESCRIPTION
        "Represents system name of the AP which sets up the tunnel with the AC."
    ::= { hpnicfDot11ACMtTrapVarObjects 11 }

hpnicfDot11ACMtFirstTrapTime OBJECT-TYPE
    SYNTAX      TimeTicks
    MAX-ACCESS  accessible-for-notify
    STATUS      current
    DESCRIPTION
        "Represents the first trap time."
    ::= { hpnicfDot11ACMtTrapVarObjects 12 }

hpnicfDot11ACStatusSwitchInfo OBJECT-TYPE
    SYNTAX      INTEGER
        {
            activeToStandby(1),
            standbyToActive(2)
        }
    MAX-ACCESS  accessible-for-notify
    STATUS      current
    DESCRIPTION
        "Represents status which the AC switches to.
        The following values are supported:
        activeToStandby  - The AC switches from active to standby.
        standbyToActive  - The AC switches from standby to active.
        "
    ::= { hpnicfDot11ACMtTrapVarObjects 13 }

hpnicfDot11SourceACNmsIP OBJECT-TYPE
    SYNTAX      IpAddress
    MAX-ACCESS  accessible-for-notify
    STATUS      current
    DESCRIPTION
        "Represents the NMS IP address of master AC.
        "
    ::= { hpnicfDot11ACMtTrapVarObjects 14 }

hpnicfDot11ACMtTrapAPMacAddress OBJECT-TYPE
    SYNTAX      MacAddress
    MAX-ACCESS  accessible-for-notify
    STATUS      current
    DESCRIPTION
         "Represents the MAC address of an AP."
    ::= { hpnicfDot11ACMtTrapVarObjects 15 }

-- *****************************************************************************
-- *     End OF NotifyGroup
-- *****************************************************************************
END
