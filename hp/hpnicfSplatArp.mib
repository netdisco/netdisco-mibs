-- ==================================================================
-- Copyright (c) 2010-2013 Hewlett-Packard Development Company, L.P.
--
-- Description: MAC management MIB
-- Reference:
-- Version: V1.3
-- History:
--  V1.0 Created by Zhangshilin, 2001.06.29
--  V1.1 2002-01-08 modified by qizhenglin
--  V1.2 2004-09-08 modify STATUS of hpnicfLswProxyArpObject from mandatory to current by gaolong.
--  V1.3 2004-10-12 updated by gaolong
--       Import OBJECT-IDENTITY.
-- ------------------------------------------------------------------

HPN-ICF-LswARP-MIB DEFINITIONS ::= BEGIN
IMPORTS

    MODULE-IDENTITY,OBJECT-TYPE, OBJECT-IDENTITY
        FROM SNMPv2-SMI

    hpnicflswCommon
        FROM HPN-ICF-OID-MIB;


     hpnicfLswArpMib MODULE-IDENTITY
            LAST-UPDATED "200106290000Z"
            ORGANIZATION
                ""
            CONTACT-INFO
                ""
            DESCRIPTION
            ""
            REVISION "200106290000Z"
            DESCRIPTION
            ""
            ::= { hpnicflswCommon  4 }

    hpnicfLswProxyArpObject OBJECT-IDENTITY
            STATUS current
            DESCRIPTION
                "Description."
            ::= { hpnicfLswArpMib 1 }
    hpnicfLswProxyArpEnableTable OBJECT-TYPE
        SYNTAX  SEQUENCE OF HpnicfLswProxyArpEnableEntry
        MAX-ACCESS not-accessible
        STATUS   current
        DESCRIPTION "Contains information that if proxy ARP enabled for every VLAN interface. "
        ::= { hpnicfLswProxyArpObject 1 }

     hpnicfLswProxyArpEnableEntry OBJECT-TYPE
        SYNTAX  HpnicfLswProxyArpEnableEntry
        MAX-ACCESS not-accessible
        STATUS current
        DESCRIPTION
          "Contains information that if proxy ARP enabled for VLAN interface."
        INDEX   { hpnicfLswIfIndex }
        ::= { hpnicfLswProxyArpEnableTable 1 }

    HpnicfLswProxyArpEnableEntry ::=
    SEQUENCE {
        hpnicfLswIfIndex INTEGER ,
        hpnicfLswProxyArpStatus  INTEGER
        }

    hpnicfLswIfIndex OBJECT-TYPE
        SYNTAX  INTEGER
        MAX-ACCESS read-only
        STATUS current
        DESCRIPTION " Vlan interface index "
        ::= { hpnicfLswProxyArpEnableEntry 1 }

    hpnicfLswProxyArpStatus OBJECT-TYPE
        SYNTAX INTEGER
        {
            disabled(0),
            enabled(1)
        }
        MAX-ACCESS  read-write
        STATUS current
        DESCRIPTION " Proxy ARP status for this VLAN interface."
        ::= { hpnicfLswProxyArpEnableEntry 2    }


END
