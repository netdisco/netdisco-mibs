-- =================================================================
-- Copyright (c) 2010-2013 Hewlett-Packard Development Company, L.P.
--
-- Description: protocol priority mib
-- Reference:
-- Version: V1.0
-- History:
--   V1.0 created by zhuangyu
--     The initial version, 2005-01-17
-- =================================================================
HPN-ICF-PROT-PRIORITY-MIB DEFINITIONS ::= BEGIN

    IMPORTS
        hpnicfCommon
            FROM HPN-ICF-OID-MIB
        Integer32, OBJECT-TYPE, MODULE-IDENTITY
            FROM SNMPv2-SMI
        RowStatus
            FROM SNMPv2-TC;

    hpnicfProtocolPriority MODULE-IDENTITY
        LAST-UPDATED "200501171633Z"        -- January 17, 2005 at 16:33 GMT
        ORGANIZATION
            ""
        CONTACT-INFO
            ""
        DESCRIPTION
            "This MIB is used to manage and configure the priority of specified protocol.
            This MIB is applicable to routers, switches and other products.
            "
        REVISION "200501171633Z"        -- January 17, 2005 at 16:33 GMT
        DESCRIPTION
            "The initial revision of this MIB module."
        ::= { hpnicfCommon 37 }


--
-- Node definitions
--
    hpnicfProtocolPriorityObjects OBJECT IDENTIFIER ::= { hpnicfProtocolPriority 1 }

    hpnicfPPri OBJECT IDENTIFIER ::= { hpnicfProtocolPriorityObjects 1 }

    hpnicfProtocolPriorityTable OBJECT-TYPE
        SYNTAX SEQUENCE OF HpnicfProtocolPriorityEntry
        MAX-ACCESS not-accessible
        STATUS current
        DESCRIPTION
            "A table is used to configure the priority of the protocol."
        ::= { hpnicfPPri 1 }

    hpnicfProtocolPriorityEntry OBJECT-TYPE
        SYNTAX HpnicfProtocolPriorityEntry
        MAX-ACCESS not-accessible
        STATUS current
        DESCRIPTION
            "An entry containing information about the priority of the protocol."
        INDEX { hpnicfPPriProtocolType }
        ::= { hpnicfProtocolPriorityTable 1 }

    HpnicfProtocolPriorityEntry ::=
        SEQUENCE {
            hpnicfPPriProtocolType
                INTEGER,
            hpnicfPPriPriorityType
                INTEGER,
            hpnicfPPriPriorityVlaue
                Integer32,
            hpnicfPPriRowStatus
                RowStatus
        }

    hpnicfPPriProtocolType OBJECT-TYPE
        SYNTAX INTEGER
               {
               ospf(1),
               telnet(2),
               snmp(3),
               icmp(4),
               bgp(5),
               ldp(6)
               }
        MAX-ACCESS not-accessible
        STATUS current
        DESCRIPTION
            "Protocol type."
        ::= { hpnicfProtocolPriorityEntry 1 }

    hpnicfPPriPriorityType OBJECT-TYPE
        SYNTAX INTEGER
               {
               ipPrecedence(1),
               dscp(2)
               }
        MAX-ACCESS read-create
        STATUS current
        DESCRIPTION
            "Priority type."
        ::= { hpnicfProtocolPriorityEntry 2 }

    hpnicfPPriPriorityVlaue OBJECT-TYPE
        SYNTAX Integer32 (0..63)
        MAX-ACCESS read-create
        STATUS current
        DESCRIPTION
            "Priority value.
            If setting hpnicfPPriPriorityType to ip-precedence(1),
            the range of hpnicfPPriPriorityVlaue is from 0 to 7.
            If setting hpnicfPPriPriorityType to dscp(2),
            the range of hpnicfPPriPriorityVlaue is from 0 to 63."
        ::= { hpnicfProtocolPriorityEntry 3 }

    hpnicfPPriRowStatus OBJECT-TYPE
        SYNTAX RowStatus
        MAX-ACCESS read-create
        STATUS current
        DESCRIPTION
            "RowStatus, Now support createAndGo,active and destroy.
            To create a new row, hpnicfPPriPriorityType and hpnicfPPriPriorityValue must be specified.
            To modify a row,hpnicfPPriPriorityType and hpnicfPPriPriorityValue
            must change at the same time and the hpnicfPPriRowStatus is active ."
        ::= { hpnicfProtocolPriorityEntry 4 }
END
