-- ==================================================================
-- Copyright (c) 2010-2013 Hewlett-Packard Development Company, L.P.
--
-- Description: Lan Switch trap MIB
-- Reference:
-- Version: V1.3
-- History:
-- V1.0 Created by Zhangshilin, 2001.06.29
-- V1.1 Modified by lifengguang 2008.11.10, add trap node hpnicfBootImageUpdated
-- V1.2 2011-11-26 updated by duyanbing
--      Add hpnicfDevMFirstTrapTime to powerfailure and hpnicfPowerNormal.
-- V1.3 2012-04-26 updated by wangcong
--      Added hpnicfNetworkHealthMonitorFailure, hpnicfNetworkHealthMonitorNormal for reserving.
-- ==================================================================

-- ==================================================================
--
-- Variables and types be imported
--
-- ==================================================================
HPN-ICF-LswTRAP-MIB DEFINITIONS ::= BEGIN
IMPORTS
    MODULE-IDENTITY, NOTIFICATION-TYPE
        FROM SNMPv2-SMI

    hpnicflswCommon
        FROM HPN-ICF-OID-MIB

    hpnicfDevMPowerNum, hpnicfDevMFanNum, hpnicfDevMFirstTrapTime
        FROM HPN-ICF-LswDEVM-MIB

    hpnicfLswFrameIndex, hpnicfLswSlotIndex, hpnicfLswSubslotIndex
        FROM HPN-ICF-LSW-DEV-ADM-MIB;

-- ==================================================================
--
-- ======================= definition begin =========================
--
-- ==================================================================

    hpnicfLswTrapMib MODULE-IDENTITY
            LAST-UPDATED "201111260000Z"
            ORGANIZATION
                ""
            CONTACT-INFO
                ""
            DESCRIPTION
            ""
            REVISION "201111260000Z"
            DESCRIPTION
            ""
            ::= { hpnicflswCommon 12 }

    hpnicfsLswTRAPMibObject OBJECT IDENTIFIER ::= { hpnicfLswTrapMib 1 }

    hpnicfpowerfailure NOTIFICATION-TYPE
      OBJECTS { hpnicfDevMPowerNum, hpnicfDevMFirstTrapTime }
      STATUS  current
      DESCRIPTION
              "Power supply failure"
      ::= { hpnicfsLswTRAPMibObject 1 }

    hpnicfPowerNormal NOTIFICATION-TYPE
      OBJECTS { hpnicfDevMPowerNum, hpnicfDevMFirstTrapTime }
      STATUS  current
      DESCRIPTION
              "Power supply normal"
      ::= { hpnicfsLswTRAPMibObject 2 }

    hpnicfMasterPowerNormal NOTIFICATION-TYPE
      OBJECTS { hpnicfDevMPowerNum }
      STATUS  current
      DESCRIPTION
              "Master power supply normal"
      ::= { hpnicfsLswTRAPMibObject 3 }

    hpnicfSlavePowerNormal NOTIFICATION-TYPE
      OBJECTS { hpnicfDevMPowerNum }
      STATUS  current
      DESCRIPTION
              "Slave power supply normal"
      ::= { hpnicfsLswTRAPMibObject 4 }

    hpnicfPowerRemoved NOTIFICATION-TYPE
      OBJECTS { hpnicfDevMPowerNum }
      STATUS  current
      DESCRIPTION
              "Power removed"
      ::= { hpnicfsLswTRAPMibObject 5 }

    hpnicffanfailure NOTIFICATION-TYPE
      OBJECTS { hpnicfDevMFanNum }
      STATUS  current
      DESCRIPTION
              "Fan failure"
      ::= { hpnicfsLswTRAPMibObject 6 }

    hpnicfFanNormal NOTIFICATION-TYPE
      OBJECTS { hpnicfDevMFanNum }
      STATUS  current
      DESCRIPTION
              "Fan normal"
      ::= { hpnicfsLswTRAPMibObject 7 }

    hpnicfBoardRemoved NOTIFICATION-TYPE
      OBJECTS { hpnicfLswFrameIndex, hpnicfLswSlotIndex }
      STATUS  current
      DESCRIPTION
              "Board removed"
      ::= { hpnicfsLswTRAPMibObject 8 }

    hpnicfBoardInserted NOTIFICATION-TYPE
      OBJECTS { hpnicfLswFrameIndex,hpnicfLswSlotIndex }
      STATUS  current
      DESCRIPTION
              "Board inserted"
      ::= { hpnicfsLswTRAPMibObject 9 }

    hpnicfBoardFailure NOTIFICATION-TYPE
      OBJECTS { hpnicfLswFrameIndex, hpnicfLswSlotIndex }
      STATUS  current
      DESCRIPTION
              "Board failed"
      ::= { hpnicfsLswTRAPMibObject 10 }

    hpnicfBoardNormal NOTIFICATION-TYPE
      OBJECTS { hpnicfLswFrameIndex, hpnicfLswSlotIndex }
      STATUS  current
      DESCRIPTION
              "Board normal"
      ::= { hpnicfsLswTRAPMibObject 11 }

    hpnicfSubcardRemove NOTIFICATION-TYPE
      OBJECTS { hpnicfLswFrameIndex, hpnicfLswSlotIndex, hpnicfLswSubslotIndex }
      STATUS  current
      DESCRIPTION
              "Sub card removeed"
      ::= { hpnicfsLswTRAPMibObject 12 }

    hpnicfSubcardInsert NOTIFICATION-TYPE
      OBJECTS { hpnicfLswFrameIndex, hpnicfLswSlotIndex, hpnicfLswSubslotIndex }
      STATUS  current
      DESCRIPTION
              "Sub card inserted"
      ::= { hpnicfsLswTRAPMibObject 13 }

    hpnicfBoardTemperatureLower NOTIFICATION-TYPE
      OBJECTS { hpnicfLswFrameIndex, hpnicfLswSlotIndex }
      STATUS  current
      DESCRIPTION
              "Board temperature low"
      ::= { hpnicfsLswTRAPMibObject 14 }

    hpnicfBoardTemperatureFromLowerToNormal NOTIFICATION-TYPE
      OBJECTS { hpnicfLswFrameIndex, hpnicfLswSlotIndex }
      STATUS  current
      DESCRIPTION
              "Board temperature form lower to normal"
      ::= { hpnicfsLswTRAPMibObject 15 }

    hpnicfBoardTemperatureHigher NOTIFICATION-TYPE
      OBJECTS { hpnicfLswFrameIndex, hpnicfLswSlotIndex }
      STATUS  current
      DESCRIPTION
              "Board temperature high"
      ::= { hpnicfsLswTRAPMibObject 16 }

    hpnicfBoardTemperatureFormHigherToNormal NOTIFICATION-TYPE
      OBJECTS { hpnicfLswFrameIndex, hpnicfLswSlotIndex }
      STATUS  current
      DESCRIPTION
              "Board temperature from higher to normal"
      ::= { hpnicfsLswTRAPMibObject 17 }

    hpnicfRequestLoading NOTIFICATION-TYPE
      OBJECTS { hpnicfLswFrameIndex, hpnicfLswSlotIndex }
      STATUS  current
      DESCRIPTION
              "Board request load"
      ::= { hpnicfsLswTRAPMibObject 18 }

    hpnicfLoadFailure NOTIFICATION-TYPE
      OBJECTS { hpnicfLswFrameIndex, hpnicfLswSlotIndex }
      STATUS  current
      DESCRIPTION
              "Board load failure"
      ::= { hpnicfsLswTRAPMibObject 19 }

    hpnicfLoadFinished NOTIFICATION-TYPE
      OBJECTS { hpnicfLswFrameIndex, hpnicfLswSlotIndex }
      STATUS  current
      DESCRIPTION
              "Board load finished"
      ::= { hpnicfsLswTRAPMibObject 20 }

    hpnicfBackBoardModeSetFuilure NOTIFICATION-TYPE
      OBJECTS { hpnicfLswFrameIndex }
      STATUS  current
      DESCRIPTION
              "Back board mode set failure"
      ::= { hpnicfsLswTRAPMibObject 21 }

    hpnicfBackBoardModeSetOK NOTIFICATION-TYPE
      OBJECTS { hpnicfLswFrameIndex }
      STATUS  current
      DESCRIPTION
              "Back board mode set OK"
      ::= { hpnicfsLswTRAPMibObject 22 }

    hpnicfPowerInserted NOTIFICATION-TYPE
      OBJECTS { hpnicfDevMPowerNum }
      STATUS  current
      DESCRIPTION
              "Power inserted"
      ::= { hpnicfsLswTRAPMibObject 23 }

    hpnicfBootImageUpdated NOTIFICATION-TYPE
      OBJECTS { hpnicfLswFrameIndex, hpnicfLswSlotIndex }
      STATUS  current
      DESCRIPTION
              "This trap node indicates that the boot image of specified board
              is updated."
      ::= { hpnicfsLswTRAPMibObject 24 }

    hpnicfNetworkHealthMonitorFailure OBJECT IDENTIFIER ::= { hpnicfsLswTRAPMibObject 98 }
    hpnicfNetworkHealthMonitorNormal OBJECT IDENTIFIER ::= { hpnicfsLswTRAPMibObject 99 }

END
