HP-ICF-OSPFV3-MIB DEFINITIONS ::= BEGIN

    IMPORTS
            MODULE-IDENTITY, OBJECT-TYPE,
            Counter32, Integer32, Unsigned32, Gauge32
                    FROM SNMPv2-SMI
            TruthValue
                    FROM SNMPv2-TC
            MODULE-COMPLIANCE, OBJECT-GROUP
                    FROM SNMPv2-CONF
            InetAddressIPv6
                    FROM INET-ADDRESS-MIB
            hpSwitch
                    FROM HP-ICF-OID
            HpicfOspfLogType, HpicfOspfLogAction
                   FROM HP-ICF-OSPF
            Metric, BigMetric
                    FROM OSPF-MIB
            ospfv3AsLsdbEntry, ospfv3LinkLsdbEntry,
	    ospfv3AreaLsdbEntry,
            ospfv3IfEntry, ospfv3NbrEntry, ospfv3IfIndex,
	    ospfv3IfInstId,
            ospfv3AreaLsdbAreaId, ospfv3AreaLsdbType, ospfv3AreaLsdbLsid,
            ospfv3AreaLsdbRouterId, ospfv3LinkLsdbIfIndex,
            ospfv3LinkLsdbIfInstId, ospfv3LinkLsdbType,
	    ospfv3LinkLsdbRouterId,
            ospfv3LinkLsdbLsid,
            Ospfv3RouterIdTC, ospfv3AreaEntry,
            ospfv3AreaAggregateEntry
                    FROM OSPFV3-MIB;



    hpicfOspfv3MIB  MODULE-IDENTITY
            LAST-UPDATED "201803070000Z" -- March 7, 2018
            ORGANIZATION "HP Networking"
            CONTACT-INFO "Hewlett Packard Company
                          8000 Foothills Blvd.
                          Roseville, CA 95747"
            DESCRIPTION "The MIB module contains HP proprietary
                           extensions to the OSPFV3-MIB module."

            REVISION    "201803070000Z" -- March 7, 2018
            DESCRIPTION "Added hpicfOspfv3DistributeListEntry.
                         Added hpicfOspfv3DistributeListGroup."

            REVISION    "201705180000Z"
            DESCRIPTION "Added hpicfOspfv3ReferenceCost.
                         Added hpicfOspfv3IfFlagValue
                         Added hpicfOspfv3MetricGroup
                         Added hpicfOspfv3Compliance2
                         Deprecated hpicfOspfv3Compliance."

            REVISION    "201406130000Z"
            DESCRIPTION "Updated the descriptions for MIB objects.
                         Deleted Notifications."


            REVISION    "201204300000Z"
            DESCRIPTION "Added objects in hpicfOspfv3NbrTable
                           hpicfOspfv3NbrDataBaseSummary
                           hpicfOspfv3NbrLinkStateRequest
                           hpicfOspfv3NbrRestartState
                         Added objected in hpicfOspfv3IfStatsTable
                           hpicfOspfv3IfSentTotalErrorCount
                           hpicfOspfv3IfRcvdTotalErrorCount"

            REVISION    "201204200000Z"
            DESCRIPTION "Added hpicfOspfv3AreaLsdbStatsTable,
                         hpicfOspfv3AreaLsdbStatsTable and added objects
                           hpicfOspfv3AreaLsdbStatRtrLsaCnt
                           hpicfOspfv3AreaLsdbStatNwLsaCnt
                           hpicfOspfv3AreaLsdbStatInterPreLsaCnt
                           hpicfOspfv3AreaLsdbStatInterRtrLsaCnt
                           hpicfOspfv3AreaLsdbStatIntraPreLsaCnt,
                         Added objects in hpicfOspfv3GeneralGroup
                           hpicfOspfv3AreaCount
                           hpicfOspfv3RestartHelper
                           hpicfOspfv3ASscopeUnknownLsaCount
                           hpicfOspfv3LinkLsdbStatLinkLsa,
                         Added objects in hpicfOspfv3LinkLsdbTable,
                         Added objects in hpicfOspfv3AreaTable
                           hpicfOspfv3AreaNbrDownCount
                           hpicfOspfv3AreaNbrAttemptCount
                           hpicfOspfv3AreaNbrInitCount
                           hpicfOspfv3AreaNbr2wayCount
                           hpicfOspfv3AreaNbrExstartCount
                           hpicfOspfv3AreaNbrExchangeCount
                           hpicfOspfv3AreaNbrLoadingCount
                           hpicfOspfv3AreaNbrFullCount
                           hpicfOspfv3AreaInterfaceCount
                           hpicfOspfv3AreaScopeUnknownLsaCount
                         Added objects in hpicfOspfv3AreaLsdbTable
                           hpicfOspfv3AreaLsdbLsaLength
                           hpicfOspfv3AreaLsdbLinks"

            REVISION    "201106131953Z"
            DESCRIPTION "Added hpicfOspfv3AreaAggregateTable,
                         hpicfOspfv3AreaAggregateEntry,
                         HpicfOspfv3AreaAggregateEntry and
                         hpicfOspfv3AreaAggregateCost"


            REVISION    "201011040000Z"
            DESCRIPTION "Added 'hpicfOspfv3AreaTable',
                         'hpicfOspfv3VirtIntfTable' and added objects
                         in 'hpicfOspfv3IfTable'"

            REVISION    "200902051800Z"
            DESCRIPTION "Initial revision."
            ::= { hpSwitch 44 }

    -- Top-level structure of MIB
     hpicfOspfv3Objects        OBJECT IDENTIFIER ::= {  hpicfOspfv3MIB 1 }
     hpicfOspfv3Conformance    OBJECT IDENTIFIER ::= {  hpicfOspfv3MIB 2 }

    -- extension to OSPFv3 MIB

    -- These parameters apply globally to the Router's
    -- OSPFv3 Process.

     hpicfOspfv3GeneralGroup OBJECT IDENTIFIER ::= {  hpicfOspfv3Objects 1 }

     hpicfOspfv3DefaultImportMetric OBJECT-TYPE
        SYNTAX      BigMetric
        MAX-ACCESS  read-write
        STATUS      current
        DESCRIPTION "The default metric used for advertising
                    external routes by this router."
        ::= { hpicfOspfv3GeneralGroup 1 }

     hpicfOspfv3DefaultImportMetricType OBJECT-TYPE
        SYNTAX      INTEGER {
                        externalType1(1),
                        externalType2(2)
                    }
        MAX-ACCESS  read-write
        STATUS      current
        DESCRIPTION "The default metric type used for advertising
                    external routes by this router."
        ::= { hpicfOspfv3GeneralGroup 2 }

    hpicfOspfv3IntraAreaDistance OBJECT-TYPE
        SYNTAX      Integer32 (1..255)
        MAX-ACCESS  read-write
        STATUS      current
        DESCRIPTION "The administrative distance to associate
                    with intra-area routes learned by OSPF.  Routes
                    with lower distances are preferred.  By default,
                    OSPF routes have an administrative distance of 110.

                    Note that the administrative distance settings
                    for OSPF do not affect the choice of routes
                    within OSPF.  OSPF will still prefer intra-area
                    routes over inter-area or AS-external routes even
                    if hpicfOspfv3InterAreaDistance or
                    hpicfOspfv3ExternalDistance is lower than
                    hpicfOspfv3IntraAreaDistance.  The appropriate
                    administrative distance value is applied to the
                    route that OSPF selects as its best route to a
                    destination and is used to decide whether OSPF's
                    route is preferred over a route from some other
                    source."
        ::= { hpicfOspfv3GeneralGroup 3}

    hpicfOspfv3InterAreaDistance OBJECT-TYPE
        SYNTAX      Integer32 (1..255)
        MAX-ACCESS  read-write
        STATUS      current
        DESCRIPTION "The administrative distance to associate
                    with inter-area routes learned by OSPF.  Routes
                    with lower distances are preferred.  By default,
                    OSPF routes have an administrative distance of 110.

                    Note that the administrative distance settings
                    for OSPF do not affect the choice of routes
                    within OSPF.  OSPF will still prefer intra-area
                    routes over inter-area routes, even if
                    hpicfOspfv3InterAreaDistance is lower than
                    hpicfOspfv3IntraAreaDistance.  It will also still
                    prefer inter-area routes over AS-external routes
                    even if hpicfOspfv3ExternalDistance is lower than
                    hpicfOspfv3InterAreaDistance.  The appropriate
                    administrative distance value is applied to the
                    route that OSPF selects as its best route to a
                    destination and is used to decide whether OSPF's
                    route is preferred over a route from some other
                    source."
        ::= { hpicfOspfv3GeneralGroup 4 }

    hpicfOspfv3ExternalDistance OBJECT-TYPE
        SYNTAX      Integer32 (1..255)
        MAX-ACCESS  read-write
        STATUS      current
        DESCRIPTION "The administrative distance to associate
                    with AS-external routes learned by OSPF.  Routes
                    with lower distances are preferred.  By default,
                    OSPF routes have an administrative distance of 110.

                    Note that the administrative distance settings
                    for OSPF do not affect the choice of routes
                    within OSPF.  OSPF will still prefer intra-area
                    routes and inter-area routes over AS-external
                    routes even if hpicfOspfv3ExternalDistance is lower
                    than the hpicfOspfv3IntraAreaDistance or
                    hpicfOspfv3InterAreaDistance.  The appropriate
                    administrative distance value is applied to the
                    route that OSPF selects as its best route to a
                    destination and is used to decide whether OSPF's
                    route is preferred over a route from some other
                    source."
        ::= { hpicfOspfv3GeneralGroup  5 }

    hpicfOspfv3SpfThrottleStartInterval OBJECT-TYPE
        SYNTAX      Integer32 (0..600)
        MAX-ACCESS  read-write
        STATUS      current
        DESCRIPTION "Initial SPF schedule delay"
        DEFVAL {0 }
        ::= { hpicfOspfv3GeneralGroup 7}

    hpicfOspfv3SpfThrottleWaitInterval OBJECT-TYPE
        SYNTAX      Integer32 (0..600)
        MAX-ACCESS  read-write
        STATUS      current
        DESCRIPTION "Minimum wait time between two consecutive SPFs
                     When spf throttle is triggered."
        DEFVAL {0 }
        ::= { hpicfOspfv3GeneralGroup 8}

    hpicfOspfv3SpfThrottleMaxWaitTime OBJECT-TYPE
        SYNTAX      Integer32 (0..600)
        MAX-ACCESS  read-write
        STATUS      current
        DESCRIPTION "Maximum time between two consecutive SPFs
                     runs when spf throttling active."

        DEFVAL {0 }
        ::= { hpicfOspfv3GeneralGroup 9}

    hpicfOspfv3SpfThrottleCurrentSpfInterval OBJECT-TYPE
        SYNTAX      Unsigned32
        MAX-ACCESS  read-only
        STATUS      current
        DESCRIPTION "Current dynamic wait interval between SPF computations"
        ::= { hpicfOspfv3GeneralGroup 10}

    hpicfOspfv3AreaCount OBJECT-TYPE
        SYNTAX      Unsigned32
        MAX-ACCESS  read-only
        STATUS      current
        DESCRIPTION "Number of areas in a router"
        ::= { hpicfOspfv3GeneralGroup 11}

    hpicfOspfv3RestartHelper OBJECT-TYPE
        SYNTAX      TruthValue
        MAX-ACCESS  read-only
        STATUS      current
        DESCRIPTION "Graceful restart helper status
                     A value of true (1) indicates that
                     Restart helper is enabled, false(2)
                     indicates that Restart helper is disabled."
        DEFVAL { true }
        ::= { hpicfOspfv3GeneralGroup 12}

    hpicfOspfv3ASscopeUnknownLsaCount OBJECT-TYPE
        SYNTAX          Counter32
        MAX-ACCESS      read-only
        STATUS          current
        DESCRIPTION "The total number of AS-scope unknown link state
                     advertisements received."
        DEFVAL { 0 }
        ::= { hpicfOspfv3GeneralGroup 13}

    hpicfOspfv3LinkLsdbStatLinkLsa OBJECT-TYPE
    SYNTAX          Counter32
    MAX-ACCESS      read-only
    STATUS          current
    DESCRIPTION "This object indicates total
                 number of Link LSAs in the router."
    DEFVAL { 0 }
    ::= { hpicfOspfv3GeneralGroup 14 }

   hpicfOspfv3TotalUnknownLsa OBJECT-TYPE
       SYNTAX          Unsigned32
       MAX-ACCESS      read-only
       STATUS          current
       DESCRIPTION "This object indicates total
                    number of LSAs received with Unknown type."
       DEFVAL { 0 }
   ::= { hpicfOspfv3GeneralGroup 15 }

   hpicfOspfv3ReferenceCost OBJECT-TYPE
        SYNTAX      Metric
        MAX-ACCESS  read-write
        STATUS      current
        DESCRIPTION "The reference cost is used as global
                    configuration for internal area cost & vlan cost."
   ::= { hpicfOspfv3GeneralGroup 16 }

 -- END : 1@ Added PROPRIETARY


    hpicfOspfv3IfMetricObjects OBJECT IDENTIFIER ::= { hpicfOspfv3MIB 4 }
-- ---------------------------------------------------------- --
-- Extensions to the ospfv3IfEntry
-- ---------------------------------------------------------- --

    hpicfOspfv3IfMetricTable OBJECT-TYPE
       SYNTAX      SEQUENCE OF HpicfOspfIfMetricEntry
       MAX-ACCESS  not-accessible
       STATUS      current
       DESCRIPTION
           "Extensions to the table that contains OSPF Metric specific
            information."
          ::= { hpicfOspfv3IfMetricObjects 1 }

    hpicfOspfv3IfMetricEntry OBJECT-TYPE
       SYNTAX      HpicfOspfIfMetricEntry
       MAX-ACCESS  not-accessible
       STATUS      current
       DESCRIPTION
           "A list of extensions to the information maintained
            for an OSPF interface."
       AUGMENTS { ospfv3IfEntry }
          ::= { hpicfOspfv3IfMetricTable 1 }

    HpicfOspfIfMetricEntry ::=
       SEQUENCE {
            hpicfOspfv3IfFlagValue Integer32
        }

    hpicfOspfv3IfFlagValue  OBJECT-TYPE
       SYNTAX      Integer32 (-1..1)
       MAX-ACCESS  read-write
       STATUS      current
       DESCRIPTION
            "This flag is defined to know the type of OSPF cost
                 configuration..
              -1 : Default configuration.
               0 : Manual configuration.
               1 : Global configuration (value taken from global)."
       DEFVAL { -1 }

          ::= { hpicfOspfv3IfMetricEntry 1 }



    -- OSPFv3 AS-Scope Link State Database


     hpicfOspfv3AsLsdbTable OBJECT-TYPE
            SYNTAX          SEQUENCE OF HpicfOspfv3AsLsdbEntry
            MAX-ACCESS      not-accessible
            STATUS          current
            DESCRIPTION "The OSPFv3 AS-Scope Link State Database
                         (LSDB). The LSDB contains the AS-Scope Link State
                         Advertisements from throughout the areas that the
                         device is attached to."
            ::= {  hpicfOspfv3Objects 2 }

     hpicfOspfv3AsLsdbEntry OBJECT-TYPE
            SYNTAX          HpicfOspfv3AsLsdbEntry
            MAX-ACCESS      not-accessible
            STATUS          current
            DESCRIPTION "A single AS-Scope Link State Advertisement."
            AUGMENTS { ospfv3AsLsdbEntry }
            ::= {  hpicfOspfv3AsLsdbTable 1 }

    HpicfOspfv3AsLsdbEntry ::= SEQUENCE {
             hpicfOspfv3AsLsdbEFTFlags
                    BITS,
             hpicfOspfv3AsLsdbMetric
                    Metric,
             hpicfOspfv3AsLsdbPrefixLength
                    Unsigned32,
             hpicfOspfv3AsLsdbPrefixOptions
                    Unsigned32,
             hpicfOspfv3AsLsdbRefLsType
                    Unsigned32,
             hpicfOspfv3AsLsdbAddrPrefix
                    InetAddressIPv6,
             hpicfOspfv3AsLsdbFwdingAddress
                    InetAddressIPv6,
             hpicfOspfv3AsLsdbExtRouteTags
                    Unsigned32,
             hpicfOspfv3AsLsdbRefLsId
                    Unsigned32,
             hpicfOspfv3AsLsdbLsaLength
                    Unsigned32
             }

         hpicfOspfv3AsLsdbEFTFlags OBJECT-TYPE
            SYNTAX         BITS {
                bitE(0),         -- Type 1/Type 2 Metric
                bitF(1),         -- Forwarding Address present or not
                bitT(2)          -- External Route Tag
            }
            MAX-ACCESS     read-only
            STATUS         current
            DESCRIPTION "A 32-bit integer Representing the E,F and T bit flags"
            ::= { hpicfOspfv3AsLsdbEntry 1 }

     hpicfOspfv3AsLsdbMetric OBJECT-TYPE
            SYNTAX          Metric
            MAX-ACCESS      read-only
            STATUS          current
            DESCRIPTION "The cost associated with this route."
            ::= {  hpicfOspfv3AsLsdbEntry 2 }

     hpicfOspfv3AsLsdbPrefixLength OBJECT-TYPE
            SYNTAX          Unsigned32
            MAX-ACCESS      read-only
            STATUS          current
            DESCRIPTION "The Prefix Length of the Address Prefix."
            ::= {  hpicfOspfv3AsLsdbEntry 3 }

     hpicfOspfv3AsLsdbPrefixOptions OBJECT-TYPE
            SYNTAX          Unsigned32
            MAX-ACCESS      read-only
            STATUS          current
            DESCRIPTION "The Prefix Options associated with the Address Prefix."
            ::= {  hpicfOspfv3AsLsdbEntry 4 }

     hpicfOspfv3AsLsdbRefLsType OBJECT-TYPE
            SYNTAX          Unsigned32
            MAX-ACCESS      read-only
            STATUS          current
            DESCRIPTION "If non-zero value, this refers to another LSA type in
                         Link State Database further identified by the Reference
                         Link State ID field"
            ::= {  hpicfOspfv3AsLsdbEntry 5 }

     hpicfOspfv3AsLsdbAddrPrefix OBJECT-TYPE
            SYNTAX          InetAddressIPv6
            MAX-ACCESS      read-only
            STATUS          current
            DESCRIPTION "The advertised 16-byte Address Prefix."
            ::= {  hpicfOspfv3AsLsdbEntry 6 }

     hpicfOspfv3AsLsdbFwdingAddress OBJECT-TYPE
            SYNTAX          InetAddressIPv6
            MAX-ACCESS      read-only
            STATUS          current
            DESCRIPTION "If included, Data traffic for the advertised destination
                         will be forwarded to this address."
            ::= {  hpicfOspfv3AsLsdbEntry 7 }

     hpicfOspfv3AsLsdbExtRouteTags OBJECT-TYPE
            SYNTAX          Unsigned32
            MAX-ACCESS      read-only
            STATUS          current
            DESCRIPTION "The 32-bit Route Tag for the advertised Route."
            ::= {  hpicfOspfv3AsLsdbEntry 8 }

     hpicfOspfv3AsLsdbRefLsId OBJECT-TYPE
            SYNTAX          Unsigned32
            MAX-ACCESS      read-only
            STATUS          current
            DESCRIPTION "The 32-bit Link state ID of the referenced LSA entry."
            ::= {  hpicfOspfv3AsLsdbEntry 9 }

    hpicfOspfv3AsLsdbLsaLength OBJECT-TYPE
            SYNTAX          Unsigned32
            MAX-ACCESS      read-only
            STATUS          current
            DESCRIPTION "This field describes the length of LSA."
            ::= {  hpicfOspfv3AsLsdbEntry 10 }

     --  OSPFv3 Area-Scope Link State Database


     hpicfOspfv3AreaLsdbTable OBJECT-TYPE
            SYNTAX          SEQUENCE OF HpicfOspfv3AreaLsdbEntry
            MAX-ACCESS      not-accessible
            STATUS          current
            DESCRIPTION "The OSPFv3 Area-Scope link state database.
                         The LSDB contains the Area-Scope Link State
                         Advertisements from throughout the area that the
                         device is attached to."
            ::= {  hpicfOspfv3Objects 3 }

     hpicfOspfv3AreaLsdbEntry OBJECT-TYPE
            SYNTAX          HpicfOspfv3AreaLsdbEntry
            MAX-ACCESS      not-accessible
            STATUS          current
            DESCRIPTION "A single Area-Scope Link State Advertisement."
            AUGMENTS        {  ospfv3AreaLsdbEntry }
            ::= {  hpicfOspfv3AreaLsdbTable 1 }

    HpicfOspfv3AreaLsdbEntry ::= SEQUENCE {
             hpicfOspfv3AreaLsdbRtrCapBits     -- RTR
                    BITS,
             hpicfOspfv3AreaLsdbOptions        -- NTW
                    Unsigned32,
             hpicfOspfv3AreaLsdbMetric         -- RTR, NAP, NSA
                    Metric,
             hpicfOspfv3AreaLsdbPrefixLength   -- IAP, NSA
                    Unsigned32,
             hpicfOspfv3AreaLsdbPrefixOptions  -- IAP, NSA
                    Unsigned32,
             hpicfOspfv3AreaLsdbAddrPrefix     -- IAP, NSA
                    InetAddressIPv6,
             hpicfOspfv3AreaLsdbDstRtrId       -- IAR
                    Ospfv3RouterIdTC,
             hpicfOspfv3AreaLsdbNumPrefixes    -- NAP
                    Unsigned32,
             hpicfOspfv3AreaLsdbRefLsType      -- NAP, NSA
                    Unsigned32,
             hpicfOspfv3AreaLsdbRefLsId        -- NAP, NSA
                    Unsigned32,
             hpicfOspfv3AreaLsdbRefAdvRtrId    -- NAP
                    Ospfv3RouterIdTC,
             hpicfOspfv3AreaLsdbEFTFlags
                    BITS,                      -- NSA
             hpicfOspfv3AreaLsdbFwdingAddress
                    InetAddressIPv6,           -- NSA
             hpicfOspfv3AreaLsdbExtRouteTags
                    Unsigned32,                -- NSA
             hpicfOspfv3AreaLsdbLsaLength
                    Unsigned32,
             hpicfOspfv3AreaLsdbLinks
                    Counter32
             }
     hpicfOspfv3AreaLsdbRtrCapBits OBJECT-TYPE
            SYNTAX         BITS {
                bitV(0),         -- Virtual Link router (Transit Area)
                bitE(1),         -- AS Boundary Router
                bitB(2),         -- Area Border Router
                bitW(3),         -- Wide-Card Multicast receiver (MOSPF only)
                bitNt(4)         -- NSSA Translation capabale ABR (RFC3101)
            }
            MAX-ACCESS     read-only
            STATUS         current
            DESCRIPTION "This field is valid only for Router LSA. It
                         represents the capabilities of the router in the Area."
            REFERENCE
                "OSPF Version 3, Appendix A.4.2 Router LSAs, RFC5340"

            ::= { hpicfOspfv3AreaLsdbEntry 1 }

     hpicfOspfv3AreaLsdbOptions OBJECT-TYPE
            SYNTAX         Unsigned32
            MAX-ACCESS     read-only
            STATUS         current
            DESCRIPTION "The Options field enables OSPF routers to support
                         (or not support) optional capabilities, and to
                         communicate their capability level to other
                         OSPF routers. This field is valid if the LSA
                         is a Router LSA or a Network LSA, or an
                         Inter-Area-Router LSA."
            REFERENCE
                "OSPF Version 3, Appendix A.2 The Options field"
            ::= { hpicfOspfv3AreaLsdbEntry 2 }

     hpicfOspfv3AreaLsdbMetric OBJECT-TYPE
            SYNTAX         Metric
            MAX-ACCESS     read-only
            STATUS         current
            DESCRIPTION "This field is valid only for Router LSA, a
                         Inter-Area_prefix LSA or a NSSA LSA. This field
                         indicates the cost involved in
                         using the interface or route."
            ::= { hpicfOspfv3AreaLsdbEntry 3 }

     hpicfOspfv3AreaLsdbPrefixLength OBJECT-TYPE
            SYNTAX          Unsigned32
            MAX-ACCESS      read-only
            STATUS          current
            DESCRIPTION "The Prefix Length of the Address Prefix."
            ::= {  hpicfOspfv3AreaLsdbEntry 4 }

     hpicfOspfv3AreaLsdbPrefixOptions OBJECT-TYPE
            SYNTAX          Unsigned32
            MAX-ACCESS      read-only
            STATUS          current
            DESCRIPTION "The Prefix Options associated with the Address Prefix."
            ::= {  hpicfOspfv3AreaLsdbEntry 5 }

     hpicfOspfv3AreaLsdbAddrPrefix OBJECT-TYPE
            SYNTAX          InetAddressIPv6
            MAX-ACCESS      read-only
            STATUS          current
            DESCRIPTION "The advertised 16-byte Address Prefix."
            ::= {  hpicfOspfv3AreaLsdbEntry 6 }

     hpicfOspfv3AreaLsdbDstRtrId OBJECT-TYPE
            SYNTAX         Ospfv3RouterIdTC
            MAX-ACCESS     read-only
            STATUS         current
            DESCRIPTION "The Router ID of the router being described by
                         the LSA. This field is valid if
                         the LSA is a Inter-Area-Router LSA."
            ::= { hpicfOspfv3AreaLsdbEntry 7 }

     hpicfOspfv3AreaLsdbNumPrefixes OBJECT-TYPE
            SYNTAX         Unsigned32
            MAX-ACCESS     read-only
            STATUS         current
            DESCRIPTION "This field is valid only for Inter-Area-Prefix LSA
                         and indicates the number of prefixes in the LSA."
            ::= { hpicfOspfv3AreaLsdbEntry 8 }

     hpicfOspfv3AreaLsdbRefLsType OBJECT-TYPE
            SYNTAX         Unsigned32
            MAX-ACCESS     read-only
            STATUS         current
            DESCRIPTION "This field is valid only for Inter-Area-Prefix LSA or a
                         NSSA LSA. If non-zero, an LSA with this LS type is to be
                         associated with this LSA."
            ::= { hpicfOspfv3AreaLsdbEntry 9 }

     hpicfOspfv3AreaLsdbRefLsId OBJECT-TYPE
            SYNTAX         Unsigned32
            MAX-ACCESS     read-only
            STATUS         current
            DESCRIPTION "This field is valid only for Inter-Area-Prefix LSA or
                         a NSSA LSA. This field is included only if the
                         Reference LS Type field is set and identifies
                         the LSA with this Link State ID."
            ::= { hpicfOspfv3AreaLsdbEntry 10 }

     hpicfOspfv3AreaLsdbRefAdvRtrId OBJECT-TYPE
            SYNTAX         Ospfv3RouterIdTC
            MAX-ACCESS     read-only
            STATUS         current
            DESCRIPTION "This field is valid only for Inter-Area-Prefix LSA or
                         a NSSA LSA. This field is included only if the
                         Reference LS Type field is set and identifies the LSA
                         having this Router ID as the advertising Router ID."
            ::= { hpicfOspfv3AreaLsdbEntry 11 }

     hpicfOspfv3AreaLsdbEFTFlags OBJECT-TYPE
            SYNTAX         BITS {
                bitE(0),         -- Type 1/Type 2 Metric
                bitF(1),         -- Forwarding Address present or not
                bitT(2)          -- External Route Tag
            }
            MAX-ACCESS     read-only
            STATUS         current
            DESCRIPTION "This field is valid only for NSSA LSA. This field
                         represents the E,F and T bit flags"
            ::= { hpicfOspfv3AreaLsdbEntry 12 }

     hpicfOspfv3AreaLsdbFwdingAddress OBJECT-TYPE
            SYNTAX          InetAddressIPv6
            MAX-ACCESS      read-only
            STATUS          current
            DESCRIPTION "This field is valid only for NSSA LSA. This field is
                         present only if the 'F' Bit is set in the EFT flags
                         field and if included, the data traffic for the
                         advertised destination will be forwarded to this
                         address."
            ::= {  hpicfOspfv3AreaLsdbEntry 13 }

     hpicfOspfv3AreaLsdbExtRouteTags OBJECT-TYPE
            SYNTAX          Unsigned32
            MAX-ACCESS      read-only
            STATUS          current
            DESCRIPTION "This field is valid only for NSSA LSA. This field is
                         present only if the 'T' Bit is set in the EFT flags
                         field. A 32-bit field which may be used to communicate
                         additional information between AS boundary routers."
            ::= {  hpicfOspfv3AreaLsdbEntry 14 }

     hpicfOspfv3AreaLsdbLsaLength OBJECT-TYPE
            SYNTAX          Unsigned32
            MAX-ACCESS      read-only
            STATUS          current
            DESCRIPTION "This field describes the length of LSA."
            ::= {  hpicfOspfv3AreaLsdbEntry 15 }

     hpicfOspfv3AreaLsdbLinks OBJECT-TYPE
            SYNTAX          Counter32
            MAX-ACCESS      read-only
            STATUS          current
            DESCRIPTION "This field describes the number of links."
            ::= {  hpicfOspfv3AreaLsdbEntry 16 }

     -- OSPFv3 Link-Scope Link State Database, for non-virtual interfaces

     hpicfOspfv3LinkLsdbTable OBJECT-TYPE
            SYNTAX          SEQUENCE OF HpicfOspfv3LinkLsdbEntry
            MAX-ACCESS      not-accessible
            STATUS          current
            DESCRIPTION "The OSPFv3 Link-Scope link state database(LSDB) for
                         non-virtual interfaces. The LSDB contains the
                         Link-Scope Link State Advertisements from the
                         interfaces that the device is attached to."
            ::= {  hpicfOspfv3Objects  4 }

     hpicfOspfv3LinkLsdbEntry OBJECT-TYPE
            SYNTAX          HpicfOspfv3LinkLsdbEntry
            MAX-ACCESS      not-accessible
            STATUS          current
            DESCRIPTION "A single Link-Scope Link State Advertisement."
            AUGMENTS    { ospfv3LinkLsdbEntry }
            ::= {  hpicfOspfv3LinkLsdbTable 1 }

    HpicfOspfv3LinkLsdbEntry ::= SEQUENCE {
             hpicfOspfv3LinkLsdbRtrPriority
                    Unsigned32,
             hpicfOspfv3LinkLsdbOptions
                    Unsigned32,
             hpicfOspfv3LinkLsdbLocalAddress
                    InetAddressIPv6,
             hpicfOspfv3LinkLsdbNumPrefixes
                    Unsigned32,
             hpicfOspfv3LinkLsdbLsaLength
                    Unsigned32
            }

      hpicfOspfv3LinkLsdbRtrPriority OBJECT-TYPE
            SYNTAX          Unsigned32
            MAX-ACCESS      read-only
            STATUS          current
            DESCRIPTION "This field is the OSPF priority set for this router"
            ::= {  hpicfOspfv3LinkLsdbEntry 1 }

     hpicfOspfv3LinkLsdbOptions OBJECT-TYPE
            SYNTAX          Unsigned32
            MAX-ACCESS      read-only
            STATUS          current
            DESCRIPTION "The Options field enables OSPF routers to support
                         (or not support) optional capabilities, and to
                         communicate their capability level to other
                         OSPF routers."
            REFERENCE
                "OSPF Version 3, Appendix A.2 The Options field"
            ::= {  hpicfOspfv3LinkLsdbEntry 2 }

     hpicfOspfv3LinkLsdbLocalAddress  OBJECT-TYPE
            SYNTAX          InetAddressIPv6
            MAX-ACCESS      read-only
            STATUS          current
            DESCRIPTION "The advertising router's link local IPv6 address"
            ::= {  hpicfOspfv3LinkLsdbEntry 3 }

     hpicfOspfv3LinkLsdbNumPrefixes OBJECT-TYPE
            SYNTAX          Unsigned32
            MAX-ACCESS      read-only
            STATUS          current
            DESCRIPTION "The number of other links on the advertising router"
            ::= {  hpicfOspfv3LinkLsdbEntry 4 }

     hpicfOspfv3LinkLsdbLsaLength OBJECT-TYPE
            SYNTAX          Unsigned32
            MAX-ACCESS      read-only
            STATUS          current
            DESCRIPTION "This field describes the length of LSA."
            ::= {  hpicfOspfv3LinkLsdbEntry 5 }

    -- OSPFv3 Interface Table

     hpicfOspfv3IfTable OBJECT-TYPE
            SYNTAX          SEQUENCE OF HpicfOspfv3IfEntry
            MAX-ACCESS      not-accessible
            STATUS          current
            DESCRIPTION "The table describes the Ospfv3 interfaces."
            REFERENCE
                "OSPF Version 2, Appendix C.3 Router interface
                parameters"
            ::= {  hpicfOspfv3Objects 5 }

     hpicfOspfv3IfEntry OBJECT-TYPE
            SYNTAX          HpicfOspfv3IfEntry
            MAX-ACCESS      not-accessible
            STATUS          current
            DESCRIPTION "The Entry describes one Ospfv3 interface."
            AUGMENTS  { ospfv3IfEntry }
            ::= {  hpicfOspfv3IfTable 1 }

    HpicfOspfv3IfEntry ::= SEQUENCE {
             hpicfOspfv3IfPassive
                    TruthValue,
             hpicfOspfv3IfNbrCount
                    Unsigned32,
             hpicfOspfv3IfDRAddr
                    InetAddressIPv6,
             hpicfOspfv3IfBDRAddr
                    InetAddressIPv6,
             hpicfOspfv3IfHelloDueTime
                    Unsigned32,
             hpicfOspfv3IfAdjNbrCount
                    Unsigned32
            }

    hpicfOspfv3IfPassive   OBJECT-TYPE
           SYNTAX      TruthValue
           MAX-ACCESS  read-create
           STATUS      current
           DESCRIPTION "The passive state configuration of the OSPF interface.
                        In the passive mode no OSPF protocol messages are
                        exchanged on this interface.

                        true  (1)   -  The interface is configured to work
                                       in Passive mode
                        false (2)   -  The interface is configured to work
                                       in normal mode.
                             This is the default configuration.

                        Changing the value will cause OSPF to reset on this
                        interface and make necessary adjustments to
                        the link state database.

                         All other operations are not defined and will not
                         affect the state of the protocol."

           DEFVAL { false }
           ::= { hpicfOspfv3IfEntry 1 }

    hpicfOspfv3IfNbrCount OBJECT-TYPE
           SYNTAX	      Unsigned32
           MAX-ACCESS	read-only
	        STATUS	      current
	        DESCRIPTION "This object specifies the number of OSPFv3 neighbors
                        reachable via this interface. This counter should be
                        incremented when a new neighbor is added in the network
                        in which this interface is present.
                        It should be decremented when a neighbor is disconnected."
           ::= { hpicfOspfv3IfEntry 2 }

   hpicfOspfv3IfDRAddr  OBJECT-TYPE
       SYNTAX       InetAddressIPv6
       MAX-ACCESS   read-only
       STATUS       current
       DESCRIPTION "This object specifies link local ipv6 address of
                    Designated Router on the interface."
       ::= { hpicfOspfv3IfEntry 10 }

   hpicfOspfv3IfBDRAddr  OBJECT-TYPE
       SYNTAX       InetAddressIPv6
       MAX-ACCESS   read-only
       STATUS       current
       DESCRIPTION "This object specifies link local ipv6 address
                    of Backup Designated Router on the interface."
       ::= { hpicfOspfv3IfEntry 11 }

   hpicfOspfv3IfHelloDueTime  OBJECT-TYPE
       SYNTAX       Unsigned32
       MAX-ACCESS   read-only
       STATUS       current
       DESCRIPTION "This object specifies the time remaining for the
                    hello timer for the particular Interface to expire."
       ::= { hpicfOspfv3IfEntry 12 }

   hpicfOspfv3IfAdjNbrCount OBJECT-TYPE
       SYNTAX       Unsigned32
       MAX-ACCESS   read-only
       STATUS       current
       DESCRIPTION "This object specifies the number of fully
                    adjacent neighbors present on this interface.
                    This counter should be incremented when a new
                    neighbor becomes fully adjacent. It should be
                    decremented when the neighbor goes out from
                    full state."
       ::= { hpicfOspfv3IfEntry 13 }

      -- OSPFv3 Neighbor Table

     hpicfOspfv3NbrTable OBJECT-TYPE
            SYNTAX          SEQUENCE OF HpicfOspfv3NbrEntry
            MAX-ACCESS      not-accessible
            STATUS          current
            DESCRIPTION "A table describing all neighbors of the
                         of the OSPFv3 router."
            REFERENCE
                "OSPF Version 2, Section 10 The Neighbor Data
                Structure"
            ::= {  hpicfOspfv3Objects 6 }

     hpicfOspfv3NbrEntry OBJECT-TYPE
            SYNTAX          HpicfOspfv3NbrEntry
            MAX-ACCESS      not-accessible
            STATUS          current
            DESCRIPTION "The information regarding a single neighbor."
            REFERENCE
                "OSPF Version 2, Section 10 The Neighbor Data
                Structure"
            AUGMENTS   {  ospfv3NbrEntry }
            ::= {  hpicfOspfv3NbrTable 1 }

        HpicfOspfv3NbrEntry ::= SEQUENCE {
             hpicfOspfv3NbrUpTime
                    Unsigned32,
             hpicfOspfv3NbrTimeToExpiry
                    Unsigned32,
             hpicfOspfv3NbrDataBaseSummary
                    Gauge32,
             hpicfOspfv3NbrLinkStateRequest
                    Gauge32,
             hpicfOspfv3NbrRestartState
                    INTEGER
            }

        hpicfOspfv3NbrUpTime OBJECT-TYPE
	         SYNTAX    	Unsigned32
	         MAX-ACCESS	read-only
	         STATUS	      current
	         DESCRIPTION "This object specifies the time duration in
                         seconds for which the adjacency with a
                         particular neighbor is active.
                         This should be a monotonically increasing timer
                         for the duration till the adjacency is active.
                         This counter should be reset on losing
                         and re-establishing an adjacency"
        ::= {hpicfOspfv3NbrEntry 1}

        hpicfOspfv3NbrTimeToExpiry OBJECT-TYPE
            SYNTAX      Unsigned32
	          MAX-ACCESS	read-only
	          STATUS      current
	          DESCRIPTION "This object specifies the time remaining for the
                          dead timer for the particular neighbor to expire.
                          This counter thus specifies the time in seconds
                          left for an adjacency to be brought down in case
                          no hello packet is received during that interval."
	     ::= {hpicfOspfv3NbrEntry 2}

        hpicfOspfv3NbrDataBaseSummary OBJECT-TYPE
            SYNTAX      Gauge32
            MAX-ACCESS  read-only
            STATUS      current
            DESCRIPTION "The number of Link State Advertisements (LSA)
                         sent in Database Description (DD)packet."
             ::= {hpicfOspfv3NbrEntry 3}

        hpicfOspfv3NbrLinkStateRequest OBJECT-TYPE
            SYNTAX      Gauge32
            MAX-ACCESS  read-only
            STATUS      current
            DESCRIPTION "The number of Link State Advertisements (LSA)
                         in link state request list."
             ::= {hpicfOspfv3NbrEntry 4}

        hpicfOspfv3NbrRestartState OBJECT-TYPE
            SYNTAX      INTEGER { normal(0),
                                  helper(1)
                                }
            MAX-ACCESS  read-only
            STATUS      current
            DESCRIPTION "Describes the Graceful Restart(GR) state.

                         normal(0) - Indicates normal status
                         helper(1) - Helper indicates the router is helping
                             another router which is currently in graceful
                             restart."
             ::= {hpicfOspfv3NbrEntry 5}

hpicfOspfv3IfStatsTable  OBJECT-TYPE
    SYNTAX      SEQUENCE OF HpicfOspfv3IfStatsEntry
    MAX-ACCESS  not-accessible
    STATUS      current
    DESCRIPTION "Table that contains OSPFv3 Interface traffic
                 specific statistics."
        ::= { hpicfOspfv3Objects 7 }

hpicfOspfv3IfStatsEntry OBJECT-TYPE
    SYNTAX      HpicfOspfv3IfStatsEntry
    MAX-ACCESS  not-accessible
    STATUS      current
    DESCRIPTION "A list of statistics counters maintained for an
                 OSPFv3 interface traffic information."
    INDEX       { ospfv3IfIndex,
                  ospfv3IfInstId
                }
    ::= { hpicfOspfv3IfStatsTable 1 }

HpicfOspfv3IfStatsEntry ::=
    SEQUENCE {
             hpicfOspfv3IfSentHelloPkt
                    Counter32,
             hpicfOspfv3IfSentDDPkt
                    Counter32,
             hpicfOspfv3IfSentLSRPkt
                    Counter32,
             hpicfOspfv3IfSentLSUPkt
                    Counter32,
             hpicfOspfv3IfSentLSAPkt
                    Counter32,
             hpicfOspfv3IfRcvdHelloPkt
                    Counter32,
             hpicfOspfv3IfRcvdDDPkt
                    Counter32,
             hpicfOspfv3IfRcvdLSRPkt
                    Counter32,
             hpicfOspfv3IfRcvdLSUPkt
                    Counter32,
             hpicfOspfv3IfRcvdLSAPkt
                    Counter32,
             hpicfOspfv3IfSentTotalErrorCount
                    Counter32,
             hpicfOspfv3IfRcvdTotalErrorCount
                    Counter32
    }

 hpicfOspfv3IfSentHelloPkt  OBJECT-TYPE
            SYNTAX          Counter32
            MAX-ACCESS      read-only
            STATUS          current
            DESCRIPTION "The number of OSPFv3 Hello packets sent on the
                         interface. This number is incremented each time
                         an OSPFv3 Hello packet is sent out of an
                         OSPFv3 enabled interface.
                         Discontinuities in the value of this counter can
                         occur at re-initialization of the management
                         system. The counters can be cleared for any
                         interface using 'clear ipv6 ospf3 statistics'
                         command"
           ::= { hpicfOspfv3IfStatsEntry 1 }

hpicfOspfv3IfSentDDPkt  OBJECT-TYPE
            SYNTAX          Counter32
            MAX-ACCESS      read-only
            STATUS          current
            DESCRIPTION "The number of Database Description packets
                         sent on the interface. This number is incremented each
                         time an OSPFv3 DD packet is sent out of an OSPFv3
                         enabled interface.
                         Discontinuities in the value of this counter
                         can occur at re-initialization of the management
                         system. The counters can be cleared for any
                         interface using 'clear ipv6 ospf3 statistics'
                         command"
           ::= { hpicfOspfv3IfStatsEntry 2 }

hpicfOspfv3IfSentLSRPkt  OBJECT-TYPE
            SYNTAX          Counter32
            MAX-ACCESS      read-only
            STATUS          current
            DESCRIPTION "The number of Link State Request packets sent on
                         the interface. This number is incremented each
                         time OSPFv3 LSR packet is sent out of an OSPFv3
                         enabled interface.
                         Discontinuities in the value of this counter
                         can occur at re-initialization of the management
                         system. The counters can be cleared for any
                         interface using 'clear ipv6 ospf3 statistics'
                         command"
           ::= { hpicfOspfv3IfStatsEntry 3 }

hpicfOspfv3IfSentLSUPkt  OBJECT-TYPE
            SYNTAX          Counter32
            MAX-ACCESS      read-only
            STATUS          current
            DESCRIPTION "The number of Link State Update packets sent on
                         the interface. This number is incremented each
                         time OSPFv3 LSU packet is sent out of an OSPFv3
                         enabled interface.
                         Discontinuities in the value of this counter
                         can occur at re-initialization of the management
                         system. The counters can be cleared for any
                         interface using 'clear ipv6 ospf3 statistics'
                         command."
           ::= { hpicfOspfv3IfStatsEntry 4 }

hpicfOspfv3IfSentLSAPkt  OBJECT-TYPE
            SYNTAX          Counter32
            MAX-ACCESS      read-only
            STATUS          current
            DESCRIPTION "The number of Link State Acknowledgement packet
                         sent on the interface. This number is
                         incremented each time OSPFv3 LS Ack packet is sent
                         out of an OSPFv3 enabled interface.
                         Discontinuities in the value of this counter
                         can occur at re-initialization of the management
                         system. The counters can be cleared for any
                         interface using 'clear ipv6 ospf3 statistics'
                         command."
           ::= { hpicfOspfv3IfStatsEntry 5 }

hpicfOspfv3IfRcvdHelloPkt  OBJECT-TYPE
            SYNTAX          Counter32
            MAX-ACCESS      read-only
            STATUS          current
            DESCRIPTION "The number of Hello packets received on the
                         interface. This number is incremented each time
                         a hello packet is received on OSPFv3 enabled
                         interface.
                         Discontinuities in the value of this counter
                         can occur at re-initialization of the management
                         system. The counters can be cleared for any
                         interface using 'clear ipv6 ospf3 statistics'
                         command"
           ::= { hpicfOspfv3IfStatsEntry 6 }

hpicfOspfv3IfRcvdDDPkt  OBJECT-TYPE
            SYNTAX          Counter32
            MAX-ACCESS      read-only
            STATUS          current
            DESCRIPTION "The number of Database Description packets
                         received on the interface. This number is
                         incremented each time a OSPFv3 DD packet is
                         received on OSPFv3 enabled interface.
                         Discontinuities in the value of this counter
                         can occur at re-initialization of the management
                         system. The counters can be cleared for any
                         interface using 'clear ipv6 ospf3 statistics'
                         command"
           ::= { hpicfOspfv3IfStatsEntry 7 }

hpicfOspfv3IfRcvdLSRPkt  OBJECT-TYPE
            SYNTAX          Counter32
            MAX-ACCESS      read-only
            STATUS          current
            DESCRIPTION "The number of Link State Request packets received
                         on the interface. This number is incremented each
                         time a OSPFv3 LSR packet is received on OSPFv3
                         enabled interface.
                         Discontinuities in the value of this counter
                         can occur at re-initialization of the management
                         system. The counters can be cleared for any
                         interface using 'clear ipv6 ospf3 statistics'
                         command"
           ::= { hpicfOspfv3IfStatsEntry 8 }

hpicfOspfv3IfRcvdLSUPkt  OBJECT-TYPE
            SYNTAX          Counter32
            MAX-ACCESS      read-only
            STATUS          current
            DESCRIPTION "The number of Link State Update packets received
                         on the interface. This number is incremented each
                         time an OSPFv3 LSU packet is received on OSPFv3
                         enabled interface.
                         Discontinuities in the value of this counter
                         can occur at re-initialization of the management
                         system. The counters can be cleared for any
                         interface using 'clear ipv6 ospf3 statistics'
                         command"
           ::= { hpicfOspfv3IfStatsEntry 9 }

hpicfOspfv3IfRcvdLSAPkt  OBJECT-TYPE
            SYNTAX          Counter32
            MAX-ACCESS      read-only
            STATUS          current
            DESCRIPTION "The number of Link State Acknowledgement packets
                         received on the interface.
                         This number is incremented each
                         time a OSPF LS Ack packet is received on OSPFv3
                         enabled interface.
                         Discontinuities in the value of this counter
                         can occur at re-initialization of the management
                         system. The counters can be cleared for any
                         interface using 'clear ipv6 ospf3 statistics'
                         command"
           ::= { hpicfOspfv3IfStatsEntry 10 }

hpicfOspfv3IfSentTotalErrorCount  OBJECT-TYPE
            SYNTAX          Counter32
            MAX-ACCESS      read-only
            STATUS          current
            DESCRIPTION "This refers to the number of erroneous packets
                         discarded on an OSPFv3 interface while sending
                         errors.
                         Discontinuities in the value of this counter
                         can occur at re-initialization of the management
                         system."
           ::= { hpicfOspfv3IfStatsEntry 11 }

hpicfOspfv3IfRcvdTotalErrorCount  OBJECT-TYPE
            SYNTAX          Counter32
            MAX-ACCESS      read-only
            STATUS          current
            DESCRIPTION "This refers to the number of erroneous packets
                         received on an OSPFv3 interface.
                         Discontinuities in the value of this counter
                         can occur at re-initialization of the management
                         system."
           ::= { hpicfOspfv3IfStatsEntry 12 }

hpicfOspfv3IfErrorTable  OBJECT-TYPE
    SYNTAX      SEQUENCE OF HpicfOspfv3IfErrorEntry
    MAX-ACCESS  not-accessible
    STATUS      current
    DESCRIPTION "Table that contains OSPFv3 Interface traffic specific
                 error information."
        ::= { hpicfOspfv3Objects 8 }

hpicfOspfv3IfErrorEntry OBJECT-TYPE
    SYNTAX      HpicfOspfv3IfErrorEntry
    MAX-ACCESS  not-accessible
    STATUS      current
    DESCRIPTION "A list of error counters maintained for an OSPFv3
                 interface."

    INDEX       { ospfv3IfIndex,
                  ospfv3IfInstId,
                  hpicfOspfv3IfErrorType }
    ::= { hpicfOspfv3IfErrorTable 1 }

HpicfOspfv3IfErrorEntry ::=
    SEQUENCE {
        hpicfOspfv3IfErrorType          Integer32,
        hpicfOspfv3IfErrorCount         Counter32
    }

hpicfOspfv3IfErrorType  OBJECT-TYPE
            SYNTAX          Integer32 (1..'FFFF'h)
            MAX-ACCESS      not-accessible
            STATUS          current
            DESCRIPTION "This refers to the type of errors in the OSPFv3
                         packet received on an OSPFv3 enabled interface."
        ::= { hpicfOspfv3IfErrorEntry 1 }

hpicfOspfv3IfErrorCount  OBJECT-TYPE
            SYNTAX          Counter32
            MAX-ACCESS      read-only
            STATUS          current
            DESCRIPTION "This refers to the number of erroneous packets
                         received on an OSPFv3 interface for each error
                         type.
                         Discontinuities in the value of this counter
                         can occur at re-initialization of the management
                         system. The counters can be cleared for any
                         interface using 'clear ipv6 ospf3 statistics'
                         command."
        ::= { hpicfOspfv3IfErrorEntry 2 }

 hpicfOspfv3IfClearStatsTable OBJECT-TYPE
    SYNTAX      SEQUENCE OF  HpicfOspfv3IfClearStatsEntry
    MAX-ACCESS  not-accessible
    STATUS      current
    DESCRIPTION "A list used to clear statistics information
                 maintained for an OSPFv3 interface."
        ::= { hpicfOspfv3Objects 9 }

hpicfOspfv3IfClearStatsEntry OBJECT-TYPE
    SYNTAX      HpicfOspfv3IfClearStatsEntry
    MAX-ACCESS  not-accessible
    STATUS      current
    DESCRIPTION "A list used to clear statistics information
                 maintained for an OSPFv3 interface."
    INDEX       { ospfv3IfIndex,
                  ospfv3IfInstId}
    ::= { hpicfOspfv3IfClearStatsTable 1 }

HpicfOspfv3IfClearStatsEntry ::=
    SEQUENCE {
        hpicfOspfv3ClearCounters TruthValue
    }

hpicfOspfv3ClearCounters  OBJECT-TYPE
    SYNTAX      TruthValue
    MAX-ACCESS  read-write
    STATUS      current
    DESCRIPTION "When this variable is set
                 to true for a given vlan interface, correspondiing
                 interface counters will be cleared. Read of this will
                 always be false."
    DEFVAL { false }
    ::= {hpicfOspfv3IfClearStatsEntry 1 }

hpicfOspfv3SpfTable  OBJECT-TYPE
    SYNTAX      SEQUENCE OF HpicfOspfv3SpfEntry
    MAX-ACCESS  not-accessible
    STATUS      current
    DESCRIPTION "Table that contains OSPFv3 SPF execution details."
        ::= { hpicfOspfv3Objects 10 }

hpicfOspfv3SpfEntry OBJECT-TYPE
    SYNTAX      HpicfOspfv3SpfEntry
    MAX-ACCESS  not-accessible
    STATUS      current
    DESCRIPTION "A list of OSPFv3 SPF algorithm execution details."

    INDEX       { hpicfOspfv3SpfIndex}
    ::= { hpicfOspfv3SpfTable 1 }

HpicfOspfv3SpfEntry ::=
    SEQUENCE {
        hpicfOspfv3SpfIndex       Unsigned32,
        hpicfOspfv3SpfReason      Unsigned32
    }

hpicfOspfv3SpfIndex   OBJECT-TYPE
            SYNTAX          Unsigned32
            MAX-ACCESS      not-accessible
            STATUS          current
            DESCRIPTION "The index in spf table. This can range from 1 to 100
                         as only last hundred SPF run's reasons will be saved."
            ::= {hpicfOspfv3SpfEntry 1}

hpicfOspfv3SpfReason  OBJECT-TYPE
            SYNTAX          Unsigned32
            MAX-ACCESS      read-only
            STATUS          current
            DESCRIPTION "The hpicfOspfv3SpfReason refers to the reasons for
                         scheduling an SPF run. The Reasons could be OSPFv3
                         initialization, adding/deleting interface or link state
                         update received."
        ::= { hpicfOspfv3SpfEntry 2 }


   hpicfOspfv3LogTable OBJECT-TYPE
        SYNTAX      SEQUENCE OF HpicfOspfv3LogEntry
        MAX-ACCESS  not-accessible
        STATUS      current
        DESCRIPTION "A table containing the configuration parameters
                     for OSPFv3 event logging."
        ::= { hpicfOspfv3Objects 11}

    hpicfOspfv3LogEntry OBJECT-TYPE
        SYNTAX      HpicfOspfv3LogEntry
        MAX-ACCESS  not-accessible
        STATUS      current
        DESCRIPTION "The configuration parameters for OSPFv3
                     event log entry."

        INDEX       { hpicfOspfv3LogType }
        ::= { hpicfOspfv3LogTable 1 }

    HpicfOspfv3LogEntry ::=
        SEQUENCE {
            hpicfOspfv3LogType               HpicfOspfLogType,
            hpicfOspfv3LogAction             HpicfOspfLogAction
        }

    hpicfOspfv3LogType OBJECT-TYPE
        SYNTAX      HpicfOspfLogType
        MAX-ACCESS  not-accessible
        STATUS      current
        DESCRIPTION "The type of the event log in OSPFv3
                     routing protocol ."
        ::= { hpicfOspfv3LogEntry 1 }

    hpicfOspfv3LogAction OBJECT-TYPE
        SYNTAX      HpicfOspfLogAction
        MAX-ACCESS  read-write
        STATUS      current
        DESCRIPTION "The mode of OSPFv3 event logging. If the
                     OSPFv3 log type is set to
                     neighborAdjacencyChanges, then meaning of
                     this field is as follows:
                     If enabled, it logs only the adjacency
                     state transitions to final states.
                     If enabledWithDetail option, it logs all
                     the state transitions and other events and
                     error conditions related to adjacency.
                     If disabled, none of the adjacency related
                     events are logged."
           ::= { hpicfOspfv3LogEntry 2 }


    -- Router LSA expansion table

     hpicfOspfv3RouterLSATable OBJECT-TYPE
            SYNTAX          SEQUENCE OF HpicfOspfv3RouterLSAEntry
            MAX-ACCESS      not-accessible
            STATUS          current
            DESCRIPTION "This table represents details advertised in router LSA
                         in addition to area LSDB table."
            REFERENCE
                "OSPF Version 3, Appendix 4.3 Router-LSAs, rfc 5340"
            ::= {  hpicfOspfv3Objects 12 }

    hpicfOspfv3RouterLSAEntry OBJECT-TYPE
            SYNTAX          HpicfOspfv3RouterLSAEntry
            MAX-ACCESS      not-accessible
            STATUS          current
            DESCRIPTION "A single Area-Scope Link State Advertisement."
            INDEX           { ospfv3AreaLsdbAreaId,
                              ospfv3AreaLsdbType,
                              ospfv3AreaLsdbRouterId,
                              ospfv3AreaLsdbLsid,
                              hpicfOspfv3RouterLSANbrIfId,
                              hpicfOspfv3RouterLSANbrRtrId}
            ::= { hpicfOspfv3RouterLSATable 1 }

    HpicfOspfv3RouterLSAEntry ::= SEQUENCE {
             hpicfOspfv3RouterLSANbrIfId
                    Unsigned32,
             hpicfOspfv3RouterLSANbrRtrId
                    Ospfv3RouterIdTC,
             hpicfOspfv3RouterLSAIfType
                    Unsigned32,
             hpicfOspfv3RouterLSAMetric
                    Unsigned32,
             hpicfOspfv3RouterLSAIfId
                    Unsigned32
            }

     hpicfOspfv3RouterLSANbrIfId OBJECT-TYPE
            SYNTAX          Unsigned32
            MAX-ACCESS      not-accessible
            STATUS          current
            DESCRIPTION "The Interface Id of the neighbor."
            ::= {  hpicfOspfv3RouterLSAEntry 1 }

     hpicfOspfv3RouterLSANbrRtrId OBJECT-TYPE
            SYNTAX          Ospfv3RouterIdTC
            MAX-ACCESS      not-accessible
            STATUS          current
            DESCRIPTION "The Router ID the of the neighbor router."
            ::= {  hpicfOspfv3RouterLSAEntry 2 }

    hpicfOspfv3RouterLSAIfType OBJECT-TYPE
            SYNTAX          Unsigned32
            MAX-ACCESS      read-only
            STATUS          current
            DESCRIPTION
             "The kind of interface being described. One of the following:
              Type            Description
             ---------------------------------------------------
               1           Point-to-point connection to another router
               2           Connection to a transit network
               3           Reserved
               4           Virtual link ."

            ::= {  hpicfOspfv3RouterLSAEntry 3 }

     hpicfOspfv3RouterLSAMetric OBJECT-TYPE
            SYNTAX          Unsigned32 (0..'FFFFFFFF'h)
            MAX-ACCESS      read-only
            STATUS          current
            DESCRIPTION "The cost of using this router interface
                         for outbound traffic."
            ::= {  hpicfOspfv3RouterLSAEntry 4 }

     hpicfOspfv3RouterLSAIfId OBJECT-TYPE
            SYNTAX          Unsigned32 (0..'FFFFFFFF'h)
            MAX-ACCESS      read-only
            STATUS          current
            DESCRIPTION "The Interface ID assigned to the interface
                         being described."
            ::= {  hpicfOspfv3RouterLSAEntry 5 }

    -- Network LSA expansion table

    hpicfOspfv3NetworkLSATable OBJECT-TYPE
            SYNTAX          SEQUENCE OF HpicfOspfv3NetworkLSAEntry
            MAX-ACCESS      not-accessible
            STATUS          current
            DESCRIPTION "This table represents details advertised
                         in a Network LSA in addition to area LSDB table."
            REFERENCE
                "OSPF Version 3, Appendix 4.4 Network-LSAs"
            ::= {  hpicfOspfv3Objects 13 }

    hpicfOspfv3NetworkLSAEntry OBJECT-TYPE
            SYNTAX          HpicfOspfv3NetworkLSAEntry
            MAX-ACCESS      not-accessible
            STATUS          current
            DESCRIPTION "A single Area-Scope Link State Advertisement."
            INDEX           { ospfv3AreaLsdbAreaId,
                              ospfv3AreaLsdbType,
                              ospfv3AreaLsdbRouterId,
                              ospfv3AreaLsdbLsid,
                              hpicfOspfv3NetworkLSASeqNum }
            ::= { hpicfOspfv3NetworkLSATable 1 }

    HpicfOspfv3NetworkLSAEntry ::= SEQUENCE {
             hpicfOspfv3NetworkLSASeqNum
                    Unsigned32,
             hpicfOspfv3NetworkLSAAttachedRouter
                    Ospfv3RouterIdTC
            }

    hpicfOspfv3NetworkLSASeqNum OBJECT-TYPE
            SYNTAX          Unsigned32
            MAX-ACCESS      not-accessible
            STATUS          current
            DESCRIPTION "The 32-bit LSA sequence number."
            ::= { hpicfOspfv3NetworkLSAEntry 1 }

    hpicfOspfv3NetworkLSAAttachedRouter OBJECT-TYPE
            SYNTAX          Ospfv3RouterIdTC
            MAX-ACCESS      read-only
            STATUS          current
            DESCRIPTION "The 32-bit Router identifier of the attached Router."
            ::= { hpicfOspfv3NetworkLSAEntry 2 }

    -- IntraAreaPrefix LSA expansion table

    hpicfOspfv3IntraAPLSATable OBJECT-TYPE
            SYNTAX          SEQUENCE OF HpicfOspfv3IntraAPLSAEntry
            MAX-ACCESS      not-accessible
            STATUS          current
            DESCRIPTION "This table represents details advertised in Intra
                         AP LSA in addition to area LSDB table."
            REFERENCE
                "OSPF Version 3, Appendix 4.6 Intra-Area-Prefix-LSAs"
            ::= {  hpicfOspfv3Objects 14 }

    hpicfOspfv3IntraAPLSAEntry OBJECT-TYPE
            SYNTAX          HpicfOspfv3IntraAPLSAEntry
            MAX-ACCESS      not-accessible
            STATUS          current
            DESCRIPTION "A single Area-Scope Link State Advertisement."
            INDEX           { ospfv3AreaLsdbAreaId,
                              ospfv3AreaLsdbType,
                              ospfv3AreaLsdbRouterId,
                              ospfv3AreaLsdbLsid,
                              hpicfOspfv3IntraAPAddrPrefix,
                              hpicfOspfv3IntraAPPrefixLength }
            ::= {  hpicfOspfv3IntraAPLSATable 1 }

    HpicfOspfv3IntraAPLSAEntry ::= SEQUENCE {
             hpicfOspfv3IntraAPAddrPrefix
                    InetAddressIPv6,
             hpicfOspfv3IntraAPPrefixLength
                    Unsigned32,
             hpicfOspfv3IntraAPPrefixOptions
                    Unsigned32,
             hpicfOspfv3IntraAPMetric
                    Metric
            }

    hpicfOspfv3IntraAPAddrPrefix OBJECT-TYPE
            SYNTAX          InetAddressIPv6
            MAX-ACCESS      not-accessible
            STATUS          current
            DESCRIPTION "The advertised 16-byte Address Prefix."
            ::= {  hpicfOspfv3IntraAPLSAEntry 1 }

    hpicfOspfv3IntraAPPrefixLength OBJECT-TYPE
            SYNTAX          Unsigned32
            MAX-ACCESS      not-accessible
            STATUS          current
            DESCRIPTION "The Prefix Length of the Address Prefix."
            ::= {  hpicfOspfv3IntraAPLSAEntry 2 }

    hpicfOspfv3IntraAPPrefixOptions OBJECT-TYPE
            SYNTAX          Unsigned32
            MAX-ACCESS      read-only
            STATUS          current
            DESCRIPTION "The Prefix Options associated with the Address Prefix."
            ::= {  hpicfOspfv3IntraAPLSAEntry 3 }

    hpicfOspfv3IntraAPMetric OBJECT-TYPE
            SYNTAX          Metric
            MAX-ACCESS      read-only
            STATUS          current
            DESCRIPTION "The Cost associated with the Address Prefix."
            ::= {  hpicfOspfv3IntraAPLSAEntry 4 }

    -- Link LSA expansion table

     hpicfOspfv3LinkLSATable OBJECT-TYPE
            SYNTAX          SEQUENCE OF HpicfOspfv3LinkLSAEntry
            MAX-ACCESS      not-accessible
            STATUS          current
            DESCRIPTION "This table represents details advertised
                         in link LSA in addition to link LSDB table."
            ::= {  hpicfOspfv3Objects 15 }

    hpicfOspfv3LinkLSAEntry OBJECT-TYPE
            SYNTAX          HpicfOspfv3LinkLSAEntry
            MAX-ACCESS      not-accessible
            STATUS          current
            DESCRIPTION "A single Link-Scope Link State Advertisement."
            INDEX           {  ospfv3LinkLsdbIfIndex,
                               ospfv3LinkLsdbIfInstId,
                               ospfv3LinkLsdbType,
                               ospfv3LinkLsdbRouterId,
                               ospfv3LinkLsdbLsid,
                               hpicfOspfv3LinkAddrPrefix,
                               hpicfOspfv3LinkPrefixLength }
            ::= {  hpicfOspfv3LinkLSATable 1 }


    HpicfOspfv3LinkLSAEntry ::= SEQUENCE {
             hpicfOspfv3LinkAddrPrefix
                    InetAddressIPv6,
             hpicfOspfv3LinkPrefixLength
                    Unsigned32,
             hpicfOspfv3LinkPrefixOptions
                    Unsigned32
            }

     hpicfOspfv3LinkAddrPrefix OBJECT-TYPE
            SYNTAX          InetAddressIPv6
            MAX-ACCESS      not-accessible
            STATUS          current
            DESCRIPTION "The address prefix of link advertised
                         in link LSA."
            ::= {  hpicfOspfv3LinkLSAEntry 1 }

    hpicfOspfv3LinkPrefixLength OBJECT-TYPE
            SYNTAX          Unsigned32
            MAX-ACCESS      not-accessible
            STATUS          current
            DESCRIPTION "The Prefix Length of the Address Prefix."
            ::= {  hpicfOspfv3LinkLSAEntry 2 }

     hpicfOspfv3LinkPrefixOptions OBJECT-TYPE
            SYNTAX          Unsigned32 (0..'FFFFFFFF'h)
            MAX-ACCESS      read-only
            STATUS          current
            DESCRIPTION "The Prefix Options associated with the Address Prefix."
            ::= {  hpicfOspfv3LinkLSAEntry 3 }



    --  Traps
       hpicfOspfv3Trap OBJECT IDENTIFIER  ::= { hpicfOspfv3Objects 16}
       hpicfOspfv3Traps OBJECT IDENTIFIER ::= { hpicfOspfv3Trap 0 }
       hpicfOspfv3TrapControl OBJECT IDENTIFIER ::= { hpicfOspfv3Trap 1 }


       hpicfOspfv3SetTrap  OBJECT-TYPE
          SYNTAX      OCTET STRING (SIZE(4))
          MAX-ACCESS  read-write
          STATUS      current
          DESCRIPTION "A four-octet string serving as a bit map for
                       the trap events defined by the OSPFv3 traps. This
                       object is used to enable or disable  specific
                       OSPFv3 traps where a 1 in the bit field represents
                       enabled. The right-most bit  (least significant)
                       represents trap 0.
                 Trap Name                   BitMap
              ----------------------------------------
              OSPFV3_IF_STATE_CHANGE         0x00001
              OSPFV3_VIRT_IF_STATE_CHANGE    0x00002
              OSPFV3_NBR_STATE_CHANGE        0x00004
              OSPFV3_VIRT_NBR_STATE_CHANGE   0x00008
              OSPFV3_INTF_CONFIG_ERROR       0x00010
              OSPFV3_VIRT_INTF_CONFIG_ERROR  0x00020
              OSPFV3_INTF_RCV_BAD_PKT        0x00040
              OSPFV3_VIRT_INTF_RCV_BAD_PKT   0x00080
              OSPFV3_RST_STATUS              0x20000
              OSPFV3_NBR_RST_HELP_STATUS     0x40000
              OSPFV3_VIRT_NBR_RST_HELP_STAT  0x80000
              OSPFV3_ALL_TRAPS               0xE00FF"
          ::= { hpicfOspfv3TrapControl 1 }


    -- hpicfOspfv3AreaAggregateTable

    hpicfOspfv3AreaAggregateTable OBJECT-TYPE
        SYNTAX      SEQUENCE OF HpicfOspfv3AreaAggregateEntry
        MAX-ACCESS  not-accessible
        STATUS      current
        DESCRIPTION "HP proprietary extensions to ospfv3AreaAggregateTable"
        ::= { hpicfOspfv3Objects 19 }

    hpicfOspfv3AreaAggregateEntry OBJECT-TYPE
        SYNTAX      HpicfOspfv3AreaAggregateEntry
        MAX-ACCESS  not-accessible
        STATUS      current
        DESCRIPTION "Each entry is extension of ospfv3AreaAggregateEntry"
        AUGMENTS    { ospfv3AreaAggregateEntry }
        ::= { hpicfOspfv3AreaAggregateTable 1 }

    HpicfOspfv3AreaAggregateEntry ::=
        SEQUENCE {
            hpicfOspfv3AreaAggregateCost BigMetric
        }

    hpicfOspfv3AreaAggregateCost OBJECT-TYPE
        SYNTAX       BigMetric
        MAX-ACCESS   read-create
        STATUS       current
        DESCRIPTION "Manually configured cost of the summary advertisement.
                     A value of 0 indicates that the cost
                     calculated by the OSPF standard should be used.
                     Valid costs range from 1-16777215"
        DEFVAL { 0 }
        ::= { hpicfOspfv3AreaAggregateEntry 1 }

    -- hpicfOspfv3AreaTable

    hpicfOspfv3AreaTable OBJECT-TYPE
           SYNTAX            SEQUENCE OF HpicfOspfv3AreaEntry
           MAX-ACCESS        not-accessible
           STATUS            current
           DESCRIPTION "This table describes Ospfv3 area."
           ::= { hpicfOspfv3Objects 17 }

    hpicfOspfv3AreaEntry OBJECT-TYPE
           SYNTAX            HpicfOspfv3AreaEntry
           MAX-ACCESS        not-accessible
           STATUS            current
           DESCRIPTION "The object describes Ospfv3 area."
           AUGMENTS   {ospfv3AreaEntry }
           ::= { hpicfOspfv3AreaTable 1 }

    HpicfOspfv3AreaEntry ::= SEQUENCE {
             hpicfOspfv3AreaNbrDownCount
                    Counter32,
             hpicfOspfv3AreaNbrAttemptCount
                    Counter32,
             hpicfOspfv3AreaNbrInitCount
                    Counter32,
             hpicfOspfv3AreaNbr2wayCount
                    Counter32,
             hpicfOspfv3AreaNbrExstartCount
                    Counter32,
             hpicfOspfv3AreaNbrExchangeCount
                    Counter32,
             hpicfOspfv3AreaNbrLoadingCount
                    Counter32,
             hpicfOspfv3AreaNbrFullCount
                    Counter32,
             hpicfOspfv3AreaInterfaceCount
                    Counter32,
             hpicfOspfv3AreaScopeUnknownLsaCount
                    Counter32
    }

   hpicfOspfv3AreaNbrDownCount OBJECT-TYPE
       SYNTAX       Counter32
       MAX-ACCESS   read-only
       STATUS       current
       DESCRIPTION "This object indicates the number of neighbor routers
                    in this area that are in DOWN state."
       ::= { hpicfOspfv3AreaEntry 8 }

   hpicfOspfv3AreaNbrAttemptCount OBJECT-TYPE
       SYNTAX       Counter32
       MAX-ACCESS   read-only
       STATUS       current
       DESCRIPTION "This object indicates the number of neighbor routers
                    in this area that are in ATTEMPT state."
       ::= { hpicfOspfv3AreaEntry 9 }

   hpicfOspfv3AreaNbrInitCount OBJECT-TYPE
       SYNTAX       Counter32
       MAX-ACCESS   read-only
       STATUS       current
       DESCRIPTION "This object indicates the number of neighbor routers
                    in this area that are in INIT state."
       ::= { hpicfOspfv3AreaEntry 10 }

   hpicfOspfv3AreaNbr2wayCount OBJECT-TYPE
   SYNTAX       Counter32
   MAX-ACCESS   read-only
   STATUS       current
   DESCRIPTION "This object indicates the number of neighbor routers
                in this area that are in TWO WAY state."
   ::= { hpicfOspfv3AreaEntry 11 }

   hpicfOspfv3AreaNbrExstartCount OBJECT-TYPE
   SYNTAX       Counter32
   MAX-ACCESS   read-only
   STATUS       current
   DESCRIPTION "This object indicates the number of neighbor routers
                in this area that are in EX-START state."
   ::= { hpicfOspfv3AreaEntry 12 }

   hpicfOspfv3AreaNbrExchangeCount OBJECT-TYPE
   SYNTAX       Counter32
   MAX-ACCESS   read-only
   STATUS       current
   DESCRIPTION "This object indicates the number of neighbor routers
                in this area that are in EXCHANGE state."
   ::= { hpicfOspfv3AreaEntry 13 }

   hpicfOspfv3AreaNbrLoadingCount OBJECT-TYPE
   SYNTAX       Counter32
   MAX-ACCESS   read-only
   STATUS       current
   DESCRIPTION "This object indicates the number of neighbor routers
                in this area that are in LOADING state."
   ::= { hpicfOspfv3AreaEntry 14 }

   hpicfOspfv3AreaNbrFullCount OBJECT-TYPE
   SYNTAX       Counter32
   MAX-ACCESS   read-only
   STATUS       current
   DESCRIPTION "This object indicates the number of neighbor routers
                in this area that are in FULL state."
   ::= { hpicfOspfv3AreaEntry 15 }

   hpicfOspfv3AreaInterfaceCount OBJECT-TYPE
   SYNTAX       Counter32
   MAX-ACCESS   read-only
   STATUS       current
   DESCRIPTION "This object indicates the total number of
                OSPFv3 interfaces in this area."
   ::= { hpicfOspfv3AreaEntry 16 }

   hpicfOspfv3AreaScopeUnknownLsaCount OBJECT-TYPE
   SYNTAX          Counter32
   MAX-ACCESS      read-only
   STATUS          current
   DESCRIPTION "The total number of area-scope unknown link state
                advertisements in this area's link state
                database."
   DEFVAL { 0 }
   ::= { hpicfOspfv3AreaEntry 17 }

         --area lsdb statistics table

      hpicfOspfv3AreaLsdbStatsTable  OBJECT-TYPE
      SYNTAX      SEQUENCE OF HpicfOspfv3AreaLsdbStatsEntry
      MAX-ACCESS  not-accessible
      STATUS      current
      DESCRIPTION "Table that contains OSPFv3 area link state database
                   statistics specific information."
      ::= { hpicfOspfv3Objects 20 }

      hpicfOspfv3AreaLsdbStatsEntry OBJECT-TYPE
      SYNTAX      HpicfOspfv3AreaLsdbStatsEntry
      MAX-ACCESS  not-accessible
      STATUS      current
      DESCRIPTION "A list of statistics counters maintained for an OSPFv3
                   area link state database."
      AUGMENTS  { ospfv3AreaEntry }
    ::= { hpicfOspfv3AreaLsdbStatsTable 1 }

    HpicfOspfv3AreaLsdbStatsEntry ::=
        SEQUENCE {
                        hpicfOspfv3AreaLsdbStatRtrLsaCnt
                               Counter32,
                        hpicfOspfv3AreaLsdbStatNwLsaCnt
                               Counter32,
                        hpicfOspfv3AreaLsdbStatInterPreLsaCnt
                               Counter32,
                        hpicfOspfv3AreaLsdbStatInterRtrLsaCnt
                               Counter32,
                        hpicfOspfv3AreaLsdbStatIntraPreLsaCnt
                               Counter32
                 }

     hpicfOspfv3AreaLsdbStatRtrLsaCnt OBJECT-TYPE
     SYNTAX          Counter32
     MAX-ACCESS      read-only
     STATUS          current
     DESCRIPTION "This object indicates number of
                  router LSA per area."
     DEFVAL { 0 }
     ::= { hpicfOspfv3AreaLsdbStatsEntry 1 }

     hpicfOspfv3AreaLsdbStatNwLsaCnt OBJECT-TYPE
     SYNTAX          Counter32
     MAX-ACCESS      read-only
     STATUS          current
     DESCRIPTION "This object indicates number of
                  network LSA per area."
     DEFVAL { 0 }
     ::= { hpicfOspfv3AreaLsdbStatsEntry 2 }

     hpicfOspfv3AreaLsdbStatInterPreLsaCnt OBJECT-TYPE
     SYNTAX          Counter32
     MAX-ACCESS      read-only
     STATUS          current
     DESCRIPTION "This object indicates number of
                  inter-area prefix LSA per area."
     DEFVAL { 0 }
     ::= { hpicfOspfv3AreaLsdbStatsEntry 3 }

     hpicfOspfv3AreaLsdbStatInterRtrLsaCnt OBJECT-TYPE
     SYNTAX          Counter32
     MAX-ACCESS      read-only
     STATUS          current
     DESCRIPTION "This object indicates number of
                  inter-area router LSA per area."
     DEFVAL { 0 }
     ::= { hpicfOspfv3AreaLsdbStatsEntry 4 }

     hpicfOspfv3AreaLsdbStatIntraPreLsaCnt OBJECT-TYPE
     SYNTAX          Counter32
     MAX-ACCESS      read-only
     STATUS          current
     DESCRIPTION "This object indicates number of
                  intra-area prefix LSA per area."
     DEFVAL { 0 }
     ::= { hpicfOspfv3AreaLsdbStatsEntry 5 }

      --Distribution List table
    hpicfOspfv3DistributeListTable OBJECT-TYPE
        SYNTAX      SEQUENCE OF HpicfOspfv3DistributeListEntry
        MAX-ACCESS  not-accessible
        STATUS      current
        DESCRIPTION "A table of route prefixes for filtering out
                    intra-area routes that OSPFv3 should not install into
                    local routing table.  Any route that is contained by
                    a range in this table (in other words, has a longer mask
                    than that specified by hpicfOspfv3DistributeListPrefixLength
                    and where the route destination ANDed with the
                    hpicfOspfv3DistributeListPrefixLength is equal to
                    hpicfOspfv3DistributeListAddr) will not be
                    installed into FIB by OSPFv3."
        ::= { hpicfOspfv3Objects 21 }

    hpicfOspfv3DistributeListEntry OBJECT-TYPE
        SYNTAX      HpicfOspfv3DistributeListEntry
        MAX-ACCESS  not-accessible
        STATUS      current
        DESCRIPTION "A single entry in the table. Any intra-area route,
                    which is contained within the specified range will not
                    be installed into FIB by OSPFv3.  Entries in this
                    table are created dynamically using the
                    hpicfOspfv3DistributeListStatus object."
        INDEX       { hpicfOspfv3DistributeListAddr,
                      hpicfOspfv3DistributeListPrefixLength }
        ::= { hpicfOspfv3DistributeListTable 1 }

    HpicfOspfv3DistributeListEntry ::=
        SEQUENCE {
            hpicfOspfv3DistributeListAddr      InetAddressIPv6,
            hpicfOspfv3DistributeListPrefixLength      InetAddressPrefixLength,
            hpicfOspfv3DistributeListSeqNum    Unsigned32,
            hpicfOspfv3DistributeListStatus    RowStatus
        }

    hpicfOspfv3DistributeListAddr OBJECT-TYPE
        SYNTAX      InetAddressIPv6
        MAX-ACCESS  not-accessible
        STATUS      current
        DESCRIPTION "The IP address of the range of route entries
                    to exclude from installing into FIB by OSPFv3."
        ::= { hpicfOspfv3DistributeListEntry 1 }

    hpicfOspfv3DistributeListPrefixLength OBJECT-TYPE
        SYNTAX      InetAddressPrefixLength
        MAX-ACCESS  not-accessible
        STATUS      current
        DESCRIPTION "The mask for the range of route entries to
                     exclude from installing into FIB by OSPFv3."
        ::= { hpicfOspfv3DistributeListEntry 2 }

    hpicfOspfv3DistributeListSeqNum OBJECT-TYPE
        SYNTAX      Unsigned32
        MAX-ACCESS  read-only
        STATUS      current
        DESCRIPTION "The sequence number of this entry."
        ::= {hpicfOspfv3DistributeListEntry 3 }

    hpicfOspfv3DistributeListStatus OBJECT-TYPE
        SYNTAX      RowStatus
        MAX-ACCESS  read-create
        STATUS      current
        DESCRIPTION "The status of this entry."
        ::= { hpicfOspfv3DistributeListEntry 4 }

    -- conformance information

     hpicfOspfv3Groups      OBJECT IDENTIFIER ::= {  hpicfOspfv3Conformance 1 }
     hpicfOspfv3Compliances OBJECT IDENTIFIER ::= {  hpicfOspfv3Conformance 2 }

    -- compliance statements

      hpicfOspfv3Compliance MODULE-COMPLIANCE
            STATUS          deprecated
            DESCRIPTION     "The compliance statement"
            MODULE          -- this module
            MANDATORY-GROUPS {
                             hpicfOspfv3BasicGroup,
                             hpicfOspfv3IfGroup1,
                             hpicfOspfv3NbrGroup1,
                             hpicfOspfv3AreaGroup
                             }

            GROUP            hpicfOspfv3AsLsdbGroup
            DESCRIPTION
                "This group is required for OSPFv3 systems that
                 display their AS-scope link state database."

            GROUP            hpicfOspfv3AreaLsdbGroup
            DESCRIPTION
                "This group is required for OSPFv3 systems that
                 display their Area-scope link state database."

            GROUP            hpicfOspfv3LinkLsdbGroup
            DESCRIPTION
                "This group is required for OSPFv3 systems that
                display their Link-scope link state database
                for non-virtual interfaces."

            GROUP            hpicfOspfv3StatisticGroup1
            DESCRIPTION
                "This group is required for OSPFv3 interface and SPF statistics."

            GROUP            hpicfOspfv3LogGroup
            DESCRIPTION
                "This group is required to support logging of
                 OSPFv3 adjacency related events."

            GROUP            hpicfOspfv3TrapControlGroup
            DESCRIPTION
                "This group is required to control the
                 hpicfOspfv3Traps."


            GROUP            hpicfOspfv3AreaLsdbStatsGroup
            DESCRIPTION
                 "This group is for area lsdb statistics."
            ::= {  hpicfOspfv3Compliances 1 }

      hpicfOspfv3Compliance2 MODULE-COMPLIANCE
            STATUS          current
            DESCRIPTION     "The compliance statement"
            MODULE          -- this module
            MANDATORY-GROUPS {
                             hpicfOspfv3BasicGroup,
                             hpicfOspfv3IfGroup1,
                             hpicfOspfv3NbrGroup1,
                             hpicfOspfv3AreaGroup
                             }

            GROUP            hpicfOspfv3AsLsdbGroup
            DESCRIPTION
                "This group is required for OSPFv3 systems that
                 display their AS-scope link state database."

            GROUP            hpicfOspfv3AreaLsdbGroup
            DESCRIPTION
                "This group is required for OSPFv3 systems that
                 display their Area-scope link state database."

            GROUP            hpicfOspfv3LinkLsdbGroup
            DESCRIPTION
                "This group is required for OSPFv3 systems that
                display their Link-scope link state database
                for non-virtual interfaces."

            GROUP            hpicfOspfv3StatisticGroup1
            DESCRIPTION
                "This group is required for OSPFv3 interface and SPF statistics."

            GROUP            hpicfOspfv3LogGroup
            DESCRIPTION
                "This group is required to support logging of
                 OSPFv3 adjacency related events."

            GROUP            hpicfOspfv3TrapControlGroup
            DESCRIPTION
                "This group is required to control the
                 hpicfOspfv3Traps."


            GROUP            hpicfOspfv3AreaLsdbStatsGroup
            DESCRIPTION
                 "This group is for area lsdb statistics."

            GROUP            hpicfOspfv3MetricGroup
            DESCRIPTION
                "The flags in this group will identify manual or
                 global configuration of ospfv3 cost."

            GROUP        hpicfOspfv3DistributeListGroup
            DESCRIPTION
                "This group is mandatory for systems
                 that support OSPFv3 intra-area routes."

            ::= {  hpicfOspfv3Compliances 2 }

    -- units of conformance

     hpicfOspfv3BasicGroup OBJECT-GROUP
            OBJECTS         {
                             hpicfOspfv3DefaultImportMetric,
                             hpicfOspfv3DefaultImportMetricType,
                             hpicfOspfv3ReferenceCost,
                             hpicfOspfv3IntraAreaDistance,
                             hpicfOspfv3InterAreaDistance,
                             hpicfOspfv3ExternalDistance,
                             hpicfOspfv3SpfThrottleStartInterval,
                             hpicfOspfv3SpfThrottleWaitInterval,
                             hpicfOspfv3SpfThrottleMaxWaitTime,
                             hpicfOspfv3SpfThrottleCurrentSpfInterval,
                             hpicfOspfv3AreaAggregateCost,
                             hpicfOspfv3AreaCount,
                             hpicfOspfv3RestartHelper,
                             hpicfOspfv3ASscopeUnknownLsaCount,
                             hpicfOspfv3LinkLsdbStatLinkLsa,
                             hpicfOspfv3TotalUnknownLsa
                            }
            STATUS          current
            DESCRIPTION
                "These objects are used for managing/monitoring
                OSPFv3 global parameters."
            ::= {  hpicfOspfv3Groups 1 }

     hpicfOspfv3AsLsdbGroup OBJECT-GROUP
            OBJECTS         {
                             hpicfOspfv3AsLsdbEFTFlags,
                             hpicfOspfv3AsLsdbMetric,
                             hpicfOspfv3AsLsdbPrefixLength,
                             hpicfOspfv3AsLsdbPrefixOptions,
                             hpicfOspfv3AsLsdbRefLsType,
                             hpicfOspfv3AsLsdbAddrPrefix,
                             hpicfOspfv3AsLsdbFwdingAddress,
                             hpicfOspfv3AsLsdbExtRouteTags,
                             hpicfOspfv3AsLsdbRefLsId,
                             hpicfOspfv3AsLsdbLsaLength

                            }
            STATUS          current
            DESCRIPTION
                "These objects are used for OSPFv3 systems
                that display their AS-scope link state database."
            ::= {  hpicfOspfv3Groups 2 }

     hpicfOspfv3AreaLsdbGroup OBJECT-GROUP
            OBJECTS         {
                             hpicfOspfv3AreaLsdbRtrCapBits,
                             hpicfOspfv3AreaLsdbOptions,
                             hpicfOspfv3AreaLsdbMetric,
                             hpicfOspfv3AreaLsdbPrefixLength,
                             hpicfOspfv3AreaLsdbPrefixOptions,
                             hpicfOspfv3AreaLsdbAddrPrefix,
                             hpicfOspfv3AreaLsdbDstRtrId,
                             hpicfOspfv3AreaLsdbNumPrefixes,
                             hpicfOspfv3AreaLsdbRefLsType,
                             hpicfOspfv3AreaLsdbRefLsId,
                             hpicfOspfv3AreaLsdbRefAdvRtrId,
                             hpicfOspfv3AreaLsdbEFTFlags,
                             hpicfOspfv3AreaLsdbFwdingAddress,
                             hpicfOspfv3AreaLsdbExtRouteTags,
                             hpicfOspfv3RouterLSAIfType,
                             hpicfOspfv3RouterLSAMetric,
                             hpicfOspfv3RouterLSAIfId,
                             hpicfOspfv3NetworkLSAAttachedRouter,
                             hpicfOspfv3IntraAPPrefixOptions,
                             hpicfOspfv3IntraAPMetric,
                             hpicfOspfv3AreaLsdbLsaLength,
                             hpicfOspfv3AreaLsdbLinks
                            }
            STATUS          current
            DESCRIPTION
                "These objects are used for OSPFv3 systems
                that display their Area-scope link state database."
            ::= {  hpicfOspfv3Groups 3 }

     hpicfOspfv3LinkLsdbGroup OBJECT-GROUP
            OBJECTS         {
                             hpicfOspfv3LinkLsdbRtrPriority,
                             hpicfOspfv3LinkLsdbOptions,
                             hpicfOspfv3LinkLsdbLocalAddress,
                             hpicfOspfv3LinkLsdbNumPrefixes,
                             hpicfOspfv3LinkPrefixOptions,
                             hpicfOspfv3LinkLsdbLsaLength
                            }
            STATUS          current
            DESCRIPTION
                "These objects are used for OSPFv3 systems
                that display their Link-scope link state database
                for non-virtual interfaces."
            ::= {  hpicfOspfv3Groups 4 }


     hpicfOspfv3LogGroup OBJECT-GROUP
         OBJECTS    {  hpicfOspfv3LogAction}
         STATUS     current
         DESCRIPTION "A collection of objects for configuring
                     the logging of OSPFv3 adjacency related
                     events."
         ::= {hpicfOspfv3Groups 8}

    hpicfOspfv3TrapControlGroup OBJECT-GROUP
         OBJECTS    { hpicfOspfv3SetTrap
                    }
         STATUS     current
         DESCRIPTION "A collection of object which is for controlling
                      the hpicfOspfv3Traps."
         ::= { hpicfOspfv3Groups 9}

    hpicfOspfv3AreaGroup OBJECT-GROUP
         OBJECTS    {
                      hpicfOspfv3AreaNbrDownCount,
                      hpicfOspfv3AreaNbrAttemptCount,
                      hpicfOspfv3AreaNbrInitCount,
                      hpicfOspfv3AreaNbr2wayCount,
                      hpicfOspfv3AreaNbrExstartCount,
                      hpicfOspfv3AreaNbrExchangeCount,
                      hpicfOspfv3AreaNbrLoadingCount,
                      hpicfOspfv3AreaNbrFullCount,
                      hpicfOspfv3AreaInterfaceCount,
                      hpicfOspfv3AreaScopeUnknownLsaCount

                    }
         STATUS     current
         DESCRIPTION
             "These Area objects used for
              managing/monitoring OSPFv3 Areas."
         ::= {  hpicfOspfv3Groups 11 }

     hpicfOspfv3AreaLsdbStatsGroup OBJECT-GROUP
          OBJECTS    { hpicfOspfv3AreaLsdbStatRtrLsaCnt,
                       hpicfOspfv3AreaLsdbStatNwLsaCnt,
                       hpicfOspfv3AreaLsdbStatInterPreLsaCnt,
                       hpicfOspfv3AreaLsdbStatInterRtrLsaCnt,
                       hpicfOspfv3AreaLsdbStatIntraPreLsaCnt
                     }
          STATUS     current
          DESCRIPTION
              "These lsdb objects used for
               monitoring OSPFv3 statistics per area."
          ::= {  hpicfOspfv3Groups 13 }

     hpicfOspfv3NbrGroup1 OBJECT-GROUP
            OBJECTS         {
                             hpicfOspfv3NbrUpTime,
                             hpicfOspfv3NbrTimeToExpiry,
                             hpicfOspfv3NbrDataBaseSummary,
                             hpicfOspfv3NbrLinkStateRequest,
                             hpicfOspfv3NbrRestartState
                            }
            STATUS    current
            DESCRIPTION
                "These neighbor objects are used for
                managing/monitoring OSPFv3 neighbors."
            ::= {  hpicfOspfv3Groups 14 }

     hpicfOspfv3StatisticGroup1 OBJECT-GROUP
        OBJECTS     { hpicfOspfv3IfSentHelloPkt,
                      hpicfOspfv3IfSentDDPkt,
                      hpicfOspfv3IfSentLSRPkt,
                      hpicfOspfv3IfSentLSUPkt,
                      hpicfOspfv3IfSentLSAPkt,
                      hpicfOspfv3IfRcvdHelloPkt,
                      hpicfOspfv3IfRcvdDDPkt,
                      hpicfOspfv3IfRcvdLSRPkt ,
                      hpicfOspfv3IfRcvdLSUPkt,
                      hpicfOspfv3IfRcvdLSAPkt,
                      hpicfOspfv3IfErrorCount,
                      hpicfOspfv3IfSentTotalErrorCount,
                      hpicfOspfv3IfRcvdTotalErrorCount,
                      hpicfOspfv3ClearCounters,
                      hpicfOspfv3SpfReason}
        STATUS      current
        DESCRIPTION "A collection of objects that contain
                     OSPF interface and SPF statistics."
        ::= { hpicfOspfv3Groups 15 }

     hpicfOspfv3IfGroup1 OBJECT-GROUP
            OBJECTS         {
                             hpicfOspfv3IfPassive,
                             hpicfOspfv3IfNbrCount,
                             hpicfOspfv3IfDRAddr,
                             hpicfOspfv3IfBDRAddr,
                             hpicfOspfv3IfHelloDueTime,
                             hpicfOspfv3IfAdjNbrCount
                            }
            STATUS          current
            DESCRIPTION
                "These interface objects are used for
                managing/monitoring OSPFv3 interfaces."
            ::= {  hpicfOspfv3Groups 16 }

    hpicfOspfv3MetricGroup OBJECT-GROUP
        OBJECTS     { hpicfOspfv3IfFlagValue }
        STATUS      current
        DESCRIPTION "Flags to identify global or manual OSPFv3 cost
                     configuration."
        ::= { hpicfOspfv3Groups 17 }

     hpicfOspfv3DistributeListGroup OBJECT-GROUP
             OBJECTS     {
                           hpicfOspfv3DistributeListSeqNum,
                           hpicfOspfv3DistributeListStatus
                         }
             STATUS      current
             DESCRIPTION "A collection of objects for controlling the
                          installation of intra-area routes by OSPFv3."
             ::= { hpicfOspfv3Groups 19 }

-- Historical definitions retained for Netdisco compatibility.
       hpicfOspfv3LsdbAreaId OBJECT-TYPE
          SYNTAX          Ospfv3AreaIdTC
          MAX-ACCESS      accessible-for-notify
          STATUS          current
          DESCRIPTION
             "The 32-bit identifier of the Area from which the
              LSA was received."
          REFERENCE
             "OSPF Version 2, Appendix C.2 Area parameters"
          ::= { hpicfOspfv3TrapControl 2 }

       hpicfOspfv3LsdbType OBJECT-TYPE
          SYNTAX          Unsigned32(0..'FFFFFFFF'h)
          MAX-ACCESS      accessible-for-notify
          STATUS          current
          DESCRIPTION
             "The type of the link state advertisement.
              Each link state type has a separate
              advertisement format. Area-Scope LSAs unrecognized
              by the router are also stored in this database."
          ::= { hpicfOspfv3TrapControl 3 }

       hpicfOspfv3LsdbRouterId OBJECT-TYPE
          SYNTAX          Ospfv3RouterIdTC
          MAX-ACCESS      accessible-for-notify
          STATUS          current
          DESCRIPTION
             "The 32-bit number that uniquely identifies the
              originating router in the Autonomous System."
          REFERENCE
             "OSPF Version 2, Appendix C.1 Global parameters"
          ::= { hpicfOspfv3TrapControl 4 }

       hpicfOspfv3LsdbLsid OBJECT-TYPE
          SYNTAX          Ospfv3LsIdTC
          MAX-ACCESS      accessible-for-notify
          STATUS          current
          DESCRIPTION
             "The Link State ID is an LS Type Specific field
              containing a unique identifier;
              it identifies the piece of the routing domain
              that is being described by the advertisement.
              In contrast to OSPFv2, the LSID has no
              addressing semantics."
           ::= { hpicfOspfv3TrapControl 5 }

    -- Traps

       hpicfOspfv3IfStateChange NOTIFICATION-TYPE
          OBJECTS   {
                     ospfv3RouterId, -- The originator of the trap
                     ospfv3IfIndex,
                     ospfv3IfInstId,
                     ospfv3IfState -- The new state
                    }
          STATUS     current
          DESCRIPTION
             "An hpicfOspfv3IfStateChange notification signifies
              that there has been a change in the state of a non-virtual
             OSPFv3 interface. This trap should  be  generated
             when  the interface state regresses (e.g., goes
             from Dr to Down) or progresses  to  a  terminal
             state  (i.e.,  Point-to-Point, DR Other, Dr, or
             Backup)."
          ::= { hpicfOspfv3Traps 1 }

       hpicfOspfv3VirtIfStateChange NOTIFICATION-TYPE
          OBJECTS   {
                     ospfv3RouterId, -- The originator of the notification
                     ospfv3VirtIfAreaId,
                     ospfv3VirtIfNeighbor,
                     ospfv3VirtIfInstId,
                     ospfv3VirtIfState  -- The new state
                    }
          STATUS     current
          DESCRIPTION
             "An hpicfOspfv3VirtIfStateChange notification signifies that there
             has  been a change in the state of an OSPFv3 virtual
             interface.

             This notification should be generated when  the
             inter-face  state  regresses  (e.g., goes from Point-
             to-Point to Down) or progresses to  a  terminal
             state (i.e., Point-to-Point)."
          ::= { hpicfOspfv3Traps 2 }

       hpicfOspfv3NbrStateChange NOTIFICATION-TYPE
          OBJECTS   {
                     ospfv3RouterId, -- The originator of the trap
                     ospfv3NbrIfIndex,
                     ospfv3NbrIfInstId,
                     ospfv3NbrRtrId,
                     ospfv3NbrState  -- The new state
                    }
          STATUS     current
          DESCRIPTION
             "An hpicfOspfv3NbrStateChange trap signifies that
             there has been a change in the state of a non-
             virtual OSPFv3 neighbor. This trap should be
             generated when the neighbor state regresses
             (e.g., goes from Attempt or Full  to  1-Way  or
             Down)  or progresses to a terminal state (e.g.,
             2-Way or Full).  When an  neighbor  transitions
             from  or  to Full on non-broadcast multi-access
             and broadcast networks, the trap should be gen-
             erated  by the designated router.  A designated
             router transitioning to Down will be  noted  by
             hpicfOspfv3IfStateChange."
          ::= { hpicfOspfv3Traps 3 }

       hpicfOspfv3VirtNbrStateChange NOTIFICATION-TYPE
          OBJECTS   {
                     ospfv3RouterId, -- The originator of the trap
                     ospfv3VirtNbrArea,
                     ospfv3VirtNbrIfInstId,
                     ospfv3VirtNbrRtrId,
                     ospfv3VirtNbrState  -- The new state
                    }
          STATUS     current
          DESCRIPTION
             "An hpicfOspfv3VirtNbrStateChange trap signifies that
             there has  been a change in the state of an
             OSPFv3 virtual neighbor. This trap should
             be  generated when  the  neighbor state regresses
             (e.g., goes from Attempt or  Full  to  1-Way  or  Down)
             or progresses to a terminal state (e.g., Full)."
          ::= { hpicfOspfv3Traps 4 }

       hpicfOspfv3IfConfigError NOTIFICATION-TYPE
          OBJECTS   {
                     ospfv3RouterId, -- The originator of the trap
                     ospfv3IfIndex,
                     ospfv3IfInstId,
                     ospfv3PacketSrc,  -- The source IPv6 address
                     ospfv3ConfigErrorType, -- Type of error
                     ospfv3PacketType
                    }
          STATUS     current
          DESCRIPTION
             "An hpicfOspfv3IfConfigError  trap  signifies  that  a
             packet  has  been received on a non-virtual in-
             terface  from  a  router  whose   configuration
             parameters  conflict  with this router's confi-
             guration parameters.  Note that the  event  op-
             tionMismatch  should  cause  a  trap only if it
             prevents an adjacency from forming."
          ::= { hpicfOspfv3Traps 5 }

       hpicfOspfv3VirtIfConfigError NOTIFICATION-TYPE
          OBJECTS   {
                     ospfv3RouterId, -- The originator of the trap
                     ospfv3VirtIfAreaId,
                     ospfv3VirtIfNeighbor,
                     ospfv3VirtIfInstId,
                     ospfv3ConfigErrorType, -- Type of error
                     ospfv3PacketType
                    }
          STATUS     current
          DESCRIPTION
             "An hpicfOspfv3VirtIfConfigError trap signifies that a
             packet has been  received  on a virtual interface
             from a router  whose  configuration  parameters
             conflict   with   this  router's  configuration
             parameters.  Note that the event optionMismatch
             should  cause a trap only if it prevents an ad-
             jacency from forming."
          ::= { hpicfOspfv3Traps 6 }

      hpicfOspfv3IfRxBadPacket NOTIFICATION-TYPE
          OBJECTS   {
                     ospfv3RouterId, -- The originator of the trap
                     ospfv3IfIndex,
                     ospfv3IfInstId,
                     ospfv3PacketSrc,  -- The source IPv6 address
                     ospfv3PacketType
                    }
          STATUS     current
          DESCRIPTION
             "An hpicfOspfv3IfRxBadPacket trap  signifies  that  an
             OSPFv3  packet  that cannot be parsed has been received
             on a non-virtual interface."
          ::= { hpicfOspfv3Traps 7 }

       hpicfOspfv3VirtIfRxBadPacket NOTIFICATION-TYPE
          OBJECTS   {
                     ospfv3RouterId, -- The originator of the trap
                     ospfv3VirtIfAreaId,
                     ospfv3VirtIfNeighbor,
                     ospfv3VirtIfInstId,
                     ospfv3PacketType
                    }
          STATUS     current
          DESCRIPTION
              "An hpicfOspfv3VirtIfRxBadPacket trap signifies that an
              OSPFv3 packet that cannot be parsed has been received
              on a non-virtual interface."
          ::= { hpicfOspfv3Traps 8 }

       hpicfOspfv3TxRetransmit NOTIFICATION-TYPE
          OBJECTS   {
                     ospfv3RouterId, -- The originator of the trap
                     ospfv3IfIndex,
                     ospfv3IfInstId,
                     ospfv3NbrRtrId, -- Destination
                     ospfv3PacketType,
                     hpicfOspfv3LsdbType,
                     hpicfOspfv3LsdbLsid,
                     hpicfOspfv3LsdbRouterId
                    }
          STATUS     current
          DESCRIPTION
             "An hpicfOspfv3TxRetransmit trap signifies that an
             OSPFv3  packet has been retransmitted on a non-
             virtual interface. All packets that may be re-
             transmitted are associated with an LSDB entry.
             The LS type, LS ID, and Router ID are used to
             identify the LSDB entry."
          ::= { hpicfOspfv3Traps 9 }

       hpicfOspfv3VirtIfTxRetransmit NOTIFICATION-TYPE
          OBJECTS   {
                     ospfv3RouterId, -- The originator of the trap
                     ospfv3VirtIfAreaId,
                     ospfv3VirtIfNeighbor,
                     ospfv3VirtIfInstId,
                     ospfv3PacketType,
                     hpicfOspfv3LsdbType,
                     hpicfOspfv3LsdbLsid,
                     hpicfOspfv3LsdbRouterId
                    }
          STATUS     current
          DESCRIPTION
             "An hpicfOspfv3VirtIfTxRetransmit trap signifies  that
             an OSPFv3 packet has been retransmitted on a virtual
             interface. All packets that may be retransmitted
             are associated with an LSDB entry. The LS type,
             LS ID, and Router ID are used to identify the LSDB
             entry."
          ::= { hpicfOspfv3Traps 10 }

       hpicfOspfv3OriginateLsa NOTIFICATION-TYPE
          OBJECTS   {
                     ospfv3RouterId, -- The originator of the trap
                     hpicfOspfv3LsdbAreaId,  -- 0.0.0.0 for AS Externals
                     hpicfOspfv3LsdbType,
                     hpicfOspfv3LsdbLsid,
                     hpicfOspfv3LsdbRouterId
                    }
          STATUS     current
          DESCRIPTION
             "An hpicfOspfv3OriginateLsa trap signifies that a new
             LSA  has  been originated by this router.  This
             trap should not be invoked for simple refreshes
             of  LSAs  (which happesn every 30 minutes), but
             instead will only be invoked  when  an  LSA  is
             (re)originated due to a topology change.  Addi-
             tionally, this trap does not include LSAs  that
             are  being  flushed  because  they have reached
             MaxAge."
          ::= { hpicfOspfv3Traps 11 }

       hpicfOspfv3MaxAgeLsa NOTIFICATION-TYPE
          OBJECTS   {
                     ospfv3RouterId, -- The originator of the trap
                     hpicfOspfv3LsdbAreaId,  -- 0.0.0.0 for AS Externals
                     hpicfOspfv3LsdbType,
                     hpicfOspfv3LsdbLsid,
                     hpicfOspfv3LsdbRouterId
                    }
          STATUS     current
          DESCRIPTION
             "An hpicfOspfv3MaxAgeLsa trap signifies that one  of
             the LSA in the router's link-state database has
             aged to MaxAge."
          ::= { hpicfOspfv3Traps 12 }

       hpicfOspfv3UnknownLsa NOTIFICATION-TYPE
          OBJECTS   {
                     ospfv3RouterId, -- The originator of the trap
		     hpicfOspfv3LsdbLsid,
                     ospfv3IfIndex, -- Input interface
                     ospfv3IfInstId,
                     hpicfOspfv3LsdbRouterId -- Originator routerID
                    }
          STATUS     current
          DESCRIPTION
             "An hpicfOspfv3UnknownLsa trap signifies that one of
             the neighbor has sent an unknown LSA. Only DR generates
             this trap and If NBR state is less than Exchange
             need not originate this trap"
          ::= { hpicfOspfv3Traps 13 }

      hpicfOspfv3AsbrStatusChange NOTIFICATION-TYPE
          OBJECTS   {
                     ospfv3RouterId -- The originator of the trap
                    }
          STATUS     current
          DESCRIPTION
             "An hpicfOspfv3AsbrStatusChange trap signifies
             that  device's ASBR Status has changed."
          ::= { hpicfOspfv3Traps 16 }

      hpicfOspfv3AbrStatusChange NOTIFICATION-TYPE
          OBJECTS   {
                     ospfv3RouterId -- The originator of the trap
                    }
          STATUS     current
          DESCRIPTION
             "An hpicfOspfv3AbrStatusChange trap  signifies
             that  device's ABR Status has changed.
             There are two distinct definitions
             of ABR given by IBM & Cisco, Implementations are free
             to follow their own interpretation of ABR while
             originating this trap"
           ::= { hpicfOspfv3Traps 17 }


    -- conformance information

     hpicfOspfv3IfGroup OBJECT-GROUP
            OBJECTS         {
                             hpicfOspfv3IfPassive,
                             hpicfOspfv3IfNbrCount
                            }
            STATUS          current
            DESCRIPTION
                "These interface objects used for
                managing/monitoring OSPFv3 interfaces."
            ::= {  hpicfOspfv3Groups 5 }

     hpicfOspfv3NbrGroup OBJECT-GROUP
            OBJECTS         {
                             hpicfOspfv3NbrUpTime,
                             hpicfOspfv3NbrTimeToExpiry
                            }
            STATUS          current
            DESCRIPTION
                "These neighbor objects are used for
                managing/monitoring OSPFv3 neighbors."
            ::= {  hpicfOspfv3Groups 6 }

     hpicfOspfv3StatisticGroup OBJECT-GROUP
        OBJECTS     { hpicfOspfv3IfSentHelloPkt,
                      hpicfOspfv3IfSentDDPkt,
                      hpicfOspfv3IfSentLSRPkt,
                      hpicfOspfv3IfSentLSUPkt,
                      hpicfOspfv3IfSentLSAPkt,
                      hpicfOspfv3IfRcvdHelloPkt,
                      hpicfOspfv3IfRcvdDDPkt,
                      hpicfOspfv3IfRcvdLSRPkt ,
                      hpicfOspfv3IfRcvdLSUPkt,
                      hpicfOspfv3IfRcvdLSAPkt,
                      hpicfOspfv3IfErrorCount,
                      hpicfOspfv3ClearCounters,
                      hpicfOspfv3SpfReason}
        STATUS      current
        DESCRIPTION "A collection of objects that contain
                     OSPF interface and SPF statistics."
        ::= { hpicfOspfv3Groups 7 }

    hpicfOspfv3TrapsGroup NOTIFICATION-GROUP
         NOTIFICATIONS  { hpicfOspfv3VirtIfStateChange,
                          hpicfOspfv3NbrStateChange,
                          hpicfOspfv3VirtNbrStateChange,
                          hpicfOspfv3IfConfigError,
                          hpicfOspfv3VirtIfConfigError,
                          hpicfOspfv3IfRxBadPacket,
                          hpicfOspfv3VirtIfRxBadPacket,
                          hpicfOspfv3IfStateChange,
                          hpicfOspfv3TxRetransmit,
                          hpicfOspfv3VirtIfTxRetransmit,
                          hpicfOspfv3OriginateLsa,
                          hpicfOspfv3MaxAgeLsa,
                          hpicfOspfv3UnknownLsa,
                          hpicfOspfv3AsbrStatusChange,
                          hpicfOspfv3AbrStatusChange
                        }
         STATUS         current
         DESCRIPTION     "A collection of hpicfOspfv3 traps."
         ::= {hpicfOspfv3Groups 10}

END
