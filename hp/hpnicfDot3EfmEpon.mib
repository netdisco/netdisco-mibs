--===========================================================
-- Copyright (c) 2010-2013 Hewlett-Packard Development Company, L.P.
-- Description: This MIB is excerpted from the draft-ietf-hubmib-efm-epon-mib-02 directly
---             only changed the object name,added the hpnicf as prefix.
-- Reference:  
-- Version: V1.0
-- History:
-- V1.0 created by liyue.  
--     Define MODULE-IDENTITY for hpnicfDot3EfmeponMIB
--=================================================================
HPN-ICF-DOT3-EFM-EPON-MIB DEFINITIONS ::= BEGIN          
   
   IMPORTS
        hpnicfEpon            
            FROM HPN-ICF-OID-MIB   
        MODULE-IDENTITY, mib-2, OBJECT-TYPE, Counter32,
        Integer32, OBJECT-IDENTITY
            FROM SNMPv2-SMI
        TruthValue, MacAddress
            FROM SNMPv2-TC
        ifIndex
            FROM IF-MIB
        MODULE-COMPLIANCE, OBJECT-GROUP
            FROM SNMPv2-CONF;

   hpnicfDot3EfmeponMIB MODULE-IDENTITY
       LAST-UPDATED "200409210000Z"  -- September 21, 2004
       ORGANIZATION
           ""
       CONTACT-INFO
           ""
       DESCRIPTION
               "The objects in this MIB module are used to manage the
                Ethernet in the First Mile (EFM) Multi Point Control
                Protocol (MPCP) Interfaces as defined in IEEE Draft
                P802.3ah/D3.0 clause 64,65.
                The following reference is used throughout this MIB module:
                [802.3ah] refers to:
                IEEE Draft P802.3ah/D3.3: 'Draft amendment to -
                Information technology - Telecommunications and
                information exchange between systems - Local and
                metropolitan area networks - Specific requirements -
                Part 3: Carrier sense multiple access with collision
                detection (CSMA/CD) access method and physical layer
                specifications - Media Access Control Parameters,
                Physical Layers and Management Parameters for
                subscriber access networks', 22 April 2004.

                Of particular interest are Clause 64(MPCP) 65(P2MP RS) and
                60 (PON PMDs). Clause 30, 'Management', and Clause 45,
                'Management Data Input/Output (MDIO) Interface'.

                Copyright (C) The Internet Society (2004).  This version
                of this MIB module is part of XXXX see the RFC itself for
                full legal notices."

             -- Editor's Note: Replace XXXX with the actual RFC number
             -- assigned by RFC Editor and remove this note

       REVISION    "200409210000Z"  -- September 21, 2004
       DESCRIPTION "Initial version, published as RFC XXXX."

       ::= { hpnicfEpon 2 }     

       -- Editor's Note: Replace XXX with a real OID once it is
       -- assigned by IANA and remove this note.


   -- Editor-s note: MPCP MIB modules definitions ([802.3ah]
   --- clause 30.3.5)
   -- Editor-s note: Description in attributes with References should be
   -- minimized in later versions

   hpnicfDot3MpcpMIB OBJECT IDENTIFIER ::= { hpnicfDot3EfmeponMIB 1 }

   hpnicfDot3MpcpObjects OBJECT IDENTIFIER ::= { hpnicfDot3MpcpMIB 1 }

   hpnicfDot3MpcpConformance OBJECT IDENTIFIER ::= { hpnicfDot3MpcpMIB 2 }

   hpnicfDot3MpcpTable OBJECT-TYPE
       SYNTAX  SEQUENCE OF HpnicfDot3MpcpEntry
       MAX-ACCESS  not-accessible
       STATUS  current
       DESCRIPTION
               "Table for dot3 Multi-Point Control Protocol (MPCP)
               MIB modules."
       ::= { hpnicfDot3MpcpObjects 1 }

   hpnicfDot3MpcpEntry OBJECT-TYPE
       SYNTAX  HpnicfDot3MpcpEntry
       MAX-ACCESS  not-accessible
       STATUS  current
       DESCRIPTION
               "An entry in the dot3 MPCP MIB modules table."
       INDEX  { ifIndex }
       ::= { hpnicfDot3MpcpTable 1 }

   HpnicfDot3MpcpEntry ::=
       SEQUENCE {
           hpnicfDot3MpcpID                           Integer32,
           hpnicfDot3MpcpOperStatus                   TruthValue,
           hpnicfDot3MpcpMode                         INTEGER,
           hpnicfDot3MpcpLinkID                       Integer32,
           hpnicfDot3MpcpRemoteMACAddress             MacAddress,
           hpnicfDot3MpcpRegistrationState            INTEGER,
           hpnicfDot3MpcpTransmitElapsed              Integer32,
           hpnicfDot3MpcpReceiveElapsed               Integer32,
           hpnicfDot3MpcpRoundTripTime                Integer32,
           hpnicfDot3MpcpMaximumPendingGrants         Integer32,
           hpnicfDot3MpcpAdminState                   TruthValue,
           hpnicfDot3MpcpOnTime                       Integer32,
           hpnicfDot3MpcpOffTime                      Integer32,
           hpnicfDot3MpcpSyncTime                     Integer32
       }

   hpnicfDot3MpcpID OBJECT-TYPE
       SYNTAX  Integer32
       MAX-ACCESS  read-only
       STATUS  current
       DESCRIPTION
               "This variable is assigned so as to uniquely identify the
                Multi-Point MAC  Control (MPCP) entity, as defined in
                [802.3ah] clause 64, among the subordinate managed
                objects of the containing object.
                This attribute is relevant for an OLT and an ONU."
       REFERENCE   "[802.3ah], 30.3.5.1.1."
       ::= { hpnicfDot3MpcpEntry 1 }


   hpnicfDot3MpcpOperStatus OBJECT-TYPE
       SYNTAX  TruthValue
       MAX-ACCESS  read-only
       STATUS  current
       DESCRIPTION
               "This variable can be used to define the operational
                state of the Multi-Point MAC Control sublayer as
                defined in [802.3ah] clause 64. Selecting admin for an
                interface with Multi-Point MAC Control sublayer. When
                the attribute is True the the interface will act as if
                Multi-point control protocol is enabled. When the
                attribute is False the interface will act as if it does
                not have the Multi-point control protocol. The
                operational state can be changed using the
                hpnicfDot3MpcpAdminState attribute.
                This attribute is relevant for an OLT and an ONU."
       REFERENCE   "[802.3ah], 30.3.5.1.2."
       ::= { hpnicfDot3MpcpEntry 2 }

   hpnicfDot3MpcpMode  OBJECT-TYPE
       SYNTAX  INTEGER {
               olt(1),
               onu(2)
       }
       MAX-ACCESS  read-write
       STATUS  current
       DESCRIPTION
               "This variable can be used to identify the operational
                state of the Multi-Point MAC Control sublayer as
                defined in [802.3ah] clause 64. Selecting olt(1) for an
                OLT (server) mode and onu(2) for an ONU (client) mode.
                Writing can be done during only during initialization,
                when hpnicfDot3MpcpOperStatus indicates Flase.
                This attribute is relevant for an OLT and an ONU."
       REFERENCE   "[802.3ah], 30.3.5.1.3."
       DEFVAL { 1 }
       ::= { hpnicfDot3MpcpEntry 3 }

   hpnicfDot3MpcpLinkID OBJECT-TYPE
       SYNTAX  Integer32
       MAX-ACCESS  read-only
       STATUS  current
       DESCRIPTION
               "A read-only value that identifies the Logical Link
                identity (LLID) associated with the MAC port as
                specified in [802.3ah] clause 65.1.3.2.2.
                This attribute is relevant for an OLT and an ONU."
       REFERENCE   "[802.3ah], 30.3.5.1.4."
       ::= { hpnicfDot3MpcpEntry 4 }

   hpnicfDot3MpcpRemoteMACAddress OBJECT-TYPE
       SYNTAX  MacAddress
       MAX-ACCESS  read-only
       STATUS  current
       DESCRIPTION
               "A read-only value that identifies the source_address
                parameter of the last MPCPDUs passed to the MAC Control.
                This value is updated on reception of a valid frame with
                (1) a destination Field equal to the reserved multicast
                address for MAC Control specified in [802.3ah] Annex
                31A, (2) lengthOrType field value equal to the reserved
                Type for MAC Control as specified in [802.3ah] Annex
                31A. (3) an MPCP subtype value equal to the subtype
                reserved for MPCP as specified in [802.3ah] Annex 31A.
                This attribute is relevant for an OLT and an ONU."
       REFERENCE   "[802.3ah], 30.3.5.1.5."
       ::= { hpnicfDot3MpcpEntry 5 }

   hpnicfDot3MpcpRegistrationState OBJECT-TYPE
       SYNTAX  INTEGER {
               unregistered(1),
               registering(2),
               registered(3)
       }
       MAX-ACCESS  read-only
       STATUS  current
       DESCRIPTION
               "A read-only value that identifies the operational state
                of the Multi-Point MAC Control sublayer as defined in
                [802.3ah] clause 64. When this attribute has the
                enumeration unregistered(1) the interface may be used
                for registering a link partner. When this attribute has
                the enumeration registering(2) the interface is in the
                process of registering a link-partner. When this
                attribute has the enumeration registered(3) the
                interface has an established link-partner.
                This attribute is relevant for an OLT and an ONU. For
                the OLT it provides an indication per LLID."
       REFERENCE   "[802.3ah], 30.3.5.1.6."
       ::= { hpnicfDot3MpcpEntry 6 }

   hpnicfDot3MpcpTransmitElapsed OBJECT-TYPE
       SYNTAX  Integer32
       UNITS       "TQ (16nsec)"
       MAX-ACCESS  read-only
       STATUS  current
       DESCRIPTION
               "A read-only value that reports the interval from last
                MPCP frame transmission in increments of Time Quanta
                (TQ) 16ns. The value returned shall be (interval from
                last MPCP frame transmission in ns)/16. If this value
                exceeds (2^32-1) the value (2^32-1) shall be returned.
                This attribute is relevant for an OLT and an ONU."
       REFERENCE   "[802.3ah], 30.3.5.1.19."
       ::= { hpnicfDot3MpcpEntry 7 }

   hpnicfDot3MpcpReceiveElapsed OBJECT-TYPE
       SYNTAX  Integer32
       UNITS       "TQ (16nsec)"
       MAX-ACCESS  read-only
       STATUS  current
       DESCRIPTION
               "A read-only value that reports the interval from last
                MPCP frame reception in increments of Time Quanta (TQ)
                16ns. The value returned shall be (interval from last
                MPCP last MPCP frame reception in ns)/16. If this value
                exceeds (2^32-1) the value (2^32-1) shall be returned.
                This attribute is relevant for an OLT and an ONU."
       REFERENCE   "[802.3ah], 30.3.5.1.20."
       ::= { hpnicfDot3MpcpEntry 8 }

   hpnicfDot3MpcpRoundTripTime OBJECT-TYPE
       SYNTAX  Integer32
       UNITS       "TQ (16nsec)"
       MAX-ACCESS  read-only
       STATUS  current
       DESCRIPTION
               "A read-only value that reports the MPCP round trip time
                in increments of Time Quanta (TQ) 16ns. The value
                returned shall be (round trip time in ns)/16. If this
                value exceeds (2^16-1) the value (2^16-1)  shall be
                returned. This attribute is relevant for an OLT and an
                ONU. For the OLT there is a value per LLID"
       REFERENCE   "[802.3ah], 30.3.5.1.21."
       ::= { hpnicfDot3MpcpEntry 9 }

   hpnicfDot3MpcpMaximumPendingGrants OBJECT-TYPE
       SYNTAX  Integer32 (0..255)
       MAX-ACCESS  read-only
       STATUS  current
       DESCRIPTION
               "A read-only value that indicates the maximum number of
                grants an ONU can store. The maximum number of grants an
                ONU can store has a range of 0 to 255.
                This attribute is relevant for an OLT and an ONU. For
                the OLT there is a value per LLID"
       REFERENCE   "[802.3ah], 30.3.5.1.24."
       ::= { hpnicfDot3MpcpEntry 10 }

   hpnicfDot3MpcpAdminState OBJECT-TYPE
       SYNTAX  TruthValue
       MAX-ACCESS  read-write
       STATUS  current
       DESCRIPTION
               "This variable can be used to define the operational
                state of the Multi-Point MAC Control sublayer as defined
                in [802.3ah] clause 64. Selecting admin for an interface
                with Multi-Point MAC Control sublayer. When selecting
                the value as True the interface Multi-Point control
                protocol is enabled. When selecting the value as False
                the interface acts as if the Multi-point Control
                protocol does not exist. Reading reflects the state of
                the attribute and the operation of the Multi-point
                control protocol mode of the interface.
                Writing can be done all the time.
                This attribute is relevant for an OLT and an ONU."
       REFERENCE   "[802.3ah], 30.3.5.2.1."
       DEFVAL { false }
       ::= { hpnicfDot3MpcpEntry 11 }


   hpnicfDot3MpcpOnTime OBJECT-TYPE
       SYNTAX  Integer32
       UNITS       "TQ (16nsec)"
       MAX-ACCESS  read-only
       STATUS  current
       DESCRIPTION
               "A read-only value that reports the -on time- for a grant
                burst in increments of Time Quanta (TQ) 16ns as defined
                in [802.3ah] 60,64. The value returned shall be (on time
                ns)/16. If this value exceeds (2^32-1) the value
                (2^32-1) shall be returned.
                This attribute is relevant for an OLT and an ONU."
       REFERENCE   "[802.3ah], 64.3.5.1."
       ::= { hpnicfDot3MpcpEntry 12 }

   hpnicfDot3MpcpOffTime OBJECT-TYPE
       SYNTAX  Integer32
       UNITS       "TQ (16nsec)"
       MAX-ACCESS  read-only
       STATUS  current
       DESCRIPTION
               "A read-only value that reports the -off time- for a
                grant burst in increments of Time Quanta (TQ) 16ns as
                defined in [802.3ah] 60,64. The value returned shall be
                (off time ns)/16. If this value exceeds (2^32-1) the
                value (2^32-1) shall be returned.
                This attribute is relevant for an OLT and an ONU."
       REFERENCE   "[802.3ah], 64.3.5.1."
       ::= { hpnicfDot3MpcpEntry 13 }

   hpnicfDot3MpcpSyncTime OBJECT-TYPE
       SYNTAX  Integer32
       UNITS       "TQ (16nsec)"
       MAX-ACCESS  read-only
       STATUS  current
       DESCRIPTION
               "A read-only value that reports the -sync lock time- for
                an OLT receiver in increments of Time Quanta (TQ) 16ns
                as defined in [802.3ah] 60,64,65. The value returned
                shall be (sync lock time ns)/16. If this value exceeds
                (2^32-1) the value (2^32-1) shall be returned.
                This attribute is relevant for an OLT and an ONU."
       REFERENCE   "[802.3ah], 64.3.3.2."
      ::= { hpnicfDot3MpcpEntry 14 }



   hpnicfDot3MpcpStatTable OBJECT-TYPE
       SYNTAX     SEQUENCE OF HpnicfDot3MpcpStatEntry
       MAX-ACCESS not-accessible
       STATUS     current
       DESCRIPTION
               "This table defines the list of statistics counters of
                [802.3ah] clause 64 MPCP interface."
   ::= { hpnicfDot3MpcpObjects 2 }

   hpnicfDot3MpcpStatEntry OBJECT-TYPE
       SYNTAX     HpnicfDot3MpcpStatEntry
       MAX-ACCESS not-accessible
       STATUS     current
       DESCRIPTION
               "Table entries for table of statistics counters of
                [802.3ah] clause 64 MPCP interface."
       INDEX       { ifIndex }
       ::= { hpnicfDot3MpcpStatTable 1 }

   HpnicfDot3MpcpStatEntry ::=
       SEQUENCE {
               hpnicfDot3MpcpMACCtrlFramesTransmitted       Counter32,
               hpnicfDot3MpcpMACCtrlFramesReceived          Counter32,
               hpnicfDot3MpcpDiscoveryWindowsSent           Counter32,
               hpnicfDot3MpcpDiscoveryTimeout               Counter32,
               hpnicfDot3MpcpTxRegRequest                   Counter32,
               hpnicfDot3MpcpRxRegRequest                   Counter32,
               hpnicfDot3MpcpTxRegAck                       Counter32,
               hpnicfDot3MpcpRxRegAck                       Counter32,
               hpnicfDot3MpcpTxReport                       Counter32,
               hpnicfDot3MpcpRxReport                       Counter32,
               hpnicfDot3MpcpTxGate                         Counter32,
               hpnicfDot3MpcpRxGate                         Counter32,
               hpnicfDot3MpcpTxRegister                     Counter32,
               hpnicfDot3MpcpRxRegister                     Counter32,
               hpnicfDot3MpcpRxNotSupportedMPCP             Counter32
       }

   hpnicfDot3MpcpMACCtrlFramesTransmitted OBJECT-TYPE
       SYNTAX  Counter32
       UNITS      "frames"
       MAX-ACCESS  read-only
       STATUS  current
       DESCRIPTION
               "A count of MPCP frames passed to the MAC sublayer for
                transmission. This counter is incremented when a
                MA_CONTROL.request service primitive is generated within
                the MAC control sublayer with an opcode indicating a
                MPCP frame.
                This attribute is relevant for an OLT and an ONU."
       REFERENCE   "[802.3ah], 30.3.5.1.7."
       ::= { hpnicfDot3MpcpStatEntry 1 }

   hpnicfDot3MpcpMACCtrlFramesReceived OBJECT-TYPE
       SYNTAX  Counter32
       UNITS      "frames"
       MAX-ACCESS  read-only
       STATUS  current
       DESCRIPTION
               "A count of MPCP frames passed by the MAC sublayer to the
                MAC Control sublayer. This counter is incremented when a
                ReceiveFrame function call returns a valid frame with:
                (1) a lengthOrType field value equal to the reserved
                Type for 802.3_MAC_Control as specified in 31.4.1.3, and
                (2) an opcode indicating a MPCP frame.
                This attribute is relevant for an OLT and an ONU."
       REFERENCE   "[802.3ah], 30.3.5.1.8."
       ::= { hpnicfDot3MpcpStatEntry 2 }

   hpnicfDot3MpcpDiscoveryWindowsSent OBJECT-TYPE
       SYNTAX  Counter32
       MAX-ACCESS  read-only
       STATUS  current
       DESCRIPTION
               "A count of discovery windows generated. The counter is
                incremented by one for each generated discovery window.
                This attribute is relevant for an OLT and an ONU. At the
                ONU value should be zero."
       REFERENCE   "[802.3ah], 30.3.5.1.22."
       ::= { hpnicfDot3MpcpStatEntry 3 }

   hpnicfDot3MpcpDiscoveryTimeout OBJECT-TYPE
       SYNTAX  Counter32
       MAX-ACCESS  read-only
       STATUS  current
       DESCRIPTION
               "A count of the number of times a discovery timeout
                occurs. Increment the counter by one for each discovery
                processing state-machine reset resulting from timeout
                waiting for message arrival.
                This attribute is relevant for an OLT and an ONU."
       REFERENCE   "[802.3ah], 30.3.5.1.23."
       ::= { hpnicfDot3MpcpStatEntry 4 }


   hpnicfDot3MpcpTxRegRequest OBJECT-TYPE
       SYNTAX  Counter32
       UNITS      "frames"
       MAX-ACCESS  read-only
       STATUS  current
       DESCRIPTION
               "A count of the number of times a REGISTER_REQ MPCP
                frames transmission occurs. Increment the counter by one
                for each REGISTER_REQ MPCP frame transmitted as defined
                in [802.3ah] clause 64. This counter is mandatory for an
                ONU. This attribute is relevant for an OLT and an ONU.
                At the OLT value should be zero."
       REFERENCE   "[802.3ah], 30.3.5.1.12."
       ::= { hpnicfDot3MpcpStatEntry 5 }

   hpnicfDot3MpcpRxRegRequest OBJECT-TYPE
       SYNTAX  Counter32
       UNITS      "frames"
       MAX-ACCESS  read-only
       STATUS  current
       DESCRIPTION
               "A count of the number of times a REGISTER_REQ MPCP
                frames reception occurs. A single counter at the ONU and
                a set of counters, one for each LLID, at the OLT.
                Increment the counter by one for each REGISTER_REQ MPCP
                frame received for each LLID as defined in [802.3ah]
                clause 64. This counter is mandatory for an ONU and for
                an OLT. At the ONU value should be zero."
       REFERENCE   "[802.3ah], 30.3.5.1.17."
       ::= { hpnicfDot3MpcpStatEntry 6 }

   hpnicfDot3MpcpTxRegAck OBJECT-TYPE
       SYNTAX  Counter32
       UNITS      "frames"
       MAX-ACCESS  read-only
       STATUS  current
       DESCRIPTION
               "A count of the number of times a REGISTER_ACK MPCP
                frames transmission occurs. Increment the counter by one
                for each REGISTER_ACK MPCP frame transmitted as defined
                in [802.3ah] clause 64. This counter is mandatory for an
                ONU. This attribute is relevant for an OLT and an ONU.
                At the OLT the value should be zero."
       REFERENCE   "[802.3ah], 30.3.5.1.10."
       ::= { hpnicfDot3MpcpStatEntry 7 }

   hpnicfDot3MpcpRxRegAck OBJECT-TYPE
       SYNTAX  Counter32
       UNITS      "frames"
       MAX-ACCESS  read-only
       STATUS  current
       DESCRIPTION
               "A count of the number of times a REGISTER_ACK MPCP
                frames reception occurs. A single counter at the ONU and
                a set of counters, one for each LLID, at the OLT.
                Increment the counter by one for each REGISTER_ACK MPCP
                frame received for each LLID, as defined in [802.3ah]
                clause 64. This counter is mandatory for an ONU and for
                an OLT. At the ONU the value should be zero."
       REFERENCE   "[802.3ah], 30.3.5.1.15."
       ::= { hpnicfDot3MpcpStatEntry 8 }

   hpnicfDot3MpcpTxReport OBJECT-TYPE
       SYNTAX  Counter32
       UNITS      "frames"
       MAX-ACCESS  read-only
       STATUS  current
       DESCRIPTION
               "A count of the number of times a REPORT MPCP frames
                transmission occurs. Increment the counter by one for
                each REPORT MPCP frame transmitted as defined in
                [802.3ah] clause 64. This counter is mandatory for an
                ONU. This attribute is relevant for an OLT and an ONU.
                At the OLT value should be zero."
       REFERENCE   "[802.3ah], 30.3.5.1.13."
       ::= { hpnicfDot3MpcpStatEntry 9 }

   hpnicfDot3MpcpRxReport OBJECT-TYPE
       SYNTAX  Counter32
       UNITS      "frames"
       MAX-ACCESS  read-only
       STATUS  current
       DESCRIPTION
               "A count of the number of times a REPORT MPCP frames
                reception occurs. A single counter at the ONU and a set
                of counters, one for each LLID, at the OLT. Increment
                the counter by one for each REPORT MPCP frame received
                for each LLID, as defined in [802.3ah] clause 64.
                This counter is mandatory for an ONU and for an OLT.
                At the ONU value should be zero."
       REFERENCE   "[802.3ah], 30.3.5.1.18."
       ::= { hpnicfDot3MpcpStatEntry 10 }

   hpnicfDot3MpcpTxGate OBJECT-TYPE
       SYNTAX  Counter32
       UNITS      "frames"
       MAX-ACCESS  read-only
       STATUS  current
       DESCRIPTION
               "A count of the number of times a GATE MPCP frames
                transmission occurs. A set of counters, one for each
                LLID, at the OLT. Increment the counter by one for each
                GATE MPCP frame transmitted, for each LLID, as defined
                in [802.3ah] clause 64. This counter is mandatory for an
                OLT. This attribute is relevant for an OLT and an ONU.
                At the ONU the value should be zero."
       REFERENCE   "[802.3ah], 30.3.5.1.9."
       ::= { hpnicfDot3MpcpStatEntry 11 }

   hpnicfDot3MpcpRxGate OBJECT-TYPE
       SYNTAX  Counter32
       UNITS      "frames"
       MAX-ACCESS  read-only
       STATUS  current
       DESCRIPTION
               "A count of the number of times a GATE MPCP frames
                reception occurs. A single counter at the ONU and a set
                of counters, one for each LLID ,at the OLT. Increment
                the counter by one for each GATE MPCP frame received,
                for each LLID, as defined in [802.3ah] clause 64. This
                counter is mandatory for an ONU and for an OLT. At the
                OLT the value should be zero."
       REFERENCE   "[802.3ah], 30.3.5.1.14."
       ::= { hpnicfDot3MpcpStatEntry 12 }

   hpnicfDot3MpcpTxRegister OBJECT-TYPE
       SYNTAX  Counter32
       UNITS      "frames"
       MAX-ACCESS  read-only
       STATUS  current
       DESCRIPTION
               "A count of the number of times a REGISTER MPCP frames
                transmission occurs. A set of counters, one for each
                LLID, at the OLT. Increment the counter by one for each
                REGISTER MPCP frame transmitted, for each LLID, as
                defined in [802.3ah] clause 64. This counter is
                mandatory for an OLT. This attribute is relevant for an
                OLT and an ONU. At the ONU the value should be zero."
       REFERENCE   "[802.3ah], 30.3.5.1.11."
       ::= { hpnicfDot3MpcpStatEntry 13 }

   hpnicfDot3MpcpRxRegister OBJECT-TYPE
       SYNTAX  Counter32
       UNITS      "frames"
       MAX-ACCESS  read-only
       STATUS  current
       DESCRIPTION
               "A count of the number of times a REGISTER MPCP frames
                reception occurs. A single counter at the ONU and a set
                of counters, one for each LLID, at the OLT. Increment
                the counter by one for each REGISTER MPCP frame
                received, for each LLID, as defined in [802.3ah] clause
                64. This counter is mandatory for an ONU and for an OLT.
                at the OLT the value should be zero."
       REFERENCE   "[802.3ah], 30.3.5.1.16."
       ::= { hpnicfDot3MpcpStatEntry 14 }

   hpnicfDot3MpcpRxNotSupportedMPCP OBJECT-TYPE
       SYNTAX  Counter32
       UNITS      "frames"
       MAX-ACCESS  read-only
       STATUS  current
       DESCRIPTION
               "A count of the number of times a non-supported MPCP
                frames reception occurs. A single counter at the ONU and
                a set of counters, one for each LLID, at the OLT.
                Increment the counter by one for each non-supported MPCP
                frame received, for each LLID, as defined in [802.3ah]
                clause 64. This counter is mandatory for an ONU and for
                an OLT."
       ::= { hpnicfDot3MpcpStatEntry 15 }




        -- Conformance Statements

   -- Conformance Groups

   hpnicfDot3MpcpGroups      OBJECT IDENTIFIER ::= { hpnicfDot3MpcpConformance 1 }

   hpnicfDot3MpcpGroupBase OBJECT-GROUP
       OBJECTS {
               hpnicfDot3MpcpID,
               hpnicfDot3MpcpOperStatus,
               hpnicfDot3MpcpMode,
               hpnicfDot3MpcpLinkID,
               hpnicfDot3MpcpRemoteMACAddress,
               hpnicfDot3MpcpRegistrationState,
               hpnicfDot3MpcpMaximumPendingGrants,
               hpnicfDot3MpcpAdminState
       }
       STATUS  current
       DESCRIPTION
               "A collection of objects of dot3 Mpcp Basic entity state
               definition."
       ::= { hpnicfDot3MpcpGroups 1 }

   hpnicfDot3MpcpGroupParam OBJECT-GROUP
       OBJECTS {
               hpnicfDot3MpcpTransmitElapsed,
               hpnicfDot3MpcpReceiveElapsed,
               hpnicfDot3MpcpRoundTripTime,
               hpnicfDot3MpcpOnTime,
               hpnicfDot3MpcpOffTime,
               hpnicfDot3MpcpSyncTime
       }
       STATUS  current
       DESCRIPTION
               "A collection of objects of dot3 Mpcp for P2MP
                parameters."
       ::= { hpnicfDot3MpcpGroups 2 }

   hpnicfDot3MpcpGroupStat OBJECT-GROUP
       OBJECTS {
               hpnicfDot3MpcpMACCtrlFramesTransmitted,
               hpnicfDot3MpcpMACCtrlFramesReceived,
               hpnicfDot3MpcpDiscoveryWindowsSent,
               hpnicfDot3MpcpDiscoveryTimeout ,
               hpnicfDot3MpcpTxRegRequest,
               hpnicfDot3MpcpRxRegRequest,
               hpnicfDot3MpcpTxRegAck,
               hpnicfDot3MpcpRxRegAck,
               hpnicfDot3MpcpTxReport,
               hpnicfDot3MpcpRxReport,
               hpnicfDot3MpcpTxGate,
               hpnicfDot3MpcpRxGate,
               hpnicfDot3MpcpTxRegister,
               hpnicfDot3MpcpRxRegister,
               hpnicfDot3MpcpRxNotSupportedMPCP
       }
       STATUS  current
       DESCRIPTION
               "A collection of objects of dot3 Mpcp Statistics"
       ::= { hpnicfDot3MpcpGroups 3 }


   -- Compliance

   hpnicfDot3MpcpCompliances OBJECT IDENTIFIER ::= { hpnicfDot3MpcpConformance 2 }

   hpnicfDot3MpcpCompliance MODULE-COMPLIANCE
       STATUS      current
       DESCRIPTION "The compliance statement for Multi-point
                    control protocol interfaces."

       MODULE  -- this module
       MANDATORY-GROUPS { hpnicfDot3MpcpGroupBase }

      GROUP       hpnicfDot3MpcpGroupParam
      DESCRIPTION "This group is mandatory for all MPCP supporting
                   interfaces for configuration of the Multipoint
                   Parameters."
      GROUP       hpnicfDot3MpcpGroupStat
      DESCRIPTION "This group is mandatory for all MPCP supporting
                   interfaces for Statistics collection."
      ::= { hpnicfDot3MpcpCompliances 1 }


   -- Editor-s note:   OMPEmulation managed object definitions


   hpnicfDot3OmpEmulationMIB OBJECT IDENTIFIER ::= { hpnicfDot3EfmeponMIB 2 }

   hpnicfDot3OmpEmulationObjects OBJECT IDENTIFIER ::= { hpnicfDot3OmpEmulationMIB 1 }

   hpnicfDot3OmpeConformance OBJECT IDENTIFIER ::= { hpnicfDot3OmpEmulationMIB 2 }


   hpnicfDot3OmpEmulationTable OBJECT-TYPE
       SYNTAX  SEQUENCE OF HpnicfDot3OmpEmulationEntry
       MAX-ACCESS  not-accessible
       STATUS  current
       DESCRIPTION
               "Table for dot3 OmpEmulation MIB modules."
       ::= { hpnicfDot3OmpEmulationObjects 1 }

   hpnicfDot3OmpEmulationEntry OBJECT-TYPE
       SYNTAX  HpnicfDot3OmpEmulationEntry
       MAX-ACCESS  not-accessible
       STATUS  current
       DESCRIPTION
               "An entry in the dot3 OmpEmulation MIB modules table."
       INDEX  { ifIndex }
       ::= { hpnicfDot3OmpEmulationTable 1 }

       HpnicfDot3OmpEmulationEntry ::=
       SEQUENCE {
               hpnicfDot3OmpEmulationID            Integer32,
               hpnicfDot3OmpEmulationType               INTEGER
       }

   hpnicfDot3OmpEmulationID OBJECT-TYPE
       SYNTAX  Integer32
       MAX-ACCESS  read-only
       STATUS  current
       DESCRIPTION
               "The value of hpnicfDot3OmpEmulationID is assigned so as to
                uniquely identify a OMPEmulation entity among the
                subordinate managed objects of the containing object.
                The value is mandated for an ONU."
       REFERENCE   "[802.3ah], 30.3.7.1.1."
       ::= { hpnicfDot3OmpEmulationEntry 1 }

   hpnicfDot3OmpEmulationType OBJECT-TYPE
       SYNTAX  INTEGER {
               unknown(1),
               olt(2),
               onu(3)
       }
       MAX-ACCESS  read-only
       STATUS  current
       DESCRIPTION
               "A read-only value that indicates that mode of operation
                of the Reconciliation Sublayer for Point to Point
                Emulation (see [802.3ah] clause 65.1). unknown(1) value
                is assigned in initializing, true state or type not yet
                known. olt(2) value is assigned when Sublayer operating
                in OLT mode. onu(3) value is assigned when Sublayer
                operating in ONU mode."
       REFERENCE   "[802.3ah], 30.3.7.1.2."
       ::= { hpnicfDot3OmpEmulationEntry 2 }

   hpnicfDot3OmpEmulationStatTable OBJECT-TYPE
       SYNTAX     SEQUENCE OF HpnicfDot3OmpEmulationStatEntry
       MAX-ACCESS not-accessible
       STATUS     current
       DESCRIPTION
               "This table defines the list of statistics counters of
                [802.3ah] clause 65 OMP interface."
       ::= { hpnicfDot3OmpEmulationObjects 2 }

   hpnicfDot3OmpEmulationStatEntry OBJECT-TYPE
       SYNTAX     HpnicfDot3OmpEmulationStatEntry
       MAX-ACCESS not-accessible
       STATUS     current
       DESCRIPTION
               "Table entries for Table of statistics counters of
                [802.3ah] clause 65 OMP interface."
       INDEX       { ifIndex }
       ::= { hpnicfDot3OmpEmulationStatTable 1 }

   HpnicfDot3OmpEmulationStatEntry ::=
       SEQUENCE {
               hpnicfDot3OmpEmulationSLDErrors                 Counter32,
               hpnicfDot3OmpEmulationCRC8Errors                Counter32,
               hpnicfDot3OmpEmulationBadLLID                   Counter32,
               hpnicfDot3OmpEmulationGoodLLID                  Counter32,
               hpnicfDot3OmpEmulationOnuPonCastLLID            Counter32,
               hpnicfDot3OmpEmulationOltPonCastLLID            Counter32,
               hpnicfDot3OmpEmulationBroadcastLLIDNotOnuID     Counter32,
               hpnicfDot3OmpEmulationOnuLLIDNotBroadcast       Counter32,
               hpnicfDot3OmpEmulationBroadcastLLIDPlusOnuId    Counter32,
               hpnicfDot3OmpEmulationNotBroadcastLLIDNotOnuId  Counter32
       }

   hpnicfDot3OmpEmulationSLDErrors OBJECT-TYPE
       SYNTAX  Counter32
       UNITS      "frames"
       MAX-ACCESS  read-only
       STATUS  current
       DESCRIPTION
               "A count of frames received that do not contain a valid
                SLD field as defined in [802.3ah] clause 65.1.3.3.1.
                This attribute is mandatory for an OLT and optional for
                an ONU."
       REFERENCE   "[802.3ah], 30.3.7.1.3."
       ::= { hpnicfDot3OmpEmulationStatEntry 1 }

   hpnicfDot3OmpEmulationCRC8Errors OBJECT-TYPE
       SYNTAX  Counter32
       UNITS      "frames"
       MAX-ACCESS  read-only
       STATUS  current
       DESCRIPTION
               "A count of frames received that contain a valid SLD
                field, as defined in [802.3ah] clause 65.1.3.3.1, but do
                not pass the CRC-8 check as defined in [802.3ah] clause
                65.1.3.3.3. This attribute is mandatory for an OLT and
                for an ONU."
       REFERENCE   "[802.3ah], 30.3.7.1.4."
       ::= { hpnicfDot3OmpEmulationStatEntry 2 }


   hpnicfDot3OmpEmulationBadLLID OBJECT-TYPE
       SYNTAX  Counter32
       UNITS      "frames"
       MAX-ACCESS  read-only
       STATUS  current
       DESCRIPTION
               "A count of frames received that contain a valid SLD
                field, as defined in [802.3ah] clause 65.1.3.3.1, and
                pass the CRC-8 check, as defined in [802.3ah] clause
                65.1.3.3.3, but are discarded due to the LLID check as
                defined in [802.3ah] clause 65.1.3.3.2.
                This attribute is relevant for an OLT and an ONU."
       REFERENCE   "[802.3ah], 30.3.7.1.8."
       ::= { hpnicfDot3OmpEmulationStatEntry 3 }

   hpnicfDot3OmpEmulationGoodLLID OBJECT-TYPE
       SYNTAX  Counter32
       UNITS      "frames"
       MAX-ACCESS  read-only
       STATUS  current
       DESCRIPTION
               "A count of frames received that contain a valid SLD
                field, as defined in [802.3ah] clause 65.1.3.3.1, and
                pass the CRC-8 check, as defined in [802.3ah] clause
                65.1.3.3.3.
                This attribute is relevant for an OLT and an ONU."
       REFERENCE   "[802.3ah], 30.3.7.1.5."
       ::= { hpnicfDot3OmpEmulationStatEntry 4 }


   hpnicfDot3OmpEmulationOnuPonCastLLID OBJECT-TYPE
       SYNTAX  Counter32
       UNITS      "frames"
       MAX-ACCESS  read-only
       STATUS  current
       DESCRIPTION
               "A count of frames received that contain a valid SLD
                field in an ONU, as defined in [802.3ah] 65.1.3.3.1,
                passes the CRC-8 check, as defined in [802.3ah]
                65.1.3.3.3, and the frame meets the rule for acceptance
                defined in [802.3ah] 65.1.3.3.2."
       REFERENCE   "[802.3ah], 30.3.7.1.6."
       ::= { hpnicfDot3OmpEmulationStatEntry 5 }

   hpnicfDot3OmpEmulationOltPonCastLLID OBJECT-TYPE
       SYNTAX  Counter32
       UNITS      "frames"
       MAX-ACCESS  read-only
       STATUS  current
       DESCRIPTION
               "A count of frames received that contain a valid SLD
                field in an OLT, as defined in [802.3ah] 65.1.3.3.1,
                passes the CRC-8 check, as defined in [802.3ah]
                65.1.3.3.3, and the frame meets the rule for acceptance
                defined in [802.3ah] 65.1.3.3.2."
       REFERENCE   "[802.3ah], 30.3.7.1.7."
       ::= { hpnicfDot3OmpEmulationStatEntry 6 }

   hpnicfDot3OmpEmulationBroadcastLLIDNotOnuID OBJECT-TYPE
       SYNTAX  Counter32
       UNITS      "frames"
       MAX-ACCESS  read-only
       STATUS  current
       DESCRIPTION
               "A count of frames received that contain a valid SLD
                field in a OLT, as defined in [802.3ah] clause
                65.1.3.3.1, and pass the CRC-8 check, as defined in
                [802.3ah] clause 65.1.3.3.3, and contain broadcast LLID
                as defined in [802.3ah] clause 65.
                This attribute is mandatory for an OLT and for an ONU."
       ::= { hpnicfDot3OmpEmulationStatEntry 7 }

   hpnicfDot3OmpEmulationOnuLLIDNotBroadcast OBJECT-TYPE
       SYNTAX  Counter32
       UNITS      "frames"
       MAX-ACCESS  read-only
       STATUS  current
       DESCRIPTION
               "A count of frames received that contain a valid SLD
                field in a OLT, as defined in [802.3ah] clause
                65.1.3.3.1, and pass the CRC-8 check, as defined in
                [802.3ah] clause 65.1.3.3.3, and contain the ONU's LLID
                as defined in [802.3ah] clause 65. This attribute is
                mandatory for an ONU and mandatory for an OLT (a
                counter per LLID)."
       ::= { hpnicfDot3OmpEmulationStatEntry 8 }

   hpnicfDot3OmpEmulationBroadcastLLIDPlusOnuId OBJECT-TYPE
       SYNTAX  Counter32
       UNITS      "frames"
       MAX-ACCESS  read-only
       STATUS  current
       DESCRIPTION
               "A count of frames received that contain a valid SLD
                field in a OLT, as defined in [802.3ah] clause
                65.1.3.3.1, and pass the CRC-8 check, as defined in
                [802.3ah] clause 65.1.3.3.3, and contain the broadcast
                LLID plus ONU's LLID (frame reflected) as defined in
                [802.3ah] clause 65. This attribute is mandatory for an
                ONU and mandatory for an OLT (a counter per LLID)."
       ::= { hpnicfDot3OmpEmulationStatEntry 9 }

   hpnicfDot3OmpEmulationNotBroadcastLLIDNotOnuId OBJECT-TYPE
       SYNTAX  Counter32
       UNITS      "frames"
       MAX-ACCESS  read-only
       STATUS  current
       DESCRIPTION
               "A count of frames received that contain a valid SLD
                field in a OLT, as defined in [802.3ah] clause
                65.1.3.3.1, and pass the CRC-8 check, as defined in
                [802.3ah] clause 65.1.3.3.3, and does not contain the
                ONU's LLID as defined in [802.3ah] clause 65. This
                attribute is mandatory for an ONU"
       ::= { hpnicfDot3OmpEmulationStatEntry 10 }


        -- Conformance Statements

   -- Conformance Groups

   hpnicfDot3OmpeGroups OBJECT IDENTIFIER ::= { hpnicfDot3OmpeConformance 1 }


   hpnicfDot3OmpeGroupID OBJECT-GROUP
       OBJECTS {
               hpnicfDot3OmpEmulationID,
               hpnicfDot3OmpEmulationType

       }
       STATUS  current
       DESCRIPTION
               "A collection of objects of dot3 OMP emulation ID entity
                state definition."
       ::= { hpnicfDot3OmpeGroups 1 }


   hpnicfDot3OmpeGroupStat OBJECT-GROUP
       OBJECTS {
               hpnicfDot3OmpEmulationSLDErrors,
               hpnicfDot3OmpEmulationCRC8Errors,
               hpnicfDot3OmpEmulationBadLLID,
               hpnicfDot3OmpEmulationGoodLLID,
               hpnicfDot3OmpEmulationOnuPonCastLLID,
               hpnicfDot3OmpEmulationOltPonCastLLID,
               hpnicfDot3OmpEmulationBroadcastLLIDNotOnuID,
               hpnicfDot3OmpEmulationOnuLLIDNotBroadcast,
               hpnicfDot3OmpEmulationBroadcastLLIDPlusOnuId,
               hpnicfDot3OmpEmulationNotBroadcastLLIDNotOnuId
       }
       STATUS  current
       DESCRIPTION
               "A collection of objects of dot3 OMP emulation
                Statistics"
       ::= { hpnicfDot3OmpeGroups 2 }


   -- Compliance

   hpnicfDot3OmpeCompliances OBJECT IDENTIFIER ::= { hpnicfDot3OmpeConformance 2 }

   hpnicfDot3OmpeCompliance MODULE-COMPLIANCE
       STATUS      current
       DESCRIPTION "The compliance statement for OMPEmulation
                    interfaces."
       MODULE  -- this module
       MANDATORY-GROUPS { hpnicfDot3OmpeGroupID }

       GROUP       hpnicfDot3OmpeGroupStat
       DESCRIPTION "This group is mandatory for all OMPemulation
                    supporting interfaces for Statistics collection."

       ::= { hpnicfDot3OmpeCompliances 1 }




   -- Editor-s note:   MAU managed object definitions (30.5.1)

   hpnicfDot3EponMauMIB OBJECT IDENTIFIER ::= { hpnicfDot3EfmeponMIB 3 }

   hpnicfDot3EponMauObjects OBJECT IDENTIFIER ::= { hpnicfDot3EponMauMIB 1 }

   hpnicfDot3EponMauConformance OBJECT IDENTIFIER ::= { hpnicfDot3EponMauMIB 2 }

   hpnicfDot3EponMauTable OBJECT-TYPE
       SYNTAX  SEQUENCE OF HpnicfDot3EponMauEntry
       MAX-ACCESS  not-accessible
       STATUS  current
       DESCRIPTION
               "Table for dot3 MAU EPON MIB modules."
       ::= { hpnicfDot3EponMauObjects 1 }

   hpnicfDot3EponMauEntry OBJECT-TYPE
       SYNTAX  HpnicfDot3EponMauEntry
       MAX-ACCESS  not-accessible
       STATUS  current
       DESCRIPTION
               "An entry in the dot3 MAU EPON MIB modules table."
       INDEX  { ifIndex }
       ::= { hpnicfDot3EponMauTable 1 }

   HpnicfDot3EponMauEntry ::=
       SEQUENCE {
               hpnicfDot3EponMauPCSCodingViolation           Counter32,
               hpnicfDot3EponMauFecAbility                   INTEGER,
               hpnicfDot3EponMauFecMode                      INTEGER,
               hpnicfDot3EponMauFECCorrectedBlocks           Counter32,
               hpnicfDot3EponMauFECUncorrectableBlocks       Counter32,
               hpnicfDot3EponMauBufferHeadCodingViolation    Counter32
       }


   hpnicfDot3EponMauPCSCodingViolation OBJECT-TYPE
       SYNTAX  Counter32
       UNITS      "octets"
       MAX-ACCESS  read-only
       STATUS  current
       DESCRIPTION
               "For 100 Mb/ s operation it is a count of the number of
                times an invalid code-group is received, other than the
                /H/ code-group. For 1000 Mb/ s operation it is a count
                of the number of times an invalid codegroup is received,
                other than the /V/ code-group."
       REFERENCE   "[802.3ah], 30.5.1.1.12."
       ::= { hpnicfDot3EponMauEntry 1 }

   hpnicfDot3EponMauFecAbility OBJECT-TYPE
       SYNTAX  INTEGER {
               unknown (1),
               nonsupported (2),
               supported (3)
       }
       MAX-ACCESS  read-only
       STATUS  current
       DESCRIPTION
               "A read-only value that indicates the support of
                operation of the 1000BASE-PX PHY optional FEC Sublayer
                for Forward error correction see [802.3ah] clause 65.2).
                unknown(1) value is assigned in initializing, for non
                FEC support state or type not yet known. nonsupported(2)
                value is assigned when Sublayer is not support.
                supported(3) value is assigned when Sublayer is
                supported."
       REFERENCE   "[802.3ah], 30.5.1.1.13."
       ::= { hpnicfDot3EponMauEntry 2 }

   hpnicfDot3EponMauFecMode OBJECT-TYPE
       SYNTAX  INTEGER {
               unknown (1),
               disabled (2),
               enabled (3)
       }
       MAX-ACCESS  read-write
       STATUS  current
       DESCRIPTION
               "A read-write value that indicates the mode of operation
                of the 1000BASE-PX PHY optional FEC Sublayer for Forward
                error correction see [802.3ah] clause 65.2).
                A GET operation returns the current mode of operation
                the PHY. A SET operation changes the mode of operation
                of the PHY to the indicated value. unknown(1) value is
                assigned in initializing, for non FEC support state or
                type not yet known. disabled(2) value is assigned when
                Sublayer operating in disabled mode. enabled(3) value is
                assigned when Sublayer operating in FEC mode. writing
                can be done all the time."
       REFERENCE   "[802.3ah], 30.5.1.1.14."
       DEFVAL { 1 }
       ::= { hpnicfDot3EponMauEntry 3 }

   hpnicfDot3EponMauFECCorrectedBlocks OBJECT-TYPE
       SYNTAX  Counter32
       MAX-ACCESS  read-only
       STATUS  current
       DESCRIPTION
               "For 10PASS-TS, 2BASE-TL and 1000BASE-PX PHYs, a count
                of corrected FEC blocks. This counter will not increment
                for other PHY Types. Increment the counter by one for
                each received block that is corrected by the FEC
                function in the PHY."
       REFERENCE   "[802.3ah], 30.5.1.1.15."
       ::= { hpnicfDot3EponMauEntry 4 }

   hpnicfDot3EponMauFECUncorrectableBlocks OBJECT-TYPE
       SYNTAX  Counter32
       MAX-ACCESS  read-only
       STATUS  current
       DESCRIPTION
               "For 10PASS-TS, 2BASE-TL and 1000BASE-PX PHYs, a count of
                uncorrectable FEC blocks. This counter will not
                increment for other PHY Types. Increment the counter by
                one for each FEC block that is determined to be
                uncorrectable by the FEC function in the PHY."
       REFERENCE   "[802.3ah], 30.5.1.1.16."
       ::= { hpnicfDot3EponMauEntry 5 }

   hpnicfDot3EponMauBufferHeadCodingViolation OBJECT-TYPE
       SYNTAX  Counter32
       UNITS      "octets"
       MAX-ACCESS  read-only
       STATUS  current
       DESCRIPTION
               "For 1000 Mbps operation it is a counts of the number of
                invalid code-group received directly from the link."
       ::= { hpnicfDot3EponMauEntry 6 }



   -- Defining EPON MAU types
   -- Editor's Note: This section should be added to 802.3 MAU MIB
   -- module RFC. Preference would be that the MAU MIB module
   -- structure would change so that it is re-written as an
   -- IANA-maintained module.

   hpnicfDot3EponMauType OBJECT IDENTIFIER ::= { hpnicfDot3EponMauMIB 3 }

   hpnicfEponMauType1000BasePXOLT OBJECT-IDENTITY
       STATUS      current
       DESCRIPTION "Multipoint MAC Control (per 802.3 section 64,65) OLT
                    (master), unknown PMD"
       REFERENCE   "[802.3ah], 30.5.1.1.2."
       ::= { hpnicfDot3EponMauType 1 }

   hpnicfEponMauType1000BasePXONU OBJECT-IDENTITY
       STATUS      current
       DESCRIPTION "Multipoint MAC Control (per 802.3 section 64,65),ONU
       (slave), unknown PMD"
       REFERENCE   "[802.3ah], 30.5.1.1.2."
       ::= { hpnicfDot3EponMauType 2 }

   hpnicfEponMauType1000BasePX10DOLT OBJECT-IDENTITY
       STATUS      current
       DESCRIPTION "EPON over 10K link, downlink (per 802.3 section 60),
                    OLT side"
       REFERENCE   "[802.3ah], 30.5.1.1.2."
       ::= { hpnicfDot3EponMauType 3 }

   hpnicfEponMauType1000BasePX10DONU OBJECT-IDENTITY
       STATUS      current
       DESCRIPTION "EPON over 10K link, downlink (per 802.3 section 60),
                    ONU side"
       REFERENCE   "[802.3ah], 30.5.1.1.2."
       ::= { hpnicfDot3EponMauType 4 }

   hpnicfEponMauType1000BasePX10UOLT OBJECT-IDENTITY
       STATUS      current
       DESCRIPTION "EPON over 10K link, uplink (per 802.3 section 60),
                    OLT side"
       REFERENCE   "[802.3ah], 30.5.1.1.2."
       ::= { hpnicfDot3EponMauType 5 }

   hpnicfEponMauType1000BasePX10UONU OBJECT-IDENTITY
       STATUS      current
       DESCRIPTION "EPON over 10K link, uplink (per 802.3 section 60),
                    ONU side"
       REFERENCE   "[802.3ah], 30.5.1.1.2."
       ::= { hpnicfDot3EponMauType 6 }


   hpnicfEponMauType1000BasePX20DOLT OBJECT-IDENTITY
       STATUS      current
       DESCRIPTION "EPON over 20K link, downlink (per 802.3 section 60),
                    OLT side"
       REFERENCE   "[802.3ah], 30.5.1.1.2."
       ::= { hpnicfDot3EponMauType 7 }

   hpnicfEponMauType1000BasePX20DONU OBJECT-IDENTITY
       STATUS      current
       DESCRIPTION "EPON over 20K link, downlink (per 802.3 section 60),
                    ONU side"
       REFERENCE   "[802.3ah], 30.5.1.1.2."
       ::= { hpnicfDot3EponMauType 8 }

   hpnicfEponMauType1000BasePX20UOLT OBJECT-IDENTITY
       STATUS      current
       DESCRIPTION "EPON over 20K link, uplink (per 802.3 section 60),
                    OLT side"
       REFERENCE   "[802.3ah], 30.5.1.1.2."
       ::= { hpnicfDot3EponMauType 9 }

   hpnicfEponMauType1000BasePX20UONU OBJECT-IDENTITY
       STATUS      current
       DESCRIPTION "EPON over 20K link, uplink (per 802.3 section 60),
                    ONU side"
       REFERENCE   "[802.3ah], 30.5.1.1.2."
       ::= { hpnicfDot3EponMauType 10 }


        -- Conformance Statements

   -- Conformance Groups

   hpnicfDot3EponMauGroups OBJECT IDENTIFIER ::= { hpnicfDot3EponMauConformance 1 }

   hpnicfDot3EponMauGroupAll OBJECT-GROUP
       OBJECTS {
               hpnicfDot3EponMauPCSCodingViolation
       }
       STATUS  current
       DESCRIPTION
               "A collection of objects of dot3 MAU definition."
       ::= { hpnicfDot3EponMauGroups 1 }

   hpnicfDot3EponMauGroupFEC OBJECT-GROUP
       OBJECTS {
               hpnicfDot3EponMauFecAbility,
               hpnicfDot3EponMauFecMode,
               hpnicfDot3EponMauFECCorrectedBlocks,
               hpnicfDot3EponMauFECUncorrectableBlocks,
               hpnicfDot3EponMauBufferHeadCodingViolation
       }
       STATUS  current
       DESCRIPTION
               "A collection of objects of FEC group definition."
       ::= { hpnicfDot3EponMauGroups 2 }


   -- Compliance

   hpnicfDot3EponMauCompliances OBJECT IDENTIFIER ::= { hpnicfDot3EponMauConformance 2 }

   hpnicfDot3EponMauCompliance MODULE-COMPLIANCE
       STATUS      current
       DESCRIPTION "The compliance statement for MAU EPON interfaces."

       MODULE  -- this module
       MANDATORY-GROUPS { hpnicfDot3EponMauGroupAll }

       GROUP       hpnicfDot3EponMauGroupFEC
       DESCRIPTION "This group is mandatory for all EPON MAU devices
                    Supporting FEC functionality as for Definitions and
                    BER Statistics collection."

       ::= { hpnicfDot3EponMauCompliances 1 }


   END
