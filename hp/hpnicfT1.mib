-- =============================================================
-- Copyright (c) 2010-2013 Hewlett-Packard Development Company, L.P.
--
-- Description:
-- Reference:  extension of RFC 1213 and RFC 2233
-- Version: V1.2
-- History:
--   V1.0 2004-12-01
--        Initial Version  by lizhiyong and fangmin
--   V1.1 2009-06-08 modified by TONGWEI
--        Added hpnicft1Table and hpnicft1InterfaceTable
--   V1.2 2012-07-16 modified SYNTAX of hpnicft1Clock by shuaixiaojuan.
-- =============================================================
HPN-ICF-T1-MIB DEFINITIONS ::= BEGIN

IMPORTS
        MODULE-IDENTITY,
        OBJECT-TYPE,
        Integer32,
        Counter32
                FROM SNMPv2-SMI
        TEXTUAL-CONVENTION
                FROM SNMPv2-TC
        MODULE-COMPLIANCE,
        OBJECT-GROUP
                FROM SNMPv2-CONF
        ifIndex
                FROM RFC1213-MIB
        hpnicfCommon
                FROM HPN-ICF-OID-MIB;



-- =============================================================
-- T1 Module
-- =============================================================
hpnicfT1    MODULE-IDENTITY
        LAST-UPDATED "201207161741Z"
        ORGANIZATION
            ""
        CONTACT-INFO
            ""
        DESCRIPTION
             "This MIB provides T1 interface information that are
             excluded by RFC 1213 and RFC 2233"
        REVISION        "201207161741Z"
        DESCRIPTION
                "To fix bugs in the MIB file."
        REVISION        "200906081741Z"
        DESCRIPTION
                "To fix bugs in the MIB file."
        REVISION        "200412011436Z"
        DESCRIPTION
                "Initial version of this MIB module."
        ::= { hpnicfCommon 29 }


hpnicft1InterfaceStatusTable OBJECT-TYPE
        SYNTAX      SEQUENCE OF HpnicfT1InterfaceStatusEntry
        MAX-ACCESS   not-accessible
        STATUS       current
        DESCRIPTION
         "This table contains interface packet statistics  "
        ::= { hpnicfT1 1 }

hpnicft1InterfaceStatusEntry OBJECT-TYPE
        SYNTAX         HpnicfT1InterfaceStatusEntry
        MAX-ACCESS     not-accessible
        STATUS         current
        DESCRIPTION
         "This  entry contains interface packet statistics.
         The index of this Entry is ifIndex defined in ifTable
         of RFC1213-MIB"
        INDEX { ifIndex }
        ::= { hpnicft1InterfaceStatusTable 1 }

HpnicfT1InterfaceStatusEntry ::= SEQUENCE  {
        hpnicft1InterfaceInErrs            Counter32,
        hpnicft1InterfaceInRuntsErrs       Counter32,
        hpnicft1InterfaceInGiantsErrs      Counter32,
        hpnicft1InterfaceInCrcErrs         Counter32,
        hpnicft1InterfaceInAlignErrs       Counter32,
        hpnicft1InterfaceInOverRunsErrs    Counter32,
        hpnicft1InterfaceInDribblesErrs    Counter32,
        hpnicft1InterfaceInAbortedSeqErrs  Counter32,
        hpnicft1InterfaceInNoBufferErrs    Counter32,
        hpnicft1InterfaceInFramingErrs     Counter32,
        hpnicft1InterfaceOutputErrs        Counter32,
        hpnicft1InterfaceOutUnderRunErrs   Counter32,
        hpnicft1InterfaceOutCollisonsErrs  Counter32,
        hpnicft1InterfaceOutDeferedErrs    Counter32
        }

hpnicft1InterfaceInErrs        OBJECT-TYPE
        SYNTAX          Counter32
        MAX-ACCESS      read-only
        STATUS          current
        DESCRIPTION
         "The total number of error received on this interface"
        ::= { hpnicft1InterfaceStatusEntry 1 }

hpnicft1InterfaceInRuntsErrs   OBJECT-TYPE
        SYNTAX          Counter32
        MAX-ACCESS      read-only
        STATUS          current
        DESCRIPTION
         "The number of Runts Error(too short packet) received on this interface"
        ::= { hpnicft1InterfaceStatusEntry 2 }

hpnicft1InterfaceInGiantsErrs OBJECT-TYPE
        SYNTAX          Counter32
        MAX-ACCESS      read-only
        STATUS          current
        DESCRIPTION
         "The number of Giants Error(too long packet) received on this interface"
        ::= { hpnicft1InterfaceStatusEntry 3 }

hpnicft1InterfaceInCrcErrs     OBJECT-TYPE
        SYNTAX          Counter32
        MAX-ACCESS      read-only
        STATUS          current
        DESCRIPTION
         "The number of CRC Error received on this interface"
        ::= { hpnicft1InterfaceStatusEntry 4 }

hpnicft1InterfaceInAlignErrs   OBJECT-TYPE
        SYNTAX          Counter32
        MAX-ACCESS      read-only
        STATUS          current
        DESCRIPTION
         "The number of Align Error received on this interface"
        ::= { hpnicft1InterfaceStatusEntry 5 }

hpnicft1InterfaceInOverRunsErrs OBJECT-TYPE
        SYNTAX           Counter32
        MAX-ACCESS       read-only
        STATUS          current
        DESCRIPTION
         "The number of Over Runs Error received on this interface"
        ::= { hpnicft1InterfaceStatusEntry 6 }

hpnicft1InterfaceInDribblesErrs  OBJECT-TYPE
        SYNTAX            Counter32
        MAX-ACCESS        read-only
        STATUS            current
        DESCRIPTION
         "The number of dribble packets received"
        ::= { hpnicft1InterfaceStatusEntry 7 }

hpnicft1InterfaceInAbortedSeqErrs    OBJECT-TYPE
        SYNTAX                Counter32
        MAX-ACCESS            read-only
        STATUS                current
        DESCRIPTION
         "The number of AbortedSeq Error received on this interface"
        ::= { hpnicft1InterfaceStatusEntry 8 }

hpnicft1InterfaceInNoBufferErrs      OBJECT-TYPE
        SYNTAX                Counter32
        MAX-ACCESS            read-only
        STATUS                current
        DESCRIPTION
         "The number of Error (no buffer available)"
        ::= { hpnicft1InterfaceStatusEntry 9 }

hpnicft1InterfaceInFramingErrs       OBJECT-TYPE
        SYNTAX                Counter32
        MAX-ACCESS            read-only
        STATUS                current
        DESCRIPTION
         "The number of framing Errors"
        ::= { hpnicft1InterfaceStatusEntry 10 }

hpnicft1InterfaceOutputErrs          OBJECT-TYPE
        SYNTAX                Counter32
        MAX-ACCESS            read-only
        STATUS                current
        DESCRIPTION
         "The number of total Error transmited on this interface"
        ::= { hpnicft1InterfaceStatusEntry 11 }

hpnicft1InterfaceOutUnderRunErrs     OBJECT-TYPE
        SYNTAX                Counter32
        MAX-ACCESS            read-only
        STATUS                current
        DESCRIPTION
         "The number of UnderRun Error transmited on this interface"
        ::= { hpnicft1InterfaceStatusEntry 12 }

hpnicft1InterfaceOutCollisonsErrs    OBJECT-TYPE
        SYNTAX                Counter32
        MAX-ACCESS            read-only
        STATUS                current
        DESCRIPTION
         "The number of Collisions Error transmited on this interface"
        ::= { hpnicft1InterfaceStatusEntry 13 }

hpnicft1InterfaceOutDeferedErrs      OBJECT-TYPE
        SYNTAX                Counter32
        MAX-ACCESS            read-only
        STATUS                current
        DESCRIPTION
         "The number of Deferred Error transmited on this interface"
        ::= { hpnicft1InterfaceStatusEntry 14 }

hpnicft1Table OBJECT-TYPE
        SYNTAX      SEQUENCE OF HpnicfT1Entry
        MAX-ACCESS   not-accessible
        STATUS       current
        DESCRIPTION
         "A list of T1 interface entries."
        ::= { hpnicfT1 2 }

hpnicft1Entry OBJECT-TYPE
        SYNTAX         HpnicfT1Entry
        MAX-ACCESS     not-accessible
        STATUS         current
        DESCRIPTION
         "This entry contains T1 interface management information."
        INDEX { ifIndex }
        ::= { hpnicft1Table 1 }

HpnicfT1TimeSlot ::= TEXTUAL-CONVENTION
        STATUS      current
        DESCRIPTION
            "Each octet within this value specifies a set of time
            slots, with the first octet specifying time slot 1 through
            8, the second octet specifying time slots 9 through 16, etc.
            Within each octet, the most significant bit represents
            the highest numbered time slot, and the least significant bit
            represents the lowest numbered time slot.  Thus, each time slot
            of the T1 is represented by a single bit within the
            value of this object.  If that bit has a value of '1'
            then that time slot is included in the set of time slots;
            the time slot is not included if its bit has a value of '0'."
        SYNTAX      OCTET STRING(SIZE (3))

HpnicfT1Entry ::= SEQUENCE  {
        hpnicft1Type              BITS,
        hpnicft1Clock             INTEGER,
        hpnicft1FrameFormat       INTEGER,
        hpnicft1LineCode          INTEGER,
        hpnicft1PriSetTimeSlot    HpnicfT1TimeSlot,
        hpnicft1DChannelIndex     Integer32,
        hpnicft1SubScribLineChannelIndex Integer32
        }

hpnicft1Type              OBJECT-TYPE
        SYNTAX  BITS {
                    voice(0)
                }
        MAX-ACCESS      read-only
        STATUS          current
        DESCRIPTION
         "Specifies the type of the T1 interface."
        ::= { hpnicft1Entry 1 }

hpnicft1Clock             OBJECT-TYPE
        SYNTAX  INTEGER {
                    slave(1),
                    master(2),
                    internal(3),
                    line(4),
                    linePri(5)
                }
        MAX-ACCESS      read-write
        STATUS          current
        DESCRIPTION
         "Specifies the clock type used on the T1 interface."
        ::= { hpnicft1Entry 2 }

hpnicft1FrameFormat       OBJECT-TYPE
        SYNTAX   INTEGER {
                    sf(1),
                    esf(2)
                }
        MAX-ACCESS      read-write
        STATUS          current
        DESCRIPTION
         "Specifies the frame format used on the T1 interface."
        DEFVAL { esf }
        ::= { hpnicft1Entry 3 }

hpnicft1LineCode          OBJECT-TYPE
        SYNTAX  INTEGER {
                    ami(1),
                    b8zs(2)
                }
        MAX-ACCESS      read-write
        STATUS          current
        DESCRIPTION
         "Specifies the line code type used on the T1 interface."
        DEFVAL { b8zs }
        ::= { hpnicft1Entry 4 }

hpnicft1PriSetTimeSlot    OBJECT-TYPE
        SYNTAX          HpnicfT1TimeSlot
        MAX-ACCESS      read-write
        STATUS          current
        DESCRIPTION
         "This is a bit-map of PRI time slots used on the T1 interface.
         It needs to administratively shut down the D channel of
         the T1 interface before cancelling PRI time slots."
        ::= { hpnicft1Entry 5 }

hpnicft1DChannelIndex      OBJECT-TYPE
        SYNTAX                Integer32
        MAX-ACCESS            read-only
        STATUS                current
        DESCRIPTION
         "This is the ifIndex of the D channel of the T1 interface."
        ::= { hpnicft1Entry 6 }

hpnicft1SubScribLineChannelIndex      OBJECT-TYPE
        SYNTAX                Integer32
        MAX-ACCESS            read-only
        STATUS                current
        DESCRIPTION
         "This is the ifIndex of the subscriber-line channel of the T1 interface."
        ::= { hpnicft1Entry 7 }

hpnicft1InterfaceTable OBJECT-TYPE
        SYNTAX      SEQUENCE OF HpnicfT1InterfaceEntry
        MAX-ACCESS   not-accessible
        STATUS       current
        DESCRIPTION
         "A list of channels of T1 interface entries.
         Including D channels and subscriber-line channels."
        ::= { hpnicfT1 3 }

hpnicft1InterfaceEntry OBJECT-TYPE
        SYNTAX         HpnicfT1InterfaceEntry
        MAX-ACCESS     not-accessible
        STATUS         current
        DESCRIPTION
         "This entry contains channels of T1 interface management information.
         Including D channels and subscriber-line channels."
        INDEX { ifIndex }
        ::= { hpnicft1InterfaceTable 1 }

HpnicfT1InterfaceEntry ::= SEQUENCE  {
        hpnicft1ControllerIndex        Integer32
        }

hpnicft1ControllerIndex      OBJECT-TYPE
        SYNTAX                Integer32
        MAX-ACCESS            read-only
        STATUS                current
        DESCRIPTION
         "Which T1 interface is this channel belonged to."
        ::= { hpnicft1InterfaceEntry 1 }

END
