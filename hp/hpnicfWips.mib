-- =============================================================================
-- Copyright (c) 2010-2014 Hewlett-Packard Development Company, L.P.
--
-- Description:
--   The file defines a MIB to provide wireless intrusion prevention service
--   feature.
-- Reference:
-- Version: V1.2
-- History:
--   V1.0 created by sunlongfei
--     Initial version 2012-01-09
--   V1.1 updated by sunlongfei 2012-12-7
--     Modify the descriptions of hpnicfWIPSDctAPAdd2CtmList,
--     hpnicfWIPSDctAPAdd2IgnoreList,hpnicfWIPSDctAPAdd2WhiteList,
--     hpnicfWIPSDctAPAdd2BlackListc,hpnicfWIPSDctStaAdd2BlackList,
--     hpnicfWIPSDctStaAdd2WhiteList,hpnicfWIPSDctStaAdd2IgnoreList,
--     hpnicfWIPSDctStaAdd2CtmList,hpnicfWIPSDevStatTxProbeRequest.
--   V1.2 modified by sunlongfei 2013-6-7
--     In hpnicfWIPSGlobalConfigGroup,
--     Modify the descriptions of hpnicfWIPSEnable.
--     Add hpnicfWIPSDynamicTrustListAgingTime, hpnicfWIPSDevUpdateTime,
--     hpnicfWIPSADOSEnable, hpnicfWIPSAccessFlowScanEnable.
--     Modify hpnicfWIPSVsdTable, hpnicfWIPSAtkDctPolicyCfgGroup,
--     hpnicfWIPSDctAPTable, hpnicfWIPSDctStaTable.
--     Add hpnicfWIPSSigConfigGroup, hpnicfWIPSCtmConfigGroup,
--     hpnicfWIPSMalPktDctConfigGroup, hpnicfWIPSStaticTrustOUIListCfgTable
--     hpnicfWIPSStaticTrustVendorListCfgTable,
--     hpnicfWIPSCtmDeviceTable, hpnicfWIPSMalPktStatTable
--     modified by sunlongfei 2013-11-21
--     Modify the size of hpnicfWIPSSensorNameCfg, hpnicfWIPSDctModeAPName,
--     hpnicfWIPSDctAPRptSensorName, hpnicfWIPSDctStaRptSensorName
--     from '1..32' to '1..64'.
-- =============================================================================
HPN-ICF-WIPS-MIB DEFINITIONS ::= BEGIN

IMPORTS
    TimeTicks, Integer32, Unsigned32, OBJECT-TYPE, MODULE-IDENTITY, Counter64
        FROM SNMPv2-SMI
    TruthValue, RowStatus, MacAddress, TEXTUAL-CONVENTION
        FROM SNMPv2-TC
    hpnicfCommon
        FROM HPN-ICF-OID-MIB;


hpnicfWIPS MODULE-IDENTITY
    LAST-UPDATED "201112291450Z"        -- December 29, 2011 at 14:50 GMT
    ORGANIZATION
        ""
    CONTACT-INFO
        ""
    DESCRIPTION
        "This MIB provides information about WIPS feature.

        Wireless Intrusion Prevention System (WIPS)
        WIPS is designed to be employed in an area that is serviced
        by an existing wireless network.
        It aids in the early detection of malicious outsider attacks
        and intrusions via wireless networks, and takes corresponding
        measures in order to guarantee the wireless environment security.
        "
    REVISION "201112291450Z"        -- December 29, 2011 at 14:50 GMT
    DESCRIPTION
        "The initial revision of this MIB module."
    ::= {  hpnicfCommon 118 }

--
-- Textual conventions
--

HpnicfWIPSRadioType ::= TEXTUAL-CONVENTION
    STATUS current
    DESCRIPTION
        "Represents AP 802.11 radio type of 802.11a/b/g/n as per
        the standard.
        The following values are supported:
        dot11a  - 802.11a
        dot11b  - 802.11b
        dot11g  - 802.11g
        dot11n  - 802.11n
        dot11gn  - 802.11gn
        dot11an  - 802.11an"
    SYNTAX INTEGER
        {
        dot11a(1),
        dot11b(2),
        dot11g(4),
        dot11n(8),
        dot11gn(16),
        dot11an(32)
        }

HpnicfWIPSDevStatus ::= TEXTUAL-CONVENTION
    STATUS current
    DESCRIPTION
        "Represents the status of devices detected by WIPS."
    SYNTAX INTEGER
        {
        active(1),
        inactive(2)
        }

HpnicfWIPSDevCategoryWay ::= TEXTUAL-CONVENTION
    STATUS current
    DESCRIPTION
        "Represents by which way the device is categorized.
        'manual': the device is categorized by user.
        'autoByNMS': the device is automatically categorized by
        NMS(Network Management System).
        'autoByDev': the device is automatically categorized by WIPS."
    SYNTAX INTEGER
        {
        manual(1),
        autoByNMS(2),
        autoByDev(3)
        }

HpnicfWIPSDeviceCategoryType ::= TEXTUAL-CONVENTION
    STATUS current
    DESCRIPTION
        "Represents the categorized type of device detected by WIPS."
    SYNTAX INTEGER
        {
        none(0),
        authorizedAP(1),
        authorizedClient(2),
        misconfiguredAP(3),
        rogueAP(4),
        unauthorizedClient(5),
        externalAP(6),
        adhoc(7),
        bridge(8),
        misassociatedClient(9),
        potentialAuthorizedAP(10),
        potentialRogueAP(11),
        potentialExternalAP(12),
        uncategorizedAP(13),
        uncategorizedClient(14)
        }

HpnicfWIPSAPCategoryType ::= TEXTUAL-CONVENTION
    STATUS current
    DESCRIPTION
        "Represents the categorized type of AP detected by WIPS."
    SYNTAX INTEGER
        {
        adhoc(1),
        authorized(2),
        rogue(3),
        misconfigured(4),
        external(5),
        potentialAuthorized(6),
        potentialRogue(7),
        potentialExternal(8),
        uncategorized(9)
        }

HpnicfWIPSClientCategoryType ::= TEXTUAL-CONVENTION
    STATUS current
    DESCRIPTION
        "Represents the categorized type of Client detected by WIPS."
    SYNTAX INTEGER
        {
        authorized(1),
        unauthorized(2),
        misassociated(3),
        uncategorized(4)
        }

HpnicfWIPSChannel ::= TEXTUAL-CONVENTION
    DISPLAY-HINT "d"
    STATUS current
    DESCRIPTION
        "Represents the channel number."
    SYNTAX Integer32 (0..224)

HpnicfWIPSEncryptMethod ::= TEXTUAL-CONVENTION
    DISPLAY-HINT "d"
    STATUS current
    DESCRIPTION
        "Represents the frame encryption cipher types for
        frames on IEEE 802.11 radio interfaces.
        The MIB defines TC by referring to the 802.11i protocol.
        The following values are supported:
        none(1)     - clear text or no cipher method is configure,
        wep(2)      - WEP key,
        tkip(4)     - WPA Temporal Key encryption,
        ccmp(8)     - WPA AES CCMP encryption"
    SYNTAX Unsigned32

HpnicfWIPSAuthMethod ::= TEXTUAL-CONVENTION
    STATUS current
    DESCRIPTION
        "Represents the key management mode defined by 802.11i.
        The following values are supported:
        none         - No key management mode configured,
        psk          - pre-shared key authentication,
        dot1x        - 802.1x authentication.
        other        - other authentication."
    SYNTAX INTEGER
        {
        none(1),
        psk(2),
        dot1x(3),
        other(4)
        }

HpnicfWIPSAPClassifyType ::= TEXTUAL-CONVENTION
    STATUS current
    DESCRIPTION
        "Represents the classify type of AP.
        'other' - represents undo operation."
    SYNTAX INTEGER
        {
        other(1),
        authorized(2),
        external(3),
        misconfigured(4),
        rogue(5)
        }

HpnicfWIPSAPSecurityType ::= TEXTUAL-CONVENTION
    DISPLAY-HINT "d"
    STATUS current
    DESCRIPTION
        "Represents the AP security type.
        clear  0x01
        wpa2   0x02
        wpa    0x04
        wep    0x08"
    SYNTAX Unsigned32

--
-- Node definitions
--

hpnicfWIPSConfigGroup OBJECT IDENTIFIER ::= { hpnicfWIPS 1 }

hpnicfWIPSGlobalConfigGroup OBJECT IDENTIFIER ::= { hpnicfWIPSConfigGroup 1 }

hpnicfWIPSEnable OBJECT-TYPE
    SYNTAX TruthValue
    MAX-ACCESS read-write
    STATUS current
    DESCRIPTION
        "Represents whether the WIPS feature is enabled or not.
        'true': enable the WIPS feature.
        'false': disable the WIPS feature."
    ::= { hpnicfWIPSGlobalConfigGroup 1 }

hpnicfWIPSSensorLicenseNum OBJECT-TYPE
    SYNTAX Unsigned32
    MAX-ACCESS read-only
    STATUS current
    DESCRIPTION
        "Represents the number of sensor license."
    ::= { hpnicfWIPSGlobalConfigGroup 2 }

hpnicfWIPSBlocklistAction OBJECT-TYPE
    SYNTAX INTEGER
        {
        block(1),
        unblock(2)
        }
    MAX-ACCESS read-write
    STATUS current
    DESCRIPTION
        "Represents whether the block list feature is enabled or not.
        'block'  : Enable the block list feature to filter unwanted devices.
        'unblock' : Disable the block list feature."
    ::= { hpnicfWIPSGlobalConfigGroup 3 }

hpnicfWIPSAPInactiveTime OBJECT-TYPE
    SYNTAX Integer32 (60..600)
    UNITS "second"
    MAX-ACCESS read-write
    STATUS current
    DESCRIPTION
        "Represents the time for AP getting inactive."
    DEFVAL { 300 }
    ::= { hpnicfWIPSGlobalConfigGroup 4 }

hpnicfWIPSSTAInactiveTime OBJECT-TYPE
    SYNTAX Integer32 (120..1200)
    UNITS "second"
    MAX-ACCESS read-write
    STATUS current
    DESCRIPTION
        "Represents the time for STA getting inactive."
    DEFVAL { 600 }
    ::= { hpnicfWIPSGlobalConfigGroup 5 }

hpnicfWIPSDevAgingTime OBJECT-TYPE
    SYNTAX Integer32 (60..2592000)
    UNITS "second"
    MAX-ACCESS read-write
    STATUS current
    DESCRIPTION
        "Represents the time for device getting aged."
    DEFVAL { 86400 }
    ::= { hpnicfWIPSGlobalConfigGroup 6 }

hpnicfWIPSStatisticPeriod OBJECT-TYPE
    SYNTAX Integer32 (60..86400)
    UNITS "second"
    MAX-ACCESS read-write
    STATUS current
    DESCRIPTION
        "Represents the period of WIPS reporting the statistic."
    DEFVAL { 900 }
    ::= { hpnicfWIPSGlobalConfigGroup 7 }

hpnicfWIPSReclassificationPeriod OBJECT-TYPE
    SYNTAX Integer32 (10..3600)
    UNITS "second"
    MAX-ACCESS read-write
    STATUS current
    DESCRIPTION
        "Represents the period of WIPS reclassifying devices."
    DEFVAL { 600 }
    ::= { hpnicfWIPSGlobalConfigGroup 8 }

hpnicfWIPSResetAllTrustList OBJECT-TYPE
    SYNTAX TruthValue
    MAX-ACCESS read-write
    STATUS current
    DESCRIPTION
        "This object is used to remove all entries from the static trust list.
        It will return false for get operation."
    ::= { hpnicfWIPSGlobalConfigGroup 9 }

hpnicfWIPSResetAllBlockList OBJECT-TYPE
    SYNTAX TruthValue
    MAX-ACCESS read-write
    STATUS current
    DESCRIPTION
        "This object is used to remove all entries from the static block list.
        It will return false for get operation."
    ::= { hpnicfWIPSGlobalConfigGroup 10 }

hpnicfWIPSResetAllIgnoreList OBJECT-TYPE
    SYNTAX TruthValue
    MAX-ACCESS read-write
    STATUS current
    DESCRIPTION
        "This object is used to remove all entries from the ignore list.
        It will return false for get operation.."
    ::= { hpnicfWIPSGlobalConfigGroup 11 }

hpnicfWIPSResetAllCtmList OBJECT-TYPE
    SYNTAX TruthValue
    MAX-ACCESS read-write
    STATUS current
    DESCRIPTION
        "This object is used to remove all entries from the static
        countermeasure list.
        It will return false for get operation."
    ::= { hpnicfWIPSGlobalConfigGroup 12 }

hpnicfWIPSPermitChlBitMap OBJECT-TYPE
    SYNTAX OCTET STRING (SIZE (32))
    MAX-ACCESS read-write
    STATUS current
    DESCRIPTION
        "Represents the permit channel number by bitmap."
    ::= { hpnicfWIPSGlobalConfigGroup 13 }

hpnicfWIPSDynamicTrustListAgingTime OBJECT-TYPE
    SYNTAX Integer32 (60..86400)
    UNITS "second"
    MAX-ACCESS read-write
    STATUS current
    DESCRIPTION
        "Represents the time for devices in the dynamic trust list getting aged."
    DEFVAL {300}
    ::= { hpnicfWIPSGlobalConfigGroup 14 }

hpnicfWIPSDevUpdateTime OBJECT-TYPE
    SYNTAX Integer32 (10..30)
    UNITS "second"
    MAX-ACCESS read-write
    STATUS current
    DESCRIPTION
        "Represents the period of WIPS update the status of devices."
    DEFVAL {20}
    ::= { hpnicfWIPSGlobalConfigGroup 15 }

hpnicfWIPSADOSEnable OBJECT-TYPE
    SYNTAX TruthValue
    MAX-ACCESS read-write
    STATUS current
    DESCRIPTION
        "Represents whether enable the ADOS feature.
        'true': enable the ADOS feature.
        'false': disable the ADOS feature."
    DEFVAL { false }
    ::= { hpnicfWIPSGlobalConfigGroup 16 }

hpnicfWIPSAccessFlowScanEnable OBJECT-TYPE
    SYNTAX TruthValue
    MAX-ACCESS read-write
    STATUS current
    DESCRIPTION
        "Represents whether the WIPS scanning feature during the access flow is enabled or not.
        'true': enable the feature.
        'false': disable the feature."
    DEFVAL { false }
    ::= { hpnicfWIPSGlobalConfigGroup 17}

hpnicfWIPSVsdConfigGroup OBJECT IDENTIFIER ::= { hpnicfWIPSConfigGroup 2 }

hpnicfWIPSVsdTable OBJECT-TYPE
    SYNTAX SEQUENCE OF HpnicfWIPSVsdEntry
    MAX-ACCESS not-accessible
    STATUS current
    DESCRIPTION
        "The table provides the list of virtual security domain."
    ::= { hpnicfWIPSVsdConfigGroup 1 }

hpnicfWIPSVsdEntry OBJECT-TYPE
    SYNTAX HpnicfWIPSVsdEntry
    MAX-ACCESS not-accessible
    STATUS current
    DESCRIPTION
        "Each entry contains information of each VSD."
    INDEX { hpnicfWIPSVsdNameCfg }
    ::= { hpnicfWIPSVsdTable 1 }

HpnicfWIPSVsdEntry ::=
    SEQUENCE {
        hpnicfWIPSVsdNameCfg
            OCTET STRING,
        hpnicfWIPSVsdRowStatus
            RowStatus,
        hpnicfWIPSVsdAtkDctPolicyNameCfg
            OCTET STRING,
        hpnicfWIPSVsdCtmPolicyNameCfg
            OCTET STRING,
        hpnicfWIPSVsdSigPolicyNameCfg
            OCTET STRING,
        hpnicfWIPSVsdMalPktPolicyNameCfg
            OCTET STRING
     }

hpnicfWIPSVsdNameCfg OBJECT-TYPE
    SYNTAX OCTET STRING (SIZE (1..32))
    MAX-ACCESS not-accessible
    STATUS current
    DESCRIPTION
        "Represents the name of virtual security domain."
    ::= { hpnicfWIPSVsdEntry 1 }

hpnicfWIPSVsdRowStatus OBJECT-TYPE
    SYNTAX RowStatus
    MAX-ACCESS read-create
    STATUS current
    DESCRIPTION
        "The status of this table entry."
    ::= { hpnicfWIPSVsdEntry 2 }

hpnicfWIPSVsdAtkDctPolicyNameCfg OBJECT-TYPE
    SYNTAX OCTET STRING (SIZE (0..32))
    MAX-ACCESS read-create
    STATUS current
    DESCRIPTION
        "Represents the name of attack detect policy attached to the VSD."
    ::= { hpnicfWIPSVsdEntry 3 }

hpnicfWIPSVsdCtmPolicyNameCfg OBJECT-TYPE
    SYNTAX OCTET STRING (SIZE (0..32))
    MAX-ACCESS read-create
    STATUS current
    DESCRIPTION
        "Represents the name of countermeasure policy attached to the VSD."
    ::= { hpnicfWIPSVsdEntry 4 }

hpnicfWIPSVsdSigPolicyNameCfg OBJECT-TYPE
    SYNTAX OCTET STRING (SIZE (0..32))
    MAX-ACCESS read-create
    STATUS current
    DESCRIPTION
        "Represents the name of signature policy attached to the VSD"
    ::= { hpnicfWIPSVsdEntry 5 }

hpnicfWIPSVsdMalPktPolicyNameCfg OBJECT-TYPE
    SYNTAX OCTET STRING (SIZE (0..32))
    MAX-ACCESS read-create
    STATUS current
    DESCRIPTION
        "Represents the name of malformed packet detect policy attached to the VSD"
    ::= { hpnicfWIPSVsdEntry 6 }

hpnicfWIPSRule2VsdTable OBJECT-TYPE
    SYNTAX SEQUENCE OF HpnicfWIPSRule2VsdEntry
    MAX-ACCESS not-accessible
    STATUS current
    DESCRIPTION
        "The table defines the AP classification rules been attached to the VSD.
        "
    ::= { hpnicfWIPSVsdConfigGroup 2 }

hpnicfWIPSRule2VsdEntry OBJECT-TYPE
    SYNTAX HpnicfWIPSRule2VsdEntry
    MAX-ACCESS not-accessible
    STATUS current
    DESCRIPTION
        "Each entry contains information of each AP classification rule
        in each VSD.
        "
    INDEX { hpnicfWIPSVsdNameCfg, hpnicfWIPSRule2VsdAPClaRuleNameCfg }
    ::= { hpnicfWIPSRule2VsdTable 1 }

HpnicfWIPSRule2VsdEntry ::=
    SEQUENCE {
        hpnicfWIPSRule2VsdAPClaRuleNameCfg
            OCTET STRING,
        hpnicfWIPSRule2VsdRowStatus
            RowStatus,
        hpnicfWIPSRule2VsdPrecedence
            Integer32
     }

hpnicfWIPSRule2VsdAPClaRuleNameCfg OBJECT-TYPE
    SYNTAX OCTET STRING (SIZE (1..32))
    MAX-ACCESS not-accessible
    STATUS current
    DESCRIPTION
        "Represents the name of AP classification rule attached to the VSD."
    ::= { hpnicfWIPSRule2VsdEntry 1 }

hpnicfWIPSRule2VsdRowStatus OBJECT-TYPE
    SYNTAX RowStatus
    MAX-ACCESS read-create
    STATUS current
    DESCRIPTION
        "The status of this table entry."
    ::= { hpnicfWIPSRule2VsdEntry 2 }

hpnicfWIPSRule2VsdPrecedence OBJECT-TYPE
    SYNTAX Integer32 (0..15)
    MAX-ACCESS read-create
    STATUS current
    DESCRIPTION
        "Represents the precedence of AP classification rule
        attached to the VSD."
    DEFVAL { 0 }
    ::= { hpnicfWIPSRule2VsdEntry 3 }

hpnicfWIPSSensor2VsdTable OBJECT-TYPE
    SYNTAX SEQUENCE OF HpnicfWIPSSensor2VsdEntry
    MAX-ACCESS not-accessible
    STATUS current
    DESCRIPTION
        "The table defines the sensor been attached to the VSD.
        "
    ::= { hpnicfWIPSVsdConfigGroup 3 }

hpnicfWIPSSensor2VsdEntry OBJECT-TYPE
    SYNTAX HpnicfWIPSSensor2VsdEntry
    MAX-ACCESS not-accessible
    STATUS current
    DESCRIPTION
        "Each entry contains information of each sensor in each VSD."
    INDEX { hpnicfWIPSVsdNameCfg, hpnicfWIPSSensorNameCfg }
    ::= { hpnicfWIPSSensor2VsdTable 1 }

HpnicfWIPSSensor2VsdEntry ::=
    SEQUENCE {
        hpnicfWIPSSensorNameCfg
            OCTET STRING,
        hpnicfWIPSSensor2VsdRowStatus
            RowStatus,
        hpnicfWIPSSensorState
            INTEGER
     }

hpnicfWIPSSensorNameCfg OBJECT-TYPE
    SYNTAX OCTET STRING (SIZE (1..64))
    MAX-ACCESS not-accessible
    STATUS current
    DESCRIPTION
        "Represents the name of sensor attached to the VSD."
    ::= { hpnicfWIPSSensor2VsdEntry 1 }

hpnicfWIPSSensor2VsdRowStatus OBJECT-TYPE
    SYNTAX RowStatus
    MAX-ACCESS read-create
    STATUS current
    DESCRIPTION
        "The status of this table entry."
    ::= { hpnicfWIPSSensor2VsdEntry 2 }

hpnicfWIPSSensorState OBJECT-TYPE
    SYNTAX INTEGER
        {
        running(1),
        idle(2)
        }
    MAX-ACCESS read-create
    STATUS current
    DESCRIPTION
        "Represents the running state of the sensor.
        It will return false for set operation."
    ::= { hpnicfWIPSSensor2VsdEntry 3 }

hpnicfWIPSSensorRadioTable OBJECT-TYPE
    SYNTAX SEQUENCE OF HpnicfWIPSSensorRadioEntry
    MAX-ACCESS not-accessible
    STATUS current
    DESCRIPTION
        "The table represents the list of sensor radio information."
    ::= { hpnicfWIPSVsdConfigGroup 4 }

hpnicfWIPSSensorRadioEntry OBJECT-TYPE
    SYNTAX HpnicfWIPSSensorRadioEntry
    MAX-ACCESS not-accessible
    STATUS current
    DESCRIPTION
        "Each entry contains information of a radio of a sensor."
    INDEX { hpnicfWIPSVsdNameCfg, hpnicfWIPSSensorNameCfg, hpnicfWIPSSensorRadioRadioId }
    ::= { hpnicfWIPSSensorRadioTable 1 }

HpnicfWIPSSensorRadioEntry ::=
    SEQUENCE {
        hpnicfWIPSSensorRadioRadioId
            Integer32,
        hpnicfWIPSSensorRadioScanMode
            INTEGER
     }

hpnicfWIPSSensorRadioRadioId OBJECT-TYPE
    SYNTAX Integer32 (1..4)
    MAX-ACCESS not-accessible
    STATUS current
    DESCRIPTION
        "Represents the radio identifier of the sensor."
    ::= { hpnicfWIPSSensorRadioEntry 1 }

hpnicfWIPSSensorRadioScanMode OBJECT-TYPE
    SYNTAX INTEGER
        {
        accessFirst(1),
        detectFirst(2),
        middle(3),
        detectOnly(4)
        }
    MAX-ACCESS read-only
    STATUS current
    DESCRIPTION
        "Represents the scanning mode configured to the radio."
    ::= { hpnicfWIPSSensorRadioEntry 2 }

hpnicfWIPSAPClaRuleTable OBJECT-TYPE
    SYNTAX SEQUENCE OF HpnicfWIPSAPClaRuleEntry
    MAX-ACCESS not-accessible
    STATUS current
    DESCRIPTION
        "The table defines the parameters for WIPS AP classification rule.
        One rule could be assigned to different VSDs.
        "
    ::= { hpnicfWIPSConfigGroup 3 }

hpnicfWIPSAPClaRuleEntry OBJECT-TYPE
    SYNTAX HpnicfWIPSAPClaRuleEntry
    MAX-ACCESS not-accessible
    STATUS current
    DESCRIPTION
        "Each entry contains information of each AP classification rule.
        "
    INDEX { hpnicfWIPSAPClaRuleName }
    ::= { hpnicfWIPSAPClaRuleTable 1 }

HpnicfWIPSAPClaRuleEntry ::=
    SEQUENCE {
        hpnicfWIPSAPClaRuleName
            OCTET STRING,
        hpnicfWIPSAPClaRowStatus
            RowStatus,
        hpnicfWIPSAPClaSeverityLevel
            Unsigned32,
        hpnicfWIPSAPClaRuleMatchAll
            TruthValue,
        hpnicfWIPSAPClaType
            HpnicfWIPSAPClassifyType,
        hpnicfWIPSAPClaSubRuleSSIDOperator
            INTEGER,
        hpnicfWIPSAPClaSubRuleSSIDCase
            TruthValue,
        hpnicfWIPSAPClaSubRuleSSID
            OCTET STRING,
        hpnicfWIPSSecurityType
            HpnicfWIPSAPSecurityType,
        hpnicfWIPSSecurityTypeMatch
            INTEGER,
        hpnicfWIPSAPAuthType
            INTEGER,
        hpnicfWIPSMaxRSSIValue
            Unsigned32,
        hpnicfWIPSMinRSSIValue
            Unsigned32,
        hpnicfWIPSMaxDuration
            Unsigned32,
        hpnicfWIPSMinDuration
            Unsigned32,
        hpnicfWIPSMaxAPNum
            Unsigned32,
        hpnicfWIPSMinAPNum
            Unsigned32,
        hpnicfWIPSMaxClientNum
            Unsigned32,
        hpnicfWIPSMinClientNum
            Unsigned32,
        hpnicfWIPSOUIInfo
            OCTET STRING,
        hpnicfWIPSVendorInfo
            OCTET STRING
     }

hpnicfWIPSAPClaRuleName OBJECT-TYPE
    SYNTAX OCTET STRING (SIZE (1..32))
    MAX-ACCESS not-accessible
    STATUS current
    DESCRIPTION
        "Represents the name of AP classification rule."
    ::= { hpnicfWIPSAPClaRuleEntry 1 }

hpnicfWIPSAPClaRowStatus OBJECT-TYPE
    SYNTAX RowStatus
    MAX-ACCESS read-create
    STATUS current
    DESCRIPTION
        "The status of this table entry."
    ::= { hpnicfWIPSAPClaRuleEntry 2 }

hpnicfWIPSAPClaSeverityLevel OBJECT-TYPE
    SYNTAX Unsigned32
    MAX-ACCESS read-create
    STATUS current
    DESCRIPTION
        "Represents the severity level of the AP classification rule.
        Available value limits from 0 to 100."
    DEFVAL { 'ffffffff'h }
    ::= { hpnicfWIPSAPClaRuleEntry 3 }

hpnicfWIPSAPClaRuleMatchAll OBJECT-TYPE
    SYNTAX TruthValue
    MAX-ACCESS read-create
    STATUS current
    DESCRIPTION
        "Represents whether match all the AP classification sub-rules
        which have been configured."
    DEFVAL { false }
    ::= { hpnicfWIPSAPClaRuleEntry 4 }

hpnicfWIPSAPClaType OBJECT-TYPE
    SYNTAX HpnicfWIPSAPClassifyType
    MAX-ACCESS read-create
    STATUS current
    DESCRIPTION
        "Represents the type of AP classification."
    ::= { hpnicfWIPSAPClaRuleEntry 5 }

hpnicfWIPSAPClaSubRuleSSIDOperator OBJECT-TYPE
    SYNTAX INTEGER
        {
        include(1),
        notinclude(2),
        equal(3),
        notequal(4)
        }
    MAX-ACCESS read-create
    STATUS current
    DESCRIPTION
        "Represents the compare way of the SSID in the sub rule,
        including include/not include/equal/not equal."
    ::= { hpnicfWIPSAPClaRuleEntry 6 }

hpnicfWIPSAPClaSubRuleSSIDCase OBJECT-TYPE
    SYNTAX TruthValue
    MAX-ACCESS read-create
    STATUS current
    DESCRIPTION
        "Represents the case sensitive or not for the SSID match.
        'true': Case insensitive.
        'false': Case sensitive."
    DEFVAL { false }
    ::= { hpnicfWIPSAPClaRuleEntry 7 }

hpnicfWIPSAPClaSubRuleSSID OBJECT-TYPE
    SYNTAX OCTET STRING (SIZE (0..32))
    MAX-ACCESS read-create
    STATUS current
    DESCRIPTION
        "Represents the SSID match template in the ap classification rule."
    ::= { hpnicfWIPSAPClaRuleEntry 8 }

hpnicfWIPSSecurityType OBJECT-TYPE
    SYNTAX HpnicfWIPSAPSecurityType
    MAX-ACCESS read-create
    STATUS current
    DESCRIPTION
        "Represents the security type of active AP.
        "
    DEFVAL { 'ffffffff'h }
    ::= { hpnicfWIPSAPClaRuleEntry 9 }

hpnicfWIPSSecurityTypeMatch OBJECT-TYPE
    SYNTAX INTEGER
        {
        equal(1),
        include(2)
        }
    MAX-ACCESS read-create
    STATUS current
    DESCRIPTION
        "Represents match way of the security type of active AP.
        "
    ::= { hpnicfWIPSAPClaRuleEntry 10 }

hpnicfWIPSAPAuthType OBJECT-TYPE
    SYNTAX INTEGER
        {
        none(1),
        psk(2),
        dot1x(3),
        other(4),
        undo(5)
        }
    MAX-ACCESS read-create
    STATUS current
    DESCRIPTION
        "Represents the authentication type of the AP.
        undo - represents undo operation"
    DEFVAL { undo }
    ::= { hpnicfWIPSAPClaRuleEntry 11 }

hpnicfWIPSMaxRSSIValue OBJECT-TYPE
    SYNTAX Unsigned32
    MAX-ACCESS read-create
    STATUS current
    DESCRIPTION
        "Represents the high-limit of the RSSI of AP.
        Available value limits from 1 to 90."
    DEFVAL { 'ffffffff'h }
    ::= { hpnicfWIPSAPClaRuleEntry 12 }

hpnicfWIPSMinRSSIValue OBJECT-TYPE
    SYNTAX Unsigned32
    MAX-ACCESS read-create
    STATUS current
    DESCRIPTION
        "Represents the low-limit of the RSSI of AP.
        Available value limits from 0 to 89."
    DEFVAL { 'ffffffff'h }
    ::= { hpnicfWIPSAPClaRuleEntry 13 }

hpnicfWIPSMaxDuration OBJECT-TYPE
    SYNTAX Unsigned32
    UNITS "second"
    MAX-ACCESS read-create
    STATUS current
    DESCRIPTION
        "Represents the high-limit of the duration of AP.
        Available value limits from 1 to 2592000."
    DEFVAL { 'ffffffff'h }
    ::= { hpnicfWIPSAPClaRuleEntry 14 }

hpnicfWIPSMinDuration OBJECT-TYPE
    SYNTAX Unsigned32
    UNITS "second"
    MAX-ACCESS read-create
    STATUS current
    DESCRIPTION
        "Represents the low-limit of the duration of AP.
        Available value limits from 0 to 2591999."
    DEFVAL { 'ffffffff'h }
    ::= { hpnicfWIPSAPClaRuleEntry 15 }

hpnicfWIPSMaxAPNum OBJECT-TYPE
    SYNTAX Unsigned32
    MAX-ACCESS read-create
    STATUS current
    DESCRIPTION
        "Represents the high-limit of the number of AP.
        Available value limits from 1 to 128."
    DEFVAL { 'ffffffff'h }
    ::= { hpnicfWIPSAPClaRuleEntry 16 }

hpnicfWIPSMinAPNum OBJECT-TYPE
    SYNTAX Unsigned32
    MAX-ACCESS read-create
    STATUS current
    DESCRIPTION
        "Represents the low-limit of the number of AP.
        Available value limits from 0 to 127."
    DEFVAL { 'ffffffff'h }
    ::= { hpnicfWIPSAPClaRuleEntry 17 }

hpnicfWIPSMaxClientNum OBJECT-TYPE
    SYNTAX Unsigned32
    MAX-ACCESS read-create
    STATUS current
    DESCRIPTION
        "Represents the high-limit of the number of client.
        Available value limits from 1 to 128."
    DEFVAL { 'ffffffff'h }
    ::= { hpnicfWIPSAPClaRuleEntry 18 }

hpnicfWIPSMinClientNum OBJECT-TYPE
    SYNTAX Unsigned32
    MAX-ACCESS read-create
    STATUS current
    DESCRIPTION
        "Represents the low-limit of the number of client.
        Available value limits from 0 to 127."
    DEFVAL { 'ffffffff'h }
    ::= { hpnicfWIPSAPClaRuleEntry 19 }

hpnicfWIPSOUIInfo OBJECT-TYPE
    SYNTAX OCTET STRING (SIZE (0..6))
    MAX-ACCESS read-create
    STATUS current
    DESCRIPTION
        "Represents the OUI hexadecimal string of the AP."
    ::= { hpnicfWIPSAPClaRuleEntry 20 }

hpnicfWIPSVendorInfo OBJECT-TYPE
    SYNTAX OCTET STRING (SIZE (0..64))
    MAX-ACCESS read-create
    STATUS current
    DESCRIPTION
        "Represents the vendor info of the AP."
    ::= { hpnicfWIPSAPClaRuleEntry 21 }

hpnicfWIPSAtkDctPolicyCfgGroup OBJECT IDENTIFIER ::= { hpnicfWIPSConfigGroup 4 }

hpnicfWIPSAtkDctPolicyCfgSupportSet OBJECT-TYPE
    SYNTAX OCTET STRING (SIZE (16))
    MAX-ACCESS read-only
    STATUS current
    DESCRIPTION
        "Represents the bit string of supported attack detect policy.
        The specific attack detect policy is supported if its corresponding
        bit is set to 1; otherwise its corresponding bit is set to 0.
        bit0: adhoc
        bit1: ap-spoof
        bit2: client-spoof
        bit3: prohibited channel
        bit4: ap-flood
        bit5: eapol-start
        bit6: authentication
        bit7: association
        bit8: reassociation
        bit9: weak-IV
        bit10: invalid-OUI"
    ::= { hpnicfWIPSAtkDctPolicyCfgGroup 1 }

hpnicfWIPSAtkDctPolicyCfgTable OBJECT-TYPE
    SYNTAX SEQUENCE OF HpnicfWIPSAtkDctPolicyCfgEntry
    MAX-ACCESS not-accessible
    STATUS current
    DESCRIPTION
        "The table defines the parameters for WIPS attack detect policy."
    ::= { hpnicfWIPSAtkDctPolicyCfgGroup 2 }

hpnicfWIPSAtkDctPolicyCfgEntry OBJECT-TYPE
    SYNTAX HpnicfWIPSAtkDctPolicyCfgEntry
    MAX-ACCESS not-accessible
    STATUS current
    DESCRIPTION
        "Each entry contains information of each attack detect policy."
    INDEX { hpnicfWIPSAtkDctPolicyName }
    ::= { hpnicfWIPSAtkDctPolicyCfgTable 1 }

HpnicfWIPSAtkDctPolicyCfgEntry ::=
    SEQUENCE {
        hpnicfWIPSAtkDctPolicyName
            OCTET STRING,
        hpnicfWIPSAtkDctPolicyCfgRowStatus
            RowStatus,
        hpnicfWIPSAtkDctPolicyBitString
            OCTET STRING,
        hpnicfWIPSAtkDctPolicyAPFloodQT
            Integer32,
        hpnicfWIPSAtkDctPolicyAPSpoofQT
            Integer32,
        hpnicfWIPSAtkDctPolicyCliSpoofQT
            Integer32,
        hpnicfWIPSAtkDctPolicyDosAssoQT
            Integer32,
        hpnicfWIPSAtkDctPolicyDosAuthQT
            Integer32,
        hpnicfWIPSAtkDctPolicyDosEAPOLStartQT
            Integer32,
        hpnicfWIPSAtkDctPolicyDosReAssoQT
            Integer32,
        hpnicfWIPSAtkDctPolicyWeakIVQT
            Integer32,
        hpnicfWIPSAtkDctPolicyInvalidOUIAction
            INTEGER
     }

hpnicfWIPSAtkDctPolicyName OBJECT-TYPE
    SYNTAX OCTET STRING (SIZE (1..32))
    MAX-ACCESS not-accessible
    STATUS current
    DESCRIPTION
        "Represents the name of attack detect policy."
    ::= { hpnicfWIPSAtkDctPolicyCfgEntry 1 }

hpnicfWIPSAtkDctPolicyCfgRowStatus OBJECT-TYPE
    SYNTAX RowStatus
    MAX-ACCESS read-create
    STATUS current
    DESCRIPTION
        "The status of this table entry."
    ::= { hpnicfWIPSAtkDctPolicyCfgEntry 2 }

hpnicfWIPSAtkDctPolicyBitString OBJECT-TYPE
    SYNTAX OCTET STRING (SIZE (16))
    MAX-ACCESS read-create
    STATUS current
    DESCRIPTION
        "Represents the bit string of attack detect policy configuration.
        The specific attack detect policy is enabled if its corresponding
        bit is set to 1; disabled if its corresponding bit is set to 0.
        bit0: adhoc
        bit1: ap-spoof
        bit2: client-spoof
        bit3: prohibited channel
        bit4: ap-flood
        bit5: eapol-start
        bit6: authentication
        bit7: association
        bit8: reassociation
        bit9: weak-IV
        bit10: invalid-OUI"
    ::= { hpnicfWIPSAtkDctPolicyCfgEntry 3 }

hpnicfWIPSAtkDctPolicyAPFloodQT OBJECT-TYPE
    SYNTAX Integer32 (5..604800)
    MAX-ACCESS read-create
    STATUS current
    DESCRIPTION
        "Represents the quiet time after reporting
        the AP flood attack event alarm."
    DEFVAL { 600 }
    ::= { hpnicfWIPSAtkDctPolicyCfgEntry 4 }

hpnicfWIPSAtkDctPolicyAPSpoofQT OBJECT-TYPE
    SYNTAX Integer32 (5..604800)
    MAX-ACCESS read-create
    STATUS current
    DESCRIPTION
        "Represents the quiet time after reporting
        the AP spoofing attack event alarm."
    DEFVAL { 600 }
    ::= { hpnicfWIPSAtkDctPolicyCfgEntry 5 }

hpnicfWIPSAtkDctPolicyCliSpoofQT OBJECT-TYPE
    SYNTAX Integer32 (5..604800)
    MAX-ACCESS read-create
    STATUS current
    DESCRIPTION
        "Represents the quiet time after reporting
        the client spoofing attack event alarm."
    DEFVAL { 600 }
    ::= { hpnicfWIPSAtkDctPolicyCfgEntry 6 }

hpnicfWIPSAtkDctPolicyDosAssoQT OBJECT-TYPE
    SYNTAX Integer32 (5..604800)
    MAX-ACCESS read-create
    STATUS current
    DESCRIPTION
        "Represents the quiet time after reporting
        the dos of association attack event alarm."
    DEFVAL { 600 }
    ::= { hpnicfWIPSAtkDctPolicyCfgEntry 7 }

hpnicfWIPSAtkDctPolicyDosAuthQT OBJECT-TYPE
    SYNTAX Integer32 (5..604800)
    MAX-ACCESS read-create
    STATUS current
    DESCRIPTION
        "Represents the quiet time after reporting
        the dos of authentication attack event alarm."
    DEFVAL { 600 }
    ::= { hpnicfWIPSAtkDctPolicyCfgEntry 8 }

hpnicfWIPSAtkDctPolicyDosEAPOLStartQT OBJECT-TYPE
    SYNTAX Integer32 (5..604800)
    MAX-ACCESS read-create
    STATUS current
    DESCRIPTION
        "Represents the quiet time after reporting
        the dos of EAPOL-start attack event alarm."
    DEFVAL { 600 }
    ::= { hpnicfWIPSAtkDctPolicyCfgEntry 9 }

hpnicfWIPSAtkDctPolicyDosReAssoQT OBJECT-TYPE
    SYNTAX Integer32 (5..604800)
    MAX-ACCESS read-create
    STATUS current
    DESCRIPTION
        "Represents the quiet time after reporting
        the dos of reassociation attack event alarm."
    DEFVAL { 600 }
    ::= { hpnicfWIPSAtkDctPolicyCfgEntry 10 }

hpnicfWIPSAtkDctPolicyWeakIVQT OBJECT-TYPE
    SYNTAX Integer32 (5..604800)
    MAX-ACCESS read-create
    STATUS current
    DESCRIPTION
        "Represents the quiet time after reporting
        the weak-IV event alarm."
    DEFVAL { 600 }
    ::= { hpnicfWIPSAtkDctPolicyCfgEntry 11 }

hpnicfWIPSAtkDctPolicyInvalidOUIAction OBJECT-TYPE
    SYNTAX INTEGER
        {
        none(0),
        rogue(1)
        }
    MAX-ACCESS read-create
    STATUS current
    DESCRIPTION
        "Represents the action after detecting the invalid OUI,
        which classify the device as rogue device."
    ::= { hpnicfWIPSAtkDctPolicyCfgEntry 12 }

hpnicfWIPSStaticCtmListCfgTable OBJECT-TYPE
    SYNTAX SEQUENCE OF HpnicfWIPSStaticCtmListCfgEntry
    MAX-ACCESS not-accessible
    STATUS current
    DESCRIPTION
        "The table provides the MAC address list of devices
        in the static countermeasure list."
    ::= { hpnicfWIPSConfigGroup 5 }

hpnicfWIPSStaticCtmListCfgEntry OBJECT-TYPE
    SYNTAX HpnicfWIPSStaticCtmListCfgEntry
    MAX-ACCESS not-accessible
    STATUS current
    DESCRIPTION
        "Each entry contains information of each MAC address in the static
        countermeasure list.
        "
    INDEX { hpnicfWIPSStaticCtmListMAC }
    ::= { hpnicfWIPSStaticCtmListCfgTable 1 }

HpnicfWIPSStaticCtmListCfgEntry ::=
    SEQUENCE {
        hpnicfWIPSStaticCtmListMAC
            MacAddress,
        hpnicfWIPSStaticCtmListRowStatus
            RowStatus
     }

hpnicfWIPSStaticCtmListMAC OBJECT-TYPE
    SYNTAX MacAddress
    MAX-ACCESS not-accessible
    STATUS current
    DESCRIPTION
        "Represents the MAC address in static countermeasure list."
    ::= { hpnicfWIPSStaticCtmListCfgEntry 1 }

hpnicfWIPSStaticCtmListRowStatus OBJECT-TYPE
    SYNTAX RowStatus
    MAX-ACCESS read-create
    STATUS current
    DESCRIPTION
        "The status of this table entry."
    ::= { hpnicfWIPSStaticCtmListCfgEntry 2 }

hpnicfWIPSStaticBlockListCfgTable OBJECT-TYPE
    SYNTAX SEQUENCE OF HpnicfWIPSStaticBlockListCfgEntry
    MAX-ACCESS not-accessible
    STATUS current
    DESCRIPTION
        "The table provides the MAC address list
        of devices in the static block list.
        WIPS will ignore the frames from the devices in the list,
        and take the devices as rogue devices."
    ::= { hpnicfWIPSConfigGroup 6 }

hpnicfWIPSStaticBlockListCfgEntry OBJECT-TYPE
    SYNTAX HpnicfWIPSStaticBlockListCfgEntry
    MAX-ACCESS not-accessible
    STATUS current
    DESCRIPTION
        "Each entry contains information of each MAC address
        in the static block list.
        "
    INDEX { hpnicfWIPSStaticBlockListMAC }
    ::= { hpnicfWIPSStaticBlockListCfgTable 1 }

HpnicfWIPSStaticBlockListCfgEntry ::=
    SEQUENCE {
        hpnicfWIPSStaticBlockListMAC
            MacAddress,
        hpnicfWIPSStaticBlockListRowStatus
            RowStatus
     }

hpnicfWIPSStaticBlockListMAC OBJECT-TYPE
    SYNTAX MacAddress
    MAX-ACCESS not-accessible
    STATUS current
    DESCRIPTION
        "Represents the MAC address in static block list."
    ::= { hpnicfWIPSStaticBlockListCfgEntry 1 }

hpnicfWIPSStaticBlockListRowStatus OBJECT-TYPE
    SYNTAX RowStatus
    MAX-ACCESS read-create
    STATUS current
    DESCRIPTION
        "The status of this table entry."
    ::= { hpnicfWIPSStaticBlockListCfgEntry 2 }

hpnicfWIPSStaticTrustListCfgTable OBJECT-TYPE
    SYNTAX SEQUENCE OF HpnicfWIPSStaticTrustListCfgEntry
    MAX-ACCESS not-accessible
    STATUS current
    DESCRIPTION
        "The table provides the MAC address list
        of devices in the static trust list.
        WIPS will take the devices in the list as authorized devices."
    ::= { hpnicfWIPSConfigGroup 7 }

hpnicfWIPSStaticTrustListCfgEntry OBJECT-TYPE
    SYNTAX HpnicfWIPSStaticTrustListCfgEntry
    MAX-ACCESS not-accessible
    STATUS current
    DESCRIPTION
        "Each entry contains information of each MAC address
        in the static trust list.
        "
    INDEX { hpnicfWIPSStaticTrustListMAC }
    ::= { hpnicfWIPSStaticTrustListCfgTable 1 }

HpnicfWIPSStaticTrustListCfgEntry ::=
    SEQUENCE {
        hpnicfWIPSStaticTrustListMAC
            MacAddress,
        hpnicfWIPSStaticTrustListRowStatus
            RowStatus
     }

hpnicfWIPSStaticTrustListMAC OBJECT-TYPE
    SYNTAX MacAddress
    MAX-ACCESS not-accessible
    STATUS current
    DESCRIPTION
        "Represents the MAC address in static trust list."
    ::= { hpnicfWIPSStaticTrustListCfgEntry 1 }

hpnicfWIPSStaticTrustListRowStatus OBJECT-TYPE
    SYNTAX RowStatus
    MAX-ACCESS read-create
    STATUS current
    DESCRIPTION
        "The status of this table entry."
    ::= { hpnicfWIPSStaticTrustListCfgEntry 2 }

hpnicfWIPSIgnoreListCfgTable OBJECT-TYPE
    SYNTAX SEQUENCE OF HpnicfWIPSIgnoreListCfgEntry
    MAX-ACCESS not-accessible
    STATUS current
    DESCRIPTION
        "The table provides the MAC address list of devices in the ignore list.
        WIPS will ignore the events caused by the device in the list."
    ::= { hpnicfWIPSConfigGroup 8 }

hpnicfWIPSIgnoreListCfgEntry OBJECT-TYPE
    SYNTAX HpnicfWIPSIgnoreListCfgEntry
    MAX-ACCESS not-accessible
    STATUS current
    DESCRIPTION
        "Each entry contains information of each MAC address in the ignore list.
        "
    INDEX { hpnicfWIPSIgnoreListMAC }
    ::= { hpnicfWIPSIgnoreListCfgTable 1 }

HpnicfWIPSIgnoreListCfgEntry ::=
    SEQUENCE {
        hpnicfWIPSIgnoreListMAC
            MacAddress,
        hpnicfWIPSIgnoreListRowStatus
            RowStatus
     }

hpnicfWIPSIgnoreListMAC OBJECT-TYPE
    SYNTAX MacAddress
    MAX-ACCESS not-accessible
    STATUS current
    DESCRIPTION
        "Represents the MAC address in ignore list."
    ::= { hpnicfWIPSIgnoreListCfgEntry 1 }

hpnicfWIPSIgnoreListRowStatus OBJECT-TYPE
    SYNTAX RowStatus
    MAX-ACCESS read-create
    STATUS current
    DESCRIPTION
        "The status of this table entry."
    ::= { hpnicfWIPSIgnoreListCfgEntry 2 }

hpnicfWIPSDctModeTable OBJECT-TYPE
    SYNTAX SEQUENCE OF HpnicfWIPSDctModeEntry
    MAX-ACCESS not-accessible
    STATUS current
    DESCRIPTION
        "The table represents the list of AP scanning mode configuration
        on radio."
    ::= { hpnicfWIPSConfigGroup 9 }

hpnicfWIPSDctModeEntry OBJECT-TYPE
    SYNTAX HpnicfWIPSDctModeEntry
    MAX-ACCESS not-accessible
    STATUS current
    DESCRIPTION
        "Each entry contains information of WIPS scanning mode on radio."
    INDEX { hpnicfWIPSDctModeAPName, hpnicfWIPSDctModeRadio }
    ::= { hpnicfWIPSDctModeTable 1 }

HpnicfWIPSDctModeEntry ::=
    SEQUENCE {
        hpnicfWIPSDctModeAPName
            OCTET STRING,
        hpnicfWIPSDctModeRadio
            Integer32,
        hpnicfWIPSDctModeScanMode
            INTEGER,
        hpnicfWIPSDctModeRowStatus
            RowStatus
     }

hpnicfWIPSDctModeAPName OBJECT-TYPE
    SYNTAX OCTET STRING (SIZE (1..64))
    MAX-ACCESS not-accessible
    STATUS current
    DESCRIPTION
        "Represents the name of AP."
    ::= { hpnicfWIPSDctModeEntry 1 }

hpnicfWIPSDctModeRadio OBJECT-TYPE
    SYNTAX Integer32 (1..4)
    MAX-ACCESS not-accessible
    STATUS current
    DESCRIPTION
        "Represents the radio of AP."
    ::= { hpnicfWIPSDctModeEntry 2 }

hpnicfWIPSDctModeScanMode OBJECT-TYPE
    SYNTAX INTEGER
        {
        accessFirst(1),
        detectFirst(2),
        middle(3),
        detectOnly(4)
        }
    MAX-ACCESS read-create
    STATUS current
    DESCRIPTION
        "Represents the scanning mode.
        The radio enable-disable status must be disabled before
        WIPS scanning mode is configured on this radio.
        The mesh feature must be disabled before any WIPS scanning mode
        is set on radio.
        This radio can not apply any service template before
        the detectOnly scanning mode is set on the radio. "
    ::= { hpnicfWIPSDctModeEntry 3 }

hpnicfWIPSDctModeRowStatus OBJECT-TYPE
    SYNTAX RowStatus
    MAX-ACCESS read-create
    STATUS current
    DESCRIPTION
        "The status of this table entry."
    ::= { hpnicfWIPSDctModeEntry 4 }

hpnicfWIPSSigConfigGroup OBJECT IDENTIFIER ::= { hpnicfWIPSConfigGroup 10 }

hpnicfWIPSSigPolicyTable OBJECT-TYPE
    SYNTAX SEQUENCE OF HpnicfWIPSSigPolicyEntry
    MAX-ACCESS not-accessible
    STATUS current
    DESCRIPTION
        "The table defines the parameters for WIPS signature policy.
        One policy could be assigned to different VSDs.
        "
    ::= { hpnicfWIPSSigConfigGroup 1 }

hpnicfWIPSSigPolicyEntry OBJECT-TYPE
    SYNTAX HpnicfWIPSSigPolicyEntry
    MAX-ACCESS not-accessible
    STATUS current
    DESCRIPTION
        "Each entry contains information of each signature policy."
    INDEX { hpnicfWIPSSigPolicyNameCfg }
    ::= { hpnicfWIPSSigPolicyTable 1 }

HpnicfWIPSSigPolicyEntry ::=
    SEQUENCE {
        hpnicfWIPSSigPolicyNameCfg
            OCTET STRING,
        hpnicfWIPSSigPolicyRowStatus
            RowStatus
     }

hpnicfWIPSSigPolicyNameCfg OBJECT-TYPE
    SYNTAX OCTET STRING (SIZE (1..32))
    MAX-ACCESS not-accessible
    STATUS current
    DESCRIPTION
        "Represents the name of signature policy."
    ::= { hpnicfWIPSSigPolicyEntry 1 }

hpnicfWIPSSigPolicyRowStatus OBJECT-TYPE
    SYNTAX RowStatus
    MAX-ACCESS read-create
    STATUS current
    DESCRIPTION
        "The status of this table entry."
    ::= { hpnicfWIPSSigPolicyEntry 2 }

hpnicfWIPSSigRule2PolicyTable OBJECT-TYPE
    SYNTAX SEQUENCE OF HpnicfWIPSSigRule2PolicyEntry
    MAX-ACCESS not-accessible
    STATUS current
    DESCRIPTION
        "The table defines the signature rules been attached to the signature policy.
        "
    ::= { hpnicfWIPSSigConfigGroup 2 }

hpnicfWIPSSigRule2PolicyEntry OBJECT-TYPE
    SYNTAX HpnicfWIPSSigRule2PolicyEntry
    MAX-ACCESS not-accessible
    STATUS current
    DESCRIPTION
        "Each entry contains information of each signature rules
        attached to signature policy."
    INDEX { hpnicfWIPSSigPolicyNameCfg, hpnicfWIPSSigRule2PolicySigRuleIDCfg }
    ::= { hpnicfWIPSSigRule2PolicyTable 1 }

HpnicfWIPSSigRule2PolicyEntry ::=
    SEQUENCE {
        hpnicfWIPSSigRule2PolicySigRuleIDCfg
            Unsigned32,
        hpnicfWIPSSigRule2PolicyRowStatus
            RowStatus,
        hpnicfWIPSSigRule2PolicyPrecedence
            Unsigned32
     }

hpnicfWIPSSigRule2PolicySigRuleIDCfg OBJECT-TYPE
    SYNTAX Unsigned32 (1..64)
    MAX-ACCESS not-accessible
    STATUS current
    DESCRIPTION
        "Represents the ID of signature rule attached to signature policy."
    ::= { hpnicfWIPSSigRule2PolicyEntry 1 }

hpnicfWIPSSigRule2PolicyRowStatus OBJECT-TYPE
    SYNTAX RowStatus
    MAX-ACCESS read-create
    STATUS current
    DESCRIPTION
        "The status of this table entry."
    ::= { hpnicfWIPSSigRule2PolicyEntry 2 }

hpnicfWIPSSigRule2PolicyPrecedence OBJECT-TYPE
    SYNTAX Unsigned32 (1..64)
    MAX-ACCESS read-create
    STATUS current
    DESCRIPTION
        "Represents the precedence of signature rule attached to signature policy."
    DEFVAL { 1 }
    ::= { hpnicfWIPSSigRule2PolicyEntry 3 }

hpnicfWIPSSigRuleTable OBJECT-TYPE
    SYNTAX SEQUENCE OF HpnicfWIPSSigRuleEntry
    MAX-ACCESS not-accessible
    STATUS current
    DESCRIPTION
        "The table defines the signature rules.
        "
    ::= { hpnicfWIPSSigConfigGroup 3 }

hpnicfWIPSSigRuleEntry OBJECT-TYPE
    SYNTAX HpnicfWIPSSigRuleEntry
    MAX-ACCESS not-accessible
    STATUS current
    DESCRIPTION
        "Each entry contains information of each signature rules."
    INDEX { hpnicfWIPSSigRuleName }
    ::= { hpnicfWIPSSigRuleTable 1 }

HpnicfWIPSSigRuleEntry ::=
    SEQUENCE {
        hpnicfWIPSSigRuleName
            OCTET STRING,
        hpnicfWIPSSigRuleID
            Integer32,
        hpnicfWIPSSigRuleRowStatus
            RowStatus,
        hpnicfWIPSSigSubRuleMatchAll
            TruthValue,
        hpnicfWIPSSigRuleDctPeriod
            Unsigned32,
        hpnicfWIPSSigRuleTrackMethod
            INTEGER,
        hpnicfWIPSSigRuleDctThresholdPerMAC
            Unsigned32,
        hpnicfWIPSSigRuleDctThresholdPerSig
            Unsigned32,
        hpnicfWIPSSigRuleActionEvtLevel
            Unsigned32,
        hpnicfWIPSSigRuleQuietTime
            Unsigned32,
        hpnicfWIPSSigSubRuleFrameType
            INTEGER,
        hpnicfWIPSSigSubRuleFrameSubType
            INTEGER,
        hpnicfWIPSSigSubRuleMac
            OCTET STRING,
        hpnicfWIPSSigSubRuleMacType
            INTEGER,
        hpnicfWIPSSigSubRuleSeqNumMin
            Unsigned32,
        hpnicfWIPSSigSubRuleSeqNumMax
            Unsigned32,
        hpnicfWIPSSigSubRuleSSIDLenMin
            Unsigned32,
        hpnicfWIPSSigSubRuleSSIDLenMax
            Unsigned32,
        hpnicfWIPSSigSubRuleSSID
            OCTET STRING,
        hpnicfWIPSSigSubRuleSSIDOpe
            INTEGER,
        hpnicfWIPSSigSubRuleSSIDCase
            TruthValue
     }

hpnicfWIPSSigRuleName OBJECT-TYPE
    SYNTAX OCTET STRING (SIZE (1..32))
    MAX-ACCESS not-accessible
    STATUS current
    DESCRIPTION
        "Represents the name of signature rule."
    ::= { hpnicfWIPSSigRuleEntry 1 }

hpnicfWIPSSigRuleID OBJECT-TYPE
    SYNTAX Integer32 (1..64)
    MAX-ACCESS read-create
    STATUS current
    DESCRIPTION
        "Represents the ID of signature rule.
        The values from 1 to 32 are for built-in rules, which can not
        be assigned to user-define rules.
        When a user-define signature rule is being created, if ID is not specified,
        the ID of the rule will be automatically assigned, which values from 33 to 64.
        Once the rule is created, the ID is fixed and can not be changed again."
    ::= { hpnicfWIPSSigRuleEntry 2 }

hpnicfWIPSSigRuleRowStatus OBJECT-TYPE
    SYNTAX RowStatus
    MAX-ACCESS read-create
    STATUS current
    DESCRIPTION
        "The status of this table entry."
    ::= { hpnicfWIPSSigRuleEntry 3 }

hpnicfWIPSSigSubRuleMatchAll OBJECT-TYPE
    SYNTAX TruthValue
    MAX-ACCESS read-create
    STATUS current
    DESCRIPTION
        "Represents whether match all the sub rules
        which have been configured in the signature rule.
        The default value for user-define rule is false,
        and for built-in rule is true."
    ::= { hpnicfWIPSSigRuleEntry 4 }

hpnicfWIPSSigRuleDctPeriod OBJECT-TYPE
    SYNTAX Unsigned32
    UNITS "second"
    MAX-ACCESS read-create
    STATUS current
    DESCRIPTION
        "Represents the detect period of signature rule.
         Available value limits from 1 to 3600.
         The default value depends on the certain rule.
         For user-define rules it is 60.
         The value 0xffffffff represents restoring default value operation."
    ::= { hpnicfWIPSSigRuleEntry 5 }

hpnicfWIPSSigRuleTrackMethod OBJECT-TYPE
    SYNTAX INTEGER
        {
        perSig(1),
        perMAC(2),
        both(3)
        }
    MAX-ACCESS read-create
    STATUS current
    DESCRIPTION
        "Represents the track-method for the signature rule.
         The default value depends on the certain rule.
         For user-define rules it is 'both(3)'."
    ::= { hpnicfWIPSSigRuleEntry 6 }

hpnicfWIPSSigRuleDctThresholdPerMAC OBJECT-TYPE
    SYNTAX Unsigned32
    MAX-ACCESS read-create
    STATUS current
    DESCRIPTION
        "Represents the detect threshold for per-MAC track-method.
         Available value limits from 1 to 32000.
         The default value depends on the certain rule.
         For user-define rules it is 1000.
         The value 0xffffffff represents restoring default value operation."
    ::= { hpnicfWIPSSigRuleEntry 7 }

hpnicfWIPSSigRuleDctThresholdPerSig OBJECT-TYPE
    SYNTAX Unsigned32
    MAX-ACCESS read-create
    STATUS current
    DESCRIPTION
        "Represents the detect threshold for per-Signature track-method.
         Available value limits from 1 to 32000.
         The default value depends on the certain rule.
         For user-define rules it is 1000.
         The value 0xffffffff represents restoring default value operation."
    ::= { hpnicfWIPSSigRuleEntry 8 }

hpnicfWIPSSigRuleActionEvtLevel OBJECT-TYPE
    SYNTAX Unsigned32
    MAX-ACCESS read-create
    STATUS current
    DESCRIPTION
        "Represents the level of event sended for the action of reporting event alarm.
         Available value limits from 0 to 7.
         The default value depends on the certain rule.
         For user-define rules it is 0xffffffff."
    ::= { hpnicfWIPSSigRuleEntry 9 }

hpnicfWIPSSigRuleQuietTime OBJECT-TYPE
    SYNTAX Unsigned32
    MAX-ACCESS read-create
    STATUS current
    DESCRIPTION
        "Represents the quiet time after reporting event alarm.
         Available value limits from 60 to 32000.
         The default value depends on the certain rule.
         For user-define rules it is 900.
         The value 0xffffffff represents restoring default value operation."
    ::= { hpnicfWIPSSigRuleEntry 10 }

hpnicfWIPSSigSubRuleFrameType OBJECT-TYPE
    SYNTAX INTEGER
        {
        manage(0),
        control(1),
        data(2),
        undo(3)
        }
    MAX-ACCESS read-create
    STATUS current
    DESCRIPTION
        "Represents the type of frame to match.
        0x0 management type
        0x1 control type
        0x2 data type
        The default value depends on the certain rule.
        For user-define rules it is 'undo(3)'."
    ::= { hpnicfWIPSSigRuleEntry 11 }

hpnicfWIPSSigSubRuleFrameSubType OBJECT-TYPE
    SYNTAX INTEGER
        {
        none(0),
        assocReq(1),
        assocRes(2),
        probeReq(3),
        beacon(4),
        disasso(5),
        auth(6),
        deauth(7)
        }
    MAX-ACCESS read-create
    STATUS current
    DESCRIPTION
        "Represents the sub-type of frame to match.
        1 association request
        2 association response
        3 probe request
        4 beacon
        5 disassoc
        6 authentication
        7 de-authentication
        The default value depends on the certain rule.
        For user-define rules it is 'none(0)'."
    ::= { hpnicfWIPSSigRuleEntry 12 }

hpnicfWIPSSigSubRuleMac OBJECT-TYPE
    SYNTAX OCTET STRING (SIZE (0..12))
    MAX-ACCESS read-create
    STATUS current
    DESCRIPTION
        "Represents the MAC address or BSSID to match."
    ::= { hpnicfWIPSSigRuleEntry 13 }

hpnicfWIPSSigSubRuleMacType OBJECT-TYPE
    SYNTAX INTEGER
        {
        source(0),
        dest(1),
        bssid(2)
        }
    MAX-ACCESS read-create
    STATUS current
    DESCRIPTION
        "Represents the type of MAC address or BSSID to match.
         0 Source MAC address in the 802.11 frame header
         1 Destination MAC address in the 802.11 frame header
         2 BSSID field in the 802.11 frame header"
    ::= { hpnicfWIPSSigRuleEntry 14 }

hpnicfWIPSSigSubRuleSeqNumMin OBJECT-TYPE
    SYNTAX Unsigned32
    MAX-ACCESS read-create
    STATUS current
    DESCRIPTION
        "Represents the minimun value of sequence number of packet to match.
         Available value limits from 0 to 4094.
         The default value depends on the certain rule.
         For user-define rules it is 0xffffffff.
         The value 0xffffffff represents restoring default value operation."
    ::= { hpnicfWIPSSigRuleEntry 15 }

hpnicfWIPSSigSubRuleSeqNumMax OBJECT-TYPE
    SYNTAX Unsigned32
    MAX-ACCESS read-create
    STATUS current
    DESCRIPTION
        "Represents the maximum value of sequence number of packet to match.
        Available value limits from 1 to 4095.
        The default value depends on the certain rule.
        For user-define rules it is 0xffffffff.
        The value 0xffffffff represents restoring default value operation."
    ::= { hpnicfWIPSSigRuleEntry 16 }

hpnicfWIPSSigSubRuleSSIDLenMin OBJECT-TYPE
    SYNTAX Unsigned32
    MAX-ACCESS read-create
    STATUS current
    DESCRIPTION
        "Represents the minimun value of SSID of packet to match.
        Available value limits from 0 to 31.
        The default value depends on the certain rule.
        For user-define rules it is 0xffffffff.
        The value 0xffffffff represents restoring default value operation."
    ::= { hpnicfWIPSSigRuleEntry 17 }

hpnicfWIPSSigSubRuleSSIDLenMax OBJECT-TYPE
    SYNTAX Unsigned32
    MAX-ACCESS read-create
    STATUS current
    DESCRIPTION
        "Represents the maximum value of SSID of packet to match.
        Available value limits from 1 to 32.
        The default value depends on the certain rule.
        For user-define rules it is 0xffffffff.
        The value 0xffffffff represents restoring default value operation."
    ::= { hpnicfWIPSSigRuleEntry 18 }

hpnicfWIPSSigSubRuleSSID OBJECT-TYPE
    SYNTAX OCTET STRING (SIZE (0..32))
    MAX-ACCESS read-create
    STATUS current
    DESCRIPTION
        "Represents the string of SSID of packet to match."
    ::= { hpnicfWIPSSigRuleEntry 19 }

hpnicfWIPSSigSubRuleSSIDOpe OBJECT-TYPE
    SYNTAX INTEGER
        {
        include(1),
        notinclude(2),
        equal(3),
        notequal(4)
        }
    MAX-ACCESS read-create
    STATUS current
    DESCRIPTION
        "Represents the compare way of the SSID in the sub rule,
        including include/not include/equal/not equal."
    ::= { hpnicfWIPSSigRuleEntry 20 }

hpnicfWIPSSigSubRuleSSIDCase OBJECT-TYPE
    SYNTAX TruthValue
    MAX-ACCESS read-create
    STATUS current
    DESCRIPTION
        "Represents the case sensitive or not for the SSID match.
        'true': Case insensitive.
        'false': Case sensitive."
    DEFVAL { false }
    ::= { hpnicfWIPSSigRuleEntry 21 }

hpnicfWIPSSigSubRulePatternTable OBJECT-TYPE
    SYNTAX SEQUENCE OF HpnicfWIPSSigSubRulePatternEntry
    MAX-ACCESS not-accessible
    STATUS current
    DESCRIPTION
        "The table defines the signature sub rules
        which define the user-define match way through pattern of packet.
        "
    ::= { hpnicfWIPSSigConfigGroup 4 }

hpnicfWIPSSigSubRulePatternEntry OBJECT-TYPE
    SYNTAX HpnicfWIPSSigSubRulePatternEntry
    MAX-ACCESS not-accessible
    STATUS current
    DESCRIPTION
        "Each entry contains information of each pattern signature sub rules."
    INDEX { hpnicfWIPSSigRuleName, hpnicfWIPSSigSubRulePatternID }
    ::= { hpnicfWIPSSigSubRulePatternTable 1 }

HpnicfWIPSSigSubRulePatternEntry ::=
    SEQUENCE {
        hpnicfWIPSSigSubRulePatternID
            Unsigned32,
        hpnicfWIPSSigSubRuleRowStatus
            RowStatus,
        hpnicfWIPSSigSubRulePatternName
            OCTET STRING,
        hpnicfWIPSSigSubRulePatternOffset
            Integer32,
        hpnicfWIPSSigSubRulePatternMask
            Integer32,
        hpnicfWIPSSigSubRulePatternValueMin
            Unsigned32,
        hpnicfWIPSSigSubRulePatternValueMax
            Unsigned32,
        hpnicfWIPSSigSubRulePatternFromPayload
            TruthValue
     }

hpnicfWIPSSigSubRulePatternID OBJECT-TYPE
    SYNTAX Unsigned32 (1..27)
    MAX-ACCESS not-accessible
    STATUS current
    DESCRIPTION
        "Represents the ID of the pattern sub rule."
    ::= { hpnicfWIPSSigSubRulePatternEntry 1 }

hpnicfWIPSSigSubRuleRowStatus OBJECT-TYPE
    SYNTAX RowStatus
    MAX-ACCESS read-write
    STATUS current
    DESCRIPTION
        "The status of this table entry."
    ::= { hpnicfWIPSSigSubRulePatternEntry 2 }

hpnicfWIPSSigSubRulePatternName OBJECT-TYPE
    SYNTAX OCTET STRING (SIZE(0..32))
    MAX-ACCESS read-write
    STATUS current
    DESCRIPTION
        "Represents the name of the pattern sub rule."
    ::= { hpnicfWIPSSigSubRulePatternEntry 3 }

hpnicfWIPSSigSubRulePatternOffset OBJECT-TYPE
    SYNTAX Integer32 (0..2346)
    MAX-ACCESS read-write
    STATUS current
    DESCRIPTION
        "Represents the offset value of packet match."
    ::= { hpnicfWIPSSigSubRulePatternEntry 4 }

hpnicfWIPSSigSubRulePatternMask OBJECT-TYPE
    SYNTAX Integer32 (0..65535)
    MAX-ACCESS read-write
    STATUS current
    DESCRIPTION
        "Represents the mask value of packet match."
    ::= { hpnicfWIPSSigSubRulePatternEntry 5 }

hpnicfWIPSSigSubRulePatternValueMin OBJECT-TYPE
    SYNTAX Unsigned32
    MAX-ACCESS read-write
    STATUS current
    DESCRIPTION
        "Represents the minimun value of match byte.
         Available value limits from 0 to 65534."
    DEFVAL { 'ffffffff'h }
    ::= { hpnicfWIPSSigSubRulePatternEntry 6 }

hpnicfWIPSSigSubRulePatternValueMax OBJECT-TYPE
    SYNTAX Unsigned32
    MAX-ACCESS read-write
    STATUS current
    DESCRIPTION
        "Represents the maximun value of match byte.
         Available value limits from 1 to 65535."
    DEFVAL { 'ffffffff'h }
    ::= { hpnicfWIPSSigSubRulePatternEntry 7 }

hpnicfWIPSSigSubRulePatternFromPayload OBJECT-TYPE
    SYNTAX TruthValue
    MAX-ACCESS read-write
    STATUS current
    DESCRIPTION
        "Represents whether match start from the payload of the data frame."
    DEFVAL { false }
    ::= { hpnicfWIPSSigSubRulePatternEntry 8 }

hpnicfWIPSCtmConfigGroup OBJECT IDENTIFIER ::= { hpnicfWIPSConfigGroup 11 }

hpnicfWIPSCtmPolicyCfgSupportSet OBJECT-TYPE
    SYNTAX OCTET STRING (SIZE (16))
    MAX-ACCESS read-only
    STATUS current
    DESCRIPTION
        "Represents the bit string of supported countermeasure policy.
        The specific countermeasure policy is supported if its corresponding
        bit is set to 1; otherwise its corresponding bit is set to 0.
        bit3:  misconfigured AP
        bit4:  rogue AP
        bit5:  unauthorized station
        bit6:  external AP
        bit9:  misassociation station
        bit10: potential authorized AP
        bit11: potential rogue AP
        bit12: potential external AP
        bit13: uncategorized AP
        bit14: uncategorized station
        "
    ::= { hpnicfWIPSCtmConfigGroup 1 }

hpnicfWIPSCtmPolicyTable OBJECT-TYPE
    SYNTAX SEQUENCE OF HpnicfWIPSCtmPolicyEntry
    MAX-ACCESS not-accessible
    STATUS current
    DESCRIPTION
        "The table defines the parameters for WIPS countermeasure policy.
        One policy could be assigned to different VSDs.
        "
    ::= { hpnicfWIPSCtmConfigGroup 2 }

hpnicfWIPSCtmPolicyEntry OBJECT-TYPE
    SYNTAX HpnicfWIPSCtmPolicyEntry
    MAX-ACCESS not-accessible
    STATUS current
    DESCRIPTION
        "Each entry contains information of each countermeasure policy."
    INDEX { hpnicfWIPSCtmPolicyName }
    ::= { hpnicfWIPSCtmPolicyTable 1 }

HpnicfWIPSCtmPolicyEntry ::=
    SEQUENCE {
        hpnicfWIPSCtmPolicyName
            OCTET STRING,
        hpnicfWIPSCtmPolicyCfgRowStatus
            RowStatus,
        hpnicfWIPSCtmPolicyBitString
            OCTET STRING,
        hpnicfWIPSCtmPolicyFixedChl
            TruthValue,
        hpnicfWIPSCtmPolicyRogueAPPre
            Unsigned32,
        hpnicfWIPSCtmPolicyPtRogueAPPre
            Unsigned32,
        hpnicfWIPSCtmPolicyMisconfAPPre
            Unsigned32,
        hpnicfWIPSCtmPolicyExternalAPPre
            Unsigned32,
        hpnicfWIPSCtmPolicyPtExternalAPPre
            Unsigned32,
        hpnicfWIPSCtmPolicyUncateAPPre
            Unsigned32,
        hpnicfWIPSCtmPolicyPtAuthAPPre
            Unsigned32,
        hpnicfWIPSCtmPolicyMisassoStaPre
            Unsigned32,
        hpnicfWIPSCtmPolicyUncateStaPre
            Unsigned32,
        hpnicfWIPSCtmPolicyUnauthStaPre
            Unsigned32
     }

hpnicfWIPSCtmPolicyName OBJECT-TYPE
    SYNTAX OCTET STRING (SIZE (1..32))
    MAX-ACCESS not-accessible
    STATUS current
    DESCRIPTION
        "Represents the name of countermeasure policy."
    ::= { hpnicfWIPSCtmPolicyEntry 1 }

hpnicfWIPSCtmPolicyCfgRowStatus OBJECT-TYPE
    SYNTAX RowStatus
    MAX-ACCESS read-create
    STATUS current
    DESCRIPTION
        "The status of this table entry."
    ::= { hpnicfWIPSCtmPolicyEntry 2 }

hpnicfWIPSCtmPolicyBitString OBJECT-TYPE
    SYNTAX OCTET STRING (SIZE (16))
    MAX-ACCESS read-create
    STATUS current
    DESCRIPTION
        "Represents the bit string of countermeasure policy configuration.
        The specific countermeasure of device is enabled if its corresponding
        bit is set to 1; disabled if its corresponding bit is set to 0.
        bit3:  misconfigured AP
        bit4:  rogue AP
        bit5:  unauthorized station
        bit6:  external AP
        bit9:  misassociation station
        bit10: potential authorized AP
        bit11: potential rogue AP
        bit12: potential external AP
        bit13: uncategorized AP
        bit14: uncategorized station"
    ::= { hpnicfWIPSCtmPolicyEntry 3 }

hpnicfWIPSCtmPolicyFixedChl OBJECT-TYPE
    SYNTAX TruthValue
    MAX-ACCESS read-create
    STATUS current
    DESCRIPTION
        "Represents whether enable fixed channel scan function."
    DEFVAL { false }
    ::= { hpnicfWIPSCtmPolicyEntry 4 }

hpnicfWIPSCtmPolicyRogueAPPre OBJECT-TYPE
    SYNTAX Unsigned32
    MAX-ACCESS read-create
    STATUS current
    DESCRIPTION
        "Represents the precedence of countermeasure for rogue AP.
         Available value limits from 0 to 9.
         Value 0xffffffff represents undo operation."
    DEFVAL { 9 }
    ::= { hpnicfWIPSCtmPolicyEntry 5 }

hpnicfWIPSCtmPolicyPtRogueAPPre OBJECT-TYPE
    SYNTAX Unsigned32
    MAX-ACCESS read-create
    STATUS current
    DESCRIPTION
        "Represents the precedence of countermeasure
        for potential rogue AP.
        Available value limits from 0 to 9.
        Value 0xffffffff represents undo operation."
    DEFVAL { 7 }
    ::= { hpnicfWIPSCtmPolicyEntry 6 }

hpnicfWIPSCtmPolicyMisconfAPPre OBJECT-TYPE
    SYNTAX Unsigned32
    MAX-ACCESS read-create
    STATUS current
    DESCRIPTION
        "Represents the precedence of countermeasure
        for misconfigured AP.
        Available value limits from 0 to 9.
        Value 0xffffffff represents undo operation."
    DEFVAL { 3 }
    ::= { hpnicfWIPSCtmPolicyEntry 7 }

hpnicfWIPSCtmPolicyExternalAPPre OBJECT-TYPE
    SYNTAX Unsigned32
    MAX-ACCESS read-create
    STATUS current
    DESCRIPTION
        "Represents the precedence of countermeasure
        for external AP.
        Available value limits from 0 to 9.
        Value 0xffffffff represents undo operation."
    DEFVAL { 1 }
    ::= { hpnicfWIPSCtmPolicyEntry 8 }

hpnicfWIPSCtmPolicyPtExternalAPPre OBJECT-TYPE
    SYNTAX Unsigned32
    MAX-ACCESS read-create
    STATUS current
    DESCRIPTION
        "Represents the precedence of countermeasure
        for potential external AP.
        Available value limits from 0 to 9.
        Value 0xffffffff represents undo operation."
    DEFVAL { 2 }
    ::= { hpnicfWIPSCtmPolicyEntry 9 }

hpnicfWIPSCtmPolicyUncateAPPre OBJECT-TYPE
    SYNTAX Unsigned32
    MAX-ACCESS read-create
    STATUS current
    DESCRIPTION
        "Represents the precedence of countermeasure
        for uncategorized AP.
        Available value limits from 0 to 9.
        Value 0xffffffff represents undo operation."
    DEFVAL { 5 }
    ::= { hpnicfWIPSCtmPolicyEntry 10 }

hpnicfWIPSCtmPolicyPtAuthAPPre OBJECT-TYPE
    SYNTAX Unsigned32
    MAX-ACCESS read-create
    STATUS current
    DESCRIPTION
        "Represents the precedence of countermeasure
        for potential authorized AP.
        Available value limits from 0 to 9.
        Value 0xffffffff represents undo operation."
    DEFVAL { 0 }
    ::= { hpnicfWIPSCtmPolicyEntry 11 }

hpnicfWIPSCtmPolicyMisassoStaPre OBJECT-TYPE
    SYNTAX Unsigned32
    MAX-ACCESS read-create
    STATUS current
    DESCRIPTION
        "Represents the precedence of countermeasure
        for misassociated station.
        Available value limits from 0 to 9.
        Value 0xffffffff represents undo operation."
    DEFVAL { 6 }
    ::= { hpnicfWIPSCtmPolicyEntry 12 }

hpnicfWIPSCtmPolicyUncateStaPre OBJECT-TYPE
    SYNTAX Unsigned32
    MAX-ACCESS read-create
    STATUS current
    DESCRIPTION
        "Represents the precedence of countermeasure
        for uncategorized station.
        Available value limits from 0 to 9.
        Value 0xffffffff represents undo operation."
    DEFVAL { 4 }
    ::= { hpnicfWIPSCtmPolicyEntry 13 }

hpnicfWIPSCtmPolicyUnauthStaPre OBJECT-TYPE
    SYNTAX Unsigned32
    MAX-ACCESS read-create
    STATUS current
    DESCRIPTION
        "Represents the precedence of countermeasure
        for unauthorized station.
        Available value limits from 0 to 9.
        Value 0xffffffff represents undo operation."
    DEFVAL { 8 }
    ::= { hpnicfWIPSCtmPolicyEntry 14 }

hpnicfWIPSCtmPolicyDevListTable OBJECT-TYPE
    SYNTAX SEQUENCE OF HpnicfWIPSCtmPolicyDevListEntry
    MAX-ACCESS not-accessible
    STATUS current
    DESCRIPTION
        "The table defines the MAC address list of countermeasure device
        in WIPS countermeasure policy. "
    ::= { hpnicfWIPSCtmConfigGroup 3 }

hpnicfWIPSCtmPolicyDevListEntry OBJECT-TYPE
    SYNTAX HpnicfWIPSCtmPolicyDevListEntry
    MAX-ACCESS not-accessible
    STATUS current
    DESCRIPTION
        "Each entry contains information of each MAC address of device."
    INDEX { hpnicfWIPSCtmPolicyName,  hpnicfWIPSCtmPolicyDevMAC }
    ::= { hpnicfWIPSCtmPolicyDevListTable 1 }

HpnicfWIPSCtmPolicyDevListEntry ::=
    SEQUENCE {
        hpnicfWIPSCtmPolicyDevMAC
            MacAddress,
        hpnicfWIPSCtmPolicyDevRowStatus
            RowStatus
     }

hpnicfWIPSCtmPolicyDevMAC OBJECT-TYPE
    SYNTAX MacAddress
    MAX-ACCESS not-accessible
    STATUS current
    DESCRIPTION
        "Represents the MAC address of countermeasure device."
    ::= { hpnicfWIPSCtmPolicyDevListEntry 1 }

hpnicfWIPSCtmPolicyDevRowStatus OBJECT-TYPE
    SYNTAX RowStatus
    MAX-ACCESS read-create
    STATUS current
    DESCRIPTION
        "The status of this table entry."
    ::= { hpnicfWIPSCtmPolicyDevListEntry 2 }

hpnicfWIPSMalPktDctConfigGroup OBJECT IDENTIFIER ::= { hpnicfWIPSConfigGroup 12 }

hpnicfWIPSMalPktDctCfgLogSupportSet OBJECT-TYPE
    SYNTAX OCTET STRING  (SIZE (32))
    MAX-ACCESS read-only
    STATUS current
    DESCRIPTION
        "Represents the bit string of supported malformed packet detect policy
        controlling the log function.
        The specific malformed packet detect policy is supported if its corresponding
        bit is set to 1; otherwise its corresponding bit is set to 0.
        bit0:  invalid IE length
        bit1:  duplicated IE
        bit2:  redundant IE
        bit3:  invalid packet length
        bit4:  illegal IBSS and ESS
        bit5:  invalid source address
        bit6:  overflow EAPOL key length
        bit7:  malformed authetication
        bit8:  malformed association request
        bit9:  malformed HT-IE
        bit10: large duration
        bit11: null probe response
        bit12: invalid deauthentication reason code
        bit13: invalid disassociation reason code
        bit14: overflow SSID length
        bit15: fata-jack"
    ::= { hpnicfWIPSMalPktDctConfigGroup 1 }

hpnicfWIPSMalPktDctCfgTrapSupportSet OBJECT-TYPE
    SYNTAX OCTET STRING (SIZE (32))
    MAX-ACCESS read-only
    STATUS current
    DESCRIPTION
        "Represents the bit string of supported malformed packet detect policy
        controlling the trap function.
        The specific malformed packet detect policy is supported if its corresponding
        bit is set to 1; otherwise its corresponding bit is set to 0.
        bit0:  invalid IE length
        bit1:  duplicated IE
        bit2:  redundant IE
        bit3:  invalid packet length
        bit4:  illegal IBSS and ESS
        bit5:  invalid source address
        bit6:  overflow EAPOL key length
        bit7:  malformed authetication
        bit8:  malformed association request
        bit9:  malformed HT-IE
        bit10: large duration
        bit11: null probe response
        bit12: invalid deauthentication reason code
        bit13: invalid disassociation reason code
        bit14: overflow SSID length
        bit15: fata-jack"
    ::= { hpnicfWIPSMalPktDctConfigGroup 2 }

hpnicfWIPSMalPktDctPolicyTable OBJECT-TYPE
    SYNTAX SEQUENCE OF HpnicfWIPSMalPktDctPolicyEntry
    MAX-ACCESS not-accessible
    STATUS current
    DESCRIPTION
        "Represents."
    ::= { hpnicfWIPSMalPktDctConfigGroup 3 }

hpnicfWIPSMalPktDctPolicyEntry OBJECT-TYPE
    SYNTAX HpnicfWIPSMalPktDctPolicyEntry
    MAX-ACCESS not-accessible
    STATUS current
    DESCRIPTION
        "Represents."
    INDEX { hpnicfWIPSMalPktDctPolicyName }
    ::= { hpnicfWIPSMalPktDctPolicyTable 1 }

HpnicfWIPSMalPktDctPolicyEntry ::=
    SEQUENCE {
        hpnicfWIPSMalPktDctPolicyName
            OCTET STRING,
        hpnicfWIPSMalPktDctPolicyCfgRowStatus
            RowStatus,
        hpnicfWIPSMalPktDctPolicyLogBitString
            OCTET STRING,
        hpnicfWIPSMalPktDctPolicyTrapBitString
            OCTET STRING,
        hpnicfWIPSMalPktDctPolicyDurationThreshold
            Integer32,
        hpnicfWIPSMalPktDctPolicyQuietTime
            Integer32
     }

hpnicfWIPSMalPktDctPolicyName OBJECT-TYPE
    SYNTAX OCTET STRING (SIZE (1..32))
    MAX-ACCESS not-accessible
    STATUS current
    DESCRIPTION
        "Represents the name of malformed packet detect policy."
    ::= { hpnicfWIPSMalPktDctPolicyEntry 1 }

hpnicfWIPSMalPktDctPolicyCfgRowStatus OBJECT-TYPE
    SYNTAX RowStatus
    MAX-ACCESS read-create
    STATUS current
    DESCRIPTION
        "The status of this table entry."
    ::= { hpnicfWIPSMalPktDctPolicyEntry 2 }

hpnicfWIPSMalPktDctPolicyLogBitString OBJECT-TYPE
    SYNTAX OCTET STRING (SIZE (32))
    MAX-ACCESS read-create
    STATUS current
    DESCRIPTION
        "Represents the bit string of malformed packet detect policy
        controlling the log function configuration.
        The specific malformed packet detect is enbled if its corresponding
        bit is set to 1; disabled its corresponding bit is set to 0.
        bit0:  invalid IE length
        bit1:  duplicated IE
        bit2:  redundant IE
        bit3:  invalid packet length
        bit4:  illegal IBSS and ESS
        bit5:  invalid source address
        bit6:  overflow EAPOL key length
        bit7:  malformed authetication
        bit8:  malformed association request
        bit9:  malformed HT-IE
        bit10: large duration
        bit11: null probe response
        bit12: invalid deauthentication reason code
        bit13: invalid disassociation reason code
        bit14: overflow SSID length
        bit15: fata-jack"
    ::= { hpnicfWIPSMalPktDctPolicyEntry 3 }

hpnicfWIPSMalPktDctPolicyTrapBitString OBJECT-TYPE
    SYNTAX OCTET STRING (SIZE (32))
    MAX-ACCESS read-create
    STATUS current
    DESCRIPTION
        "Represents the bit string of malformed packet detect policy
        controlling the trap function configuration.
        The specific malformed packet detect is enbled if its corresponding
        bit is set to 1; disabled its corresponding bit is set to 0.
        bit0:  invalid IE length
        bit1:  duplicated IE
        bit2:  redundant IE
        bit3:  invalid packet length
        bit4:  illegal IBSS and ESS
        bit5:  invalid source address
        bit6:  overflow EAPOL key length
        bit7:  malformed authetication
        bit8:  malformed association request
        bit9:  malformed HT-IE
        bit10: large duration
        bit11: null probe response
        bit12: invalid deauthentication reason code
        bit13: invalid disassociation reason code
        bit14: overflow SSID length
        bit15: fata-jack"
    ::= { hpnicfWIPSMalPktDctPolicyEntry 4 }

hpnicfWIPSMalPktDctPolicyDurationThreshold OBJECT-TYPE
    SYNTAX Integer32 (1..32767)
    MAX-ACCESS read-create
    STATUS current
    DESCRIPTION
        "Represents the threshold of duration
        for large duration malformed packet detection."
    DEFVAL {5000}
    ::= { hpnicfWIPSMalPktDctPolicyEntry 5 }

hpnicfWIPSMalPktDctPolicyQuietTime OBJECT-TYPE
    SYNTAX Integer32 (5..604800)
    MAX-ACCESS read-create
    STATUS current
    DESCRIPTION
        "Represents the quiet time after reporting event alarm."
    DEFVAL { 600 }
    ::= { hpnicfWIPSMalPktDctPolicyEntry 6 }

hpnicfWIPSStaticTrustOUIListCfgTable OBJECT-TYPE
    SYNTAX SEQUENCE OF HpnicfWIPSStaticTrustOUIListCfgEntry
    MAX-ACCESS not-accessible
    STATUS current
    DESCRIPTION
        "The table provides the OUI list
        of devices in the static trust list.
        WIPS will take the devices in the list as authorized devices."
    ::= { hpnicfWIPSConfigGroup 13 }

hpnicfWIPSStaticTrustOUIListCfgEntry OBJECT-TYPE
    SYNTAX HpnicfWIPSStaticTrustOUIListCfgEntry
    MAX-ACCESS not-accessible
    STATUS current
    DESCRIPTION
        "Each entry contains information of each OUI
        in the static trust list.
        "
    INDEX { hpnicfWIPSStaticTrustOUIListOUI }
    ::= { hpnicfWIPSStaticTrustOUIListCfgTable 1 }

HpnicfWIPSStaticTrustOUIListCfgEntry ::=
    SEQUENCE {
        hpnicfWIPSStaticTrustOUIListOUI
            OCTET STRING,
        hpnicfWIPSStaticTrustOUIListRowStatus
            RowStatus
     }

hpnicfWIPSStaticTrustOUIListOUI OBJECT-TYPE
    SYNTAX OCTET STRING (SIZE (3))
    MAX-ACCESS not-accessible
    STATUS current
    DESCRIPTION
        "Represents the OUI in static trust list."
    ::= { hpnicfWIPSStaticTrustOUIListCfgEntry 1 }

hpnicfWIPSStaticTrustOUIListRowStatus OBJECT-TYPE
    SYNTAX RowStatus
    MAX-ACCESS read-create
    STATUS current
    DESCRIPTION
        "The status of this table entry."
    ::= { hpnicfWIPSStaticTrustOUIListCfgEntry 2 }

hpnicfWIPSStaticTrustVendorListCfgTable OBJECT-TYPE
    SYNTAX SEQUENCE OF HpnicfWIPSStaticTrustVendorListCfgEntry
    MAX-ACCESS not-accessible
    STATUS current
    DESCRIPTION
        "The table provides the vendor list
        of devices in the static trust list.
        WIPS will take the devices in the list as authorized devices."
    ::= { hpnicfWIPSConfigGroup 14 }

hpnicfWIPSStaticTrustVendorListCfgEntry OBJECT-TYPE
    SYNTAX HpnicfWIPSStaticTrustVendorListCfgEntry
    MAX-ACCESS not-accessible
    STATUS current
    DESCRIPTION
        "Each entry contains information of each vendor
        in the static trust list.
        "
    INDEX { hpnicfWIPSStaticTrustVendorListVendor }
    ::= { hpnicfWIPSStaticTrustVendorListCfgTable 1 }

HpnicfWIPSStaticTrustVendorListCfgEntry ::=
    SEQUENCE {
        hpnicfWIPSStaticTrustVendorListVendor
            OCTET STRING,
        hpnicfWIPSStaticTrustVendorListRowStatus
            RowStatus
     }

hpnicfWIPSStaticTrustVendorListVendor OBJECT-TYPE
    SYNTAX OCTET STRING (SIZE (1..64))
    MAX-ACCESS not-accessible
    STATUS current
    DESCRIPTION
        "Represents the vendor in static trust list."
    ::= { hpnicfWIPSStaticTrustVendorListCfgEntry 1 }

hpnicfWIPSStaticTrustVendorListRowStatus OBJECT-TYPE
    SYNTAX RowStatus
    MAX-ACCESS read-create
    STATUS current
    DESCRIPTION
        "The status of this table entry."
    ::= { hpnicfWIPSStaticTrustVendorListCfgEntry 2 }

hpnicfWIPSDetectGroup OBJECT IDENTIFIER ::= { hpnicfWIPS 2 }

hpnicfWIPSDctAPTable OBJECT-TYPE
    SYNTAX SEQUENCE OF HpnicfWIPSDctAPEntry
    MAX-ACCESS not-accessible
    STATUS current
    DESCRIPTION
        "The table represents the list of possible BSS information for
        APs detected by the WIPS."
    ::= { hpnicfWIPSDetectGroup 1 }

hpnicfWIPSDctAPEntry OBJECT-TYPE
    SYNTAX HpnicfWIPSDctAPEntry
    MAX-ACCESS not-accessible
    STATUS current
    DESCRIPTION
        "Each entry contains possible BSS information of each AP detected
        by WIPS."
    INDEX { hpnicfWIPSDctAPVSD, hpnicfWIPSDctAPBSSID }
    ::= { hpnicfWIPSDctAPTable 1 }

HpnicfWIPSDctAPEntry ::=
    SEQUENCE {
        hpnicfWIPSDctAPVSD
            OCTET STRING,
        hpnicfWIPSDctAPBSSID
            MacAddress,
        hpnicfWIPSDctAPRunningTime
            TimeTicks,
        hpnicfWIPSDctAPRunTmLastUpdateTm
            TimeTicks,
        hpnicfWIPSDctAPIsCountered
            TruthValue,
        hpnicfWIPSDctAPWorkChannel
            HpnicfWIPSChannel,
        hpnicfWIPSDctAPRadioType
            HpnicfWIPSRadioType,
        hpnicfWIPSDctAPAuthMethod
            HpnicfWIPSAuthMethod,
        hpnicfWIPSDctAPEncryptMethod
            HpnicfWIPSEncryptMethod,
        hpnicfWIPSDctAPSecurity
            HpnicfWIPSAPSecurityType,
        hpnicfWIPSDctAPSeverityLevel
            Unsigned32,
        hpnicfWIPSDctAPLastDctTm
            TimeTicks,
        hpnicfWIPSDctAPFirstDctTm
            TimeTicks,
        hpnicfWIPSDctAPAdd2BlackList
            TruthValue,
        hpnicfWIPSDctAPAdd2WhiteList
            TruthValue,
        hpnicfWIPSDctAPAdd2IgnoreList
            TruthValue,
        hpnicfWIPSDctAPAdd2CtmList
            TruthValue,
        hpnicfWIPSDctAPCategory
            HpnicfWIPSAPCategoryType,
        hpnicfWIPSDctAPCategoryWay
            HpnicfWIPSDevCategoryWay,
        hpnicfWIPSDctAPStatus
            HpnicfWIPSDevStatus,
        hpnicfWIPSDctAPSSID
            OCTET STRING,
        hpnicfWIPSDctAPAttachStaNum
            Integer32,
        hpnicfWIPSDctAPRptSensorNum
            Integer32,
        hpnicfWIPSDctAPVendor
            OCTET STRING
     }

hpnicfWIPSDctAPVSD OBJECT-TYPE
    SYNTAX OCTET STRING (SIZE (1..32))
    MAX-ACCESS not-accessible
    STATUS current
    DESCRIPTION
        "Represents the virtual security domain where the BSS was detected."
    ::= { hpnicfWIPSDctAPEntry 1 }

hpnicfWIPSDctAPBSSID OBJECT-TYPE
    SYNTAX MacAddress
    MAX-ACCESS not-accessible
    STATUS current
    DESCRIPTION
        "Represents the Basic Service Set."
    ::= { hpnicfWIPSDctAPEntry 2 }

hpnicfWIPSDctAPRunningTime OBJECT-TYPE
    SYNTAX TimeTicks
    MAX-ACCESS read-only
    STATUS current
    DESCRIPTION
        "Represents the time since AP started to work, which is got from
        beacon/probe response frame."
    ::= { hpnicfWIPSDctAPEntry 3 }

hpnicfWIPSDctAPRunTmLastUpdateTm OBJECT-TYPE
    SYNTAX TimeTicks
    MAX-ACCESS read-only
    STATUS current
    DESCRIPTION
        "Represents the time update hpnicfWIPSDctAPRunningTime since
        system is up."
    ::= { hpnicfWIPSDctAPEntry 4 }

hpnicfWIPSDctAPIsCountered OBJECT-TYPE
    SYNTAX TruthValue
    MAX-ACCESS read-only
    STATUS current
    DESCRIPTION
        "Represents whether the detected AP is countered by WIPS."
    ::= { hpnicfWIPSDctAPEntry 5 }

hpnicfWIPSDctAPWorkChannel OBJECT-TYPE
    SYNTAX HpnicfWIPSChannel
    MAX-ACCESS read-only
    STATUS current
    DESCRIPTION
        "Represents the radio channel which the detected AP work on."
    ::= { hpnicfWIPSDctAPEntry 6 }

hpnicfWIPSDctAPRadioType OBJECT-TYPE
    SYNTAX HpnicfWIPSRadioType
    MAX-ACCESS read-only
    STATUS current
    DESCRIPTION
        "Represents the radio type used by the detected AP."
    ::= { hpnicfWIPSDctAPEntry 7 }

hpnicfWIPSDctAPAuthMethod OBJECT-TYPE
    SYNTAX HpnicfWIPSAuthMethod
    MAX-ACCESS read-only
    STATUS current
    DESCRIPTION
        "Represents the authentication method used by the detected AP.
        none(1)         - No key management mode configured,
        psk(2)          - pre-shared key authentication,
        dot1x(3)        - 802.1x authentication.
        other(4)        - other authentication."
    ::= { hpnicfWIPSDctAPEntry 8 }

hpnicfWIPSDctAPEncryptMethod OBJECT-TYPE
    SYNTAX HpnicfWIPSEncryptMethod
    MAX-ACCESS read-only
    STATUS current
    DESCRIPTION
        "Represents the encrypt method used by the detected AP.
        none(1)     - clear text or no cipher method is configure,
        wep(2)      - WEP key,
        tkip(4)     - WPA Temporal Key encryption,
        ccmp(8)     - WPA AES CCMP encryption"
    ::= { hpnicfWIPSDctAPEntry 9 }

hpnicfWIPSDctAPSecurity OBJECT-TYPE
    SYNTAX HpnicfWIPSAPSecurityType
    MAX-ACCESS read-only
    STATUS current
    DESCRIPTION
        "Represents the security suites of the detected AP.
        clear  0x01
        wpa2   0x02
        wpa    0x04
        wep    0x08"
    ::= { hpnicfWIPSDctAPEntry 10 }

hpnicfWIPSDctAPSeverityLevel OBJECT-TYPE
    SYNTAX Unsigned32 (0..100)
    MAX-ACCESS read-only
    STATUS current
    DESCRIPTION
        "Represents the severity level of the detected AP."
    ::= { hpnicfWIPSDctAPEntry 11 }

hpnicfWIPSDctAPLastDctTm OBJECT-TYPE
    SYNTAX TimeTicks
    MAX-ACCESS read-only
    STATUS current
    DESCRIPTION
        "Represents the time that AP was detected for the last time since system
        is up."
    ::= { hpnicfWIPSDctAPEntry 12 }

hpnicfWIPSDctAPFirstDctTm OBJECT-TYPE
    SYNTAX TimeTicks
    MAX-ACCESS read-only
    STATUS current
    DESCRIPTION
        "Represents the time that AP was detected for the first time
        since system is up."
    ::= { hpnicfWIPSDctAPEntry 13 }

hpnicfWIPSDctAPAdd2BlackList OBJECT-TYPE
    SYNTAX TruthValue
    MAX-ACCESS read-write
    STATUS current
    DESCRIPTION
        "Represents whether the AP will be taken as a rogue AP.
        If the value is true, the MAC address will be automatically added
        into hpnicfWIPSBlockListTable and the category of the AP will be
        taken as rogue.
        If the value is false, the MAC address will be automatically deleted
        from hpnicfWIPSBlockListTable."
    DEFVAL { false }
    ::= { hpnicfWIPSDctAPEntry 14 }

hpnicfWIPSDctAPAdd2WhiteList OBJECT-TYPE
    SYNTAX TruthValue
    MAX-ACCESS read-write
    STATUS current
    DESCRIPTION
        "Represents whether the AP will be taken as an authorized AP.
        If the value is true, the MAC address will be automatically added
        into hpnicfWIPSTrustListTable.
        If the value is false, the MAC address will be automatically deleted
        from hpnicfWIPSTrustListTable"
    DEFVAL { false }
    ::= { hpnicfWIPSDctAPEntry 15 }

hpnicfWIPSDctAPAdd2IgnoreList OBJECT-TYPE
    SYNTAX TruthValue
    MAX-ACCESS read-write
    STATUS current
    DESCRIPTION
        "Represents whether the AP will be taken as an ignored AP.
        If the value is true, the MAC address will be automatically added
        into hpnicfWIPSIgnoreListTable.
        If the value is false, the MAC address will be automatically deleted
        from hpnicfWIPSIgnoreListTable"
    DEFVAL { false }
    ::= { hpnicfWIPSDctAPEntry 16 }

hpnicfWIPSDctAPAdd2CtmList OBJECT-TYPE
    SYNTAX TruthValue
    MAX-ACCESS read-write
    STATUS current
    DESCRIPTION
        "Represents whether the AP will be taken as a countered AP.
        If the value is true, the MAC address will be automatically added
        into hpnicfWIPSCountermeasureListTable.
        If the value is false, the MAC address will be automatically deleted
        from hpnicfWIPSCountermeasureListTable."
    DEFVAL { false }
    ::= { hpnicfWIPSDctAPEntry 17 }

hpnicfWIPSDctAPCategory OBJECT-TYPE
    SYNTAX HpnicfWIPSAPCategoryType
    MAX-ACCESS read-write
    STATUS current
    DESCRIPTION
        "Represents the categorized result of the AP.
        For set operation, only the following values are valid:
        authorized(2),rogue(3),misconfigured(4),external(5)"
    ::= { hpnicfWIPSDctAPEntry 18 }

hpnicfWIPSDctAPCategoryWay OBJECT-TYPE
    SYNTAX HpnicfWIPSDevCategoryWay
    MAX-ACCESS read-write
    STATUS current
    DESCRIPTION
        "Represents by which way the AP is categorized.
        manual(1)    -categorized by user
        autoByNMS(2) -categorized by NMS(Network Management System)
        autoByDev(3) -categorized by WIPS"
    DEFVAL { autoByDev }
    ::= { hpnicfWIPSDctAPEntry 19 }

hpnicfWIPSDctAPStatus OBJECT-TYPE
    SYNTAX HpnicfWIPSDevStatus
    MAX-ACCESS read-only
    STATUS current
    DESCRIPTION
        "Represents the status of the AP detected by WIPS."
    ::= { hpnicfWIPSDctAPEntry 20 }

hpnicfWIPSDctAPSSID OBJECT-TYPE
    SYNTAX OCTET STRING (SIZE (0..32))
    MAX-ACCESS read-only
    STATUS current
    DESCRIPTION
        "Represents the SSID broadcasted by AP."
    ::= { hpnicfWIPSDctAPEntry 21 }

hpnicfWIPSDctAPAttachStaNum OBJECT-TYPE
    SYNTAX Integer32
    MAX-ACCESS read-only
    STATUS current
    DESCRIPTION
        "Represents the number of clients associated with the detected AP."
    ::= { hpnicfWIPSDctAPEntry 22 }

hpnicfWIPSDctAPRptSensorNum OBJECT-TYPE
    SYNTAX Integer32
    MAX-ACCESS read-only
    STATUS current
    DESCRIPTION
        "Represents the number of sensors detecting the AP."
    ::= { hpnicfWIPSDctAPEntry 23 }


hpnicfWIPSDctAPVendor OBJECT-TYPE
    SYNTAX OCTET STRING (SIZE (0..64))
    MAX-ACCESS read-only
    STATUS current
    DESCRIPTION
        "Represents the vendor of this AP detected by WIPS."
    ::= { hpnicfWIPSDctAPEntry 24 }

hpnicfWIPSDctAPAttachStaTable OBJECT-TYPE
    SYNTAX SEQUENCE OF HpnicfWIPSDctAPAttachStaEntry
    MAX-ACCESS not-accessible
    STATUS current
    DESCRIPTION
        "The table represents the list of station associated with APs
        detected by the WIPS."
    ::= { hpnicfWIPSDetectGroup 2 }

hpnicfWIPSDctAPAttachStaEntry OBJECT-TYPE
    SYNTAX HpnicfWIPSDctAPAttachStaEntry
    MAX-ACCESS not-accessible
    STATUS current
    DESCRIPTION
        "Each entry contains possible station information detected
        by WIPS."
    INDEX { hpnicfWIPSDctAPVSD, hpnicfWIPSDctAPBSSID, hpnicfWIPSDctAPAttachStaMac }
    ::= { hpnicfWIPSDctAPAttachStaTable 1 }

HpnicfWIPSDctAPAttachStaEntry ::=
    SEQUENCE {
        hpnicfWIPSDctAPAttachStaMac
            MacAddress,
        hpnicfWIPSDctAPAttachStaRowStatus
            RowStatus
     }

hpnicfWIPSDctAPAttachStaMac OBJECT-TYPE
    SYNTAX MacAddress
    MAX-ACCESS not-accessible
    STATUS current
    DESCRIPTION
        "Represents the MAC address of station associated with AP."
    ::= { hpnicfWIPSDctAPAttachStaEntry 1 }

hpnicfWIPSDctAPAttachStaRowStatus OBJECT-TYPE
    SYNTAX RowStatus
    MAX-ACCESS read-only
    STATUS current
    DESCRIPTION
        "The status of this table entry. It is read-only and
        will return 'Not writable' for set operation."
    ::= { hpnicfWIPSDctAPAttachStaEntry 2 }

hpnicfWIPSDctAPRptSensorTable OBJECT-TYPE
    SYNTAX SEQUENCE OF HpnicfWIPSDctAPRptSensorEntry
    MAX-ACCESS not-accessible
    STATUS current
    DESCRIPTION
        "The table represents the list of sensors."
    ::= { hpnicfWIPSDetectGroup 3 }

hpnicfWIPSDctAPRptSensorEntry OBJECT-TYPE
    SYNTAX HpnicfWIPSDctAPRptSensorEntry
    MAX-ACCESS not-accessible
    STATUS current
    DESCRIPTION
        "Each entry contains possible sensor information of WIPS."
    INDEX { hpnicfWIPSDctAPVSD, hpnicfWIPSDctAPBSSID, hpnicfWIPSDctAPRptSensorName }
    ::= { hpnicfWIPSDctAPRptSensorTable 1 }

HpnicfWIPSDctAPRptSensorEntry ::=
    SEQUENCE {
        hpnicfWIPSDctAPRptSensorName
            OCTET STRING,
        hpnicfWIPSDctAPRptSensorRadioId
            Integer32,
        hpnicfWIPSDctAPRptRSSI
            Integer32,
        hpnicfWIPSDctAPLastRptTm
            TimeTicks
     }

hpnicfWIPSDctAPRptSensorName OBJECT-TYPE
    SYNTAX OCTET STRING (SIZE (1..64))
    MAX-ACCESS not-accessible
    STATUS current
    DESCRIPTION
        "Represents the name of sensor."
    ::= { hpnicfWIPSDctAPRptSensorEntry 1 }

hpnicfWIPSDctAPRptSensorRadioId OBJECT-TYPE
    SYNTAX Integer32 (1..4)
    MAX-ACCESS read-only
    STATUS current
    DESCRIPTION
        "Represents on which radio the sensor AP detected the AP."
    ::= { hpnicfWIPSDctAPRptSensorEntry 2 }

hpnicfWIPSDctAPRptRSSI OBJECT-TYPE
    SYNTAX Integer32 (0..90)
    MAX-ACCESS read-only
    STATUS current
    DESCRIPTION
        "Represents the current value of signal strength that WIPS sensor
        AP received from the AP."
    ::= { hpnicfWIPSDctAPRptSensorEntry 3 }

hpnicfWIPSDctAPLastRptTm OBJECT-TYPE
    SYNTAX TimeTicks
    MAX-ACCESS read-only
    STATUS current
    DESCRIPTION
        "Represents the time that AP was detected by this sensor
        for the last time since system is up."
    ::= { hpnicfWIPSDctAPRptSensorEntry 4 }

hpnicfWIPSDctStaTable OBJECT-TYPE
    SYNTAX SEQUENCE OF HpnicfWIPSDctStaEntry
    MAX-ACCESS not-accessible
    STATUS current
    DESCRIPTION
        "The table represents the list of possible information for
        stations detected by the WIPS."
    ::= { hpnicfWIPSDetectGroup 4 }

hpnicfWIPSDctStaEntry OBJECT-TYPE
    SYNTAX HpnicfWIPSDctStaEntry
    MAX-ACCESS not-accessible
    STATUS current
    DESCRIPTION
        "Each entry contains possible station information of each station
        detected by WIPS."
    INDEX { hpnicfWIPSDctStaVSD, hpnicfWIPSDctStaMac }
    ::= { hpnicfWIPSDctStaTable 1 }

HpnicfWIPSDctStaEntry ::=
    SEQUENCE {
        hpnicfWIPSDctStaVSD
            OCTET STRING,
        hpnicfWIPSDctStaMac
            MacAddress,
        hpnicfWIPSDctStaAssocBSSID
            MacAddress,
        hpnicfWIPSDctStaStatus
            HpnicfWIPSDevStatus,
        hpnicfWIPSDctStaCategory
            HpnicfWIPSClientCategoryType,
        hpnicfWIPSDctStaRadioType
            HpnicfWIPSRadioType,
        hpnicfWIPSDctStaWorkChannel
            HpnicfWIPSChannel,
        hpnicfWIPSDctStaIsCountered
            TruthValue,
        hpnicfWIPSDctStaAdd2BlackList
            TruthValue,
        hpnicfWIPSDctStaAdd2WhiteList
            TruthValue,
        hpnicfWIPSDctStaAdd2IgnoreList
            TruthValue,
        hpnicfWIPSDctStaAdd2CtmList
            TruthValue,
        hpnicfWIPSDctStaFirstDctTm
            TimeTicks,
        hpnicfWIPSDctStaLastDctTm
            TimeTicks,
        hpnicfWIPSDctStaRptSensorNum
            Integer32,
        hpnicfWIPSDctStaState
            INTEGER,
        hpnicfWIPSDctStaVendor
            OCTET STRING
     }

hpnicfWIPSDctStaVSD OBJECT-TYPE
    SYNTAX OCTET STRING (SIZE (1..32))
    MAX-ACCESS not-accessible
    STATUS current
    DESCRIPTION
        "Represents the virtual security domain in which the station was detected."
    ::= { hpnicfWIPSDctStaEntry 1 }

hpnicfWIPSDctStaMac OBJECT-TYPE
    SYNTAX MacAddress
    MAX-ACCESS not-accessible
    STATUS current
    DESCRIPTION
        "Represents the MAC address of station."
    ::= { hpnicfWIPSDctStaEntry 2 }

hpnicfWIPSDctStaAssocBSSID OBJECT-TYPE
    SYNTAX MacAddress
    MAX-ACCESS read-only
    STATUS current
    DESCRIPTION
        "Represents the BSSID which station associates with."
    ::= { hpnicfWIPSDctStaEntry 3 }

hpnicfWIPSDctStaStatus OBJECT-TYPE
    SYNTAX HpnicfWIPSDevStatus
    MAX-ACCESS read-only
    STATUS current
    DESCRIPTION
        "Represents the status of this station detected by WIPS."
    ::= { hpnicfWIPSDctStaEntry 4 }

hpnicfWIPSDctStaCategory OBJECT-TYPE
    SYNTAX HpnicfWIPSClientCategoryType
    MAX-ACCESS read-only
    STATUS current
    DESCRIPTION
        "Represents the categorized result of the station."
    ::= { hpnicfWIPSDctStaEntry 5 }

hpnicfWIPSDctStaRadioType OBJECT-TYPE
    SYNTAX HpnicfWIPSRadioType
    MAX-ACCESS read-only
    STATUS current
    DESCRIPTION
        "Represents the radio type used by the detected station."
    ::= { hpnicfWIPSDctStaEntry 6 }

hpnicfWIPSDctStaWorkChannel OBJECT-TYPE
    SYNTAX HpnicfWIPSChannel
    MAX-ACCESS read-only
    STATUS current
    DESCRIPTION
        "Represents on which radio channel that WIPS sensor AP detected
        the station."
    ::= { hpnicfWIPSDctStaEntry 7 }

hpnicfWIPSDctStaIsCountered OBJECT-TYPE
    SYNTAX TruthValue
    MAX-ACCESS read-only
    STATUS current
    DESCRIPTION
        "Represents whether the detected station is countered by WIPS."
    ::= { hpnicfWIPSDctStaEntry 8 }

hpnicfWIPSDctStaAdd2BlackList OBJECT-TYPE
    SYNTAX TruthValue
    MAX-ACCESS read-write
    STATUS current
    DESCRIPTION
        "Represents whether the station will be taken as a rogue station.
        If the value is true, the MAC address will be automatically added
        into hpnicfWIPSBlockListTable and the category of the station will be
        taken as rogue.
        If the value is false, the MAC address will be automatically deleted
        from hpnicfWIPSBlockListTable."
    DEFVAL { false }
    ::= { hpnicfWIPSDctStaEntry 9 }

hpnicfWIPSDctStaAdd2WhiteList OBJECT-TYPE
    SYNTAX TruthValue
    MAX-ACCESS read-write
    STATUS current
    DESCRIPTION
        "Represents whether the station will be taken as an authorized station.
        If the value is true, the MAC address will be automatically added
        into hpnicfWIPSTrustListTable.
        If the value is false, the MAC address will be automatically deleted
        from hpnicfWIPSTrustListTable."
    DEFVAL { false }
    ::= { hpnicfWIPSDctStaEntry 10 }

hpnicfWIPSDctStaAdd2IgnoreList OBJECT-TYPE
    SYNTAX TruthValue
    MAX-ACCESS read-write
    STATUS current
    DESCRIPTION
        "Represents whether the station will be taken as an ignored station.
        If the value is true, the MAC address will be automatically added
        into hpnicfWIPSIgnoreListTable.
        If the value is false, the MAC address will be automatically deleted
        from hpnicfWIPSIgnoreListTable."
    DEFVAL { false }
    ::= { hpnicfWIPSDctStaEntry 11 }

hpnicfWIPSDctStaAdd2CtmList OBJECT-TYPE
    SYNTAX TruthValue
    MAX-ACCESS read-write
    STATUS current
    DESCRIPTION
        "Represents whether the station will be taken as a countered station.
        If the value is true, the MAC address will be automatically added
        into hpnicfWIPSCountermeasureListTable.
        If the value is false, the MAC address will be automatically deleted
        from hpnicfWIPSCountermeasureListTable."
    DEFVAL { false }
    ::= { hpnicfWIPSDctStaEntry 12 }

hpnicfWIPSDctStaFirstDctTm OBJECT-TYPE
    SYNTAX TimeTicks
    MAX-ACCESS read-only
    STATUS current
    DESCRIPTION
        "Represents the time that station was detected for the first time
        since system is up."
    ::= { hpnicfWIPSDctStaEntry 13 }

hpnicfWIPSDctStaLastDctTm OBJECT-TYPE
    SYNTAX TimeTicks
    MAX-ACCESS read-only
    STATUS current
    DESCRIPTION
        "Represents the time that station was detected for the last time
        since system is up."
    ::= { hpnicfWIPSDctStaEntry 14 }

hpnicfWIPSDctStaRptSensorNum OBJECT-TYPE
    SYNTAX Integer32
    MAX-ACCESS read-only
    STATUS current
    DESCRIPTION
        "Represents the number of sensors detecting the station."
    ::= { hpnicfWIPSDctStaEntry 15 }

hpnicfWIPSDctStaState OBJECT-TYPE
    SYNTAX INTEGER
    {
        authentication(1),
        association(2),
        eapSuccess(3),
        eapLogoff(4),
        disassociation(5),
        deauthentication(6)
    }
    MAX-ACCESS read-only
    STATUS current
    DESCRIPTION
        "Represents the authentication state of station with AP."
    ::= { hpnicfWIPSDctStaEntry 16 }

hpnicfWIPSDctStaVendor OBJECT-TYPE
    SYNTAX OCTET STRING (SIZE (0..64))
    MAX-ACCESS read-only
    STATUS current
    DESCRIPTION
        "Represents the vendor of this station detected by WIPS."
    ::= { hpnicfWIPSDctStaEntry 17 }

hpnicfWIPSDctStaRptSensorTable OBJECT-TYPE
    SYNTAX SEQUENCE OF HpnicfWIPSDctStaRptSensorEntry
    MAX-ACCESS not-accessible
    STATUS current
    DESCRIPTION
        "The table represents the list of sensors detecting the station."
    ::= { hpnicfWIPSDetectGroup 5 }

hpnicfWIPSDctStaRptSensorEntry OBJECT-TYPE
    SYNTAX HpnicfWIPSDctStaRptSensorEntry
    MAX-ACCESS not-accessible
    STATUS current
    DESCRIPTION
        "Each entry contains possible sensor information of WIPS."
    INDEX { hpnicfWIPSDctStaVSD, hpnicfWIPSDctStaMac, hpnicfWIPSDctStaRtpSensorName }
    ::= { hpnicfWIPSDctStaRptSensorTable 1 }

HpnicfWIPSDctStaRptSensorEntry ::=
    SEQUENCE {
        hpnicfWIPSDctStaRtpSensorName
            OCTET STRING,
        hpnicfWIPSDctStaRptSensorRadioId
            Integer32,
        hpnicfWIPSDctStaRptRSSI
            Integer32,
        hpnicfWIPSDctStaLastRptTm
            TimeTicks
     }

hpnicfWIPSDctStaRtpSensorName OBJECT-TYPE
    SYNTAX OCTET STRING (SIZE (1..64))
    MAX-ACCESS not-accessible
    STATUS current
    DESCRIPTION
        "Represents the name of sensor."
    ::= { hpnicfWIPSDctStaRptSensorEntry 1 }

hpnicfWIPSDctStaRptSensorRadioId OBJECT-TYPE
    SYNTAX Integer32 (1..4)
    MAX-ACCESS read-only
    STATUS current
    DESCRIPTION
        "Represents on which radio the sensor AP detected the station."
    ::= { hpnicfWIPSDctStaRptSensorEntry 2 }

hpnicfWIPSDctStaRptRSSI OBJECT-TYPE
    SYNTAX Integer32
    MAX-ACCESS read-only
    STATUS current
    DESCRIPTION
        "Represents the current value of signal strength that WIPS sensor
        AP received from the station."
    ::= { hpnicfWIPSDctStaRptSensorEntry 3 }

hpnicfWIPSDctStaLastRptTm OBJECT-TYPE
    SYNTAX TimeTicks
    MAX-ACCESS read-only
    STATUS current
    DESCRIPTION
        "Represents the time that station was detected by this sensor
        for the last time since system is up."
    ::= { hpnicfWIPSDctStaRptSensorEntry 4 }

hpnicfWIPSDctSSIDTable OBJECT-TYPE
    SYNTAX SEQUENCE OF HpnicfWIPSDctSSIDEntry
    MAX-ACCESS not-accessible
    STATUS current
    DESCRIPTION
        "The table represents the list of possible ESS information for
        networks detected by WIPS."
    ::= { hpnicfWIPSDetectGroup 6 }

hpnicfWIPSDctSSIDEntry OBJECT-TYPE
    SYNTAX HpnicfWIPSDctSSIDEntry
    MAX-ACCESS not-accessible
    STATUS current
    DESCRIPTION
        "Each entry contains possible ESS information of each ESS detected
        by WIPS."
    INDEX { hpnicfWIPSDctNetworkVSD, hpnicfWIPSDctNetworkSSID,
            hpnicfWIPSDctNetworkCfg }
    ::= { hpnicfWIPSDctSSIDTable 1 }

HpnicfWIPSDctSSIDEntry ::=
    SEQUENCE {
        hpnicfWIPSDctNetworkVSD
            OCTET STRING,
        hpnicfWIPSDctNetworkSSID
            OCTET STRING,
        hpnicfWIPSDctNetworkCfg
            Unsigned32,
        hpnicfWIPSDctNetworkFirstRptTm
            TimeTicks,
        hpnicfWIPSDctNetworkLastRptTm
            TimeTicks,
        hpnicfWIPSDctNetworkStatus
            HpnicfWIPSDevStatus,
        hpnicfWIPSDctNetworkSSIDHide
            TruthValue,
        hpnicfWIPSDctNetworkBSSNum
            Integer32
     }

hpnicfWIPSDctNetworkVSD OBJECT-TYPE
    SYNTAX OCTET STRING (SIZE (1..32))
    MAX-ACCESS not-accessible
    STATUS current
    DESCRIPTION
        "Represents the virtual security domain in which the ESS was detected."
    ::= { hpnicfWIPSDctSSIDEntry 1 }

hpnicfWIPSDctNetworkSSID OBJECT-TYPE
    SYNTAX OCTET STRING (SIZE (1..32))
    MAX-ACCESS not-accessible
    STATUS current
    DESCRIPTION
        "Represents the service set identifier for the ESS.
         Using the ASCII value '1' represents that the SSID is not advertised
         in the beacon frames."
    ::= { hpnicfWIPSDctSSIDEntry 2 }

hpnicfWIPSDctNetworkCfg OBJECT-TYPE
    SYNTAX Unsigned32
    MAX-ACCESS not-accessible
    STATUS current
    DESCRIPTION
        "Represents the encrypt method, security suite and authentication method
        which are used by the detected ESS.
        The lowest 8 bits mean encrypt method. The higher 8 bits mean security suite.
        The third 8 bits stand for authentication method. The higerest 8 bits
        are reserved. The meaning is shown as follows:
        31              23              15              7             0
        + + + + + + + + + + + + + + + + + + + + + + + + + + + + + + + +
        |  reserved     |  auth method  | security suite|encryptmethod|
        + + + + + + + + + + + + + + + + + + + + + + + + + + + + + + + +
        For encrypt method, the following values are supported:
        1: none     - clear text or no cipher method is configure,
        2: wep      - WEP key,
        4: tkip     - WPA Temporal Key encryption,
        8: ccmp     - WPA AES CCMP encryption
        For security suite, the following values are supported:
        0x01: clear
        0x02: wpa2
        0x04: wpa
        0x08: wep
        For authentication method, the following values are supported:
        1:  none     - No key management mode configured,
        2:  psk      - pre-shared key authentication,
        3:  dot1x    - 802.1x authentication.
        4:  other    - other authentication"
    ::= { hpnicfWIPSDctSSIDEntry 3 }

hpnicfWIPSDctNetworkFirstRptTm OBJECT-TYPE
    SYNTAX TimeTicks
    MAX-ACCESS read-only
    STATUS current
    DESCRIPTION
        "Represents the time that ESS was detected for the first time
        since system is up."
    ::= { hpnicfWIPSDctSSIDEntry 4 }

hpnicfWIPSDctNetworkLastRptTm OBJECT-TYPE
    SYNTAX TimeTicks
    MAX-ACCESS read-only
    STATUS current
    DESCRIPTION
        "Represents the time that ESS was detected for the last time
        since system is up."
    ::= { hpnicfWIPSDctSSIDEntry 5 }

hpnicfWIPSDctNetworkStatus OBJECT-TYPE
    SYNTAX HpnicfWIPSDevStatus
    MAX-ACCESS read-only
    STATUS current
    DESCRIPTION
        "Represents the status of this ESS detected by WIPS."
    ::= { hpnicfWIPSDctSSIDEntry 6 }

hpnicfWIPSDctNetworkSSIDHide OBJECT-TYPE
    SYNTAX TruthValue
    MAX-ACCESS read-only
    STATUS current
    DESCRIPTION
        "Represents whether the ESS broadcasted its SSID."
    DEFVAL { false }
    ::= { hpnicfWIPSDctSSIDEntry 7 }

hpnicfWIPSDctNetworkBSSNum OBJECT-TYPE
    SYNTAX Integer32
    MAX-ACCESS read-only
    STATUS current
    DESCRIPTION
        "Represents the number of APs using the same SSID in the ESS."
    ::= { hpnicfWIPSDctSSIDEntry 8 }

hpnicfWIPSDctSSIDBSSTable OBJECT-TYPE
    SYNTAX SEQUENCE OF HpnicfWIPSDctSSIDBSSEntry
    MAX-ACCESS not-accessible
    STATUS current
    DESCRIPTION
        "The table represents the list of APs using the same SSID in the ESS."
    ::= { hpnicfWIPSDetectGroup 7 }

hpnicfWIPSDctSSIDBSSEntry OBJECT-TYPE
    SYNTAX HpnicfWIPSDctSSIDBSSEntry
    MAX-ACCESS not-accessible
    STATUS current
    DESCRIPTION
        "Each entry contains possible BSS information of each AP detected
        by WIPS."
    INDEX { hpnicfWIPSDctNetworkVSD, hpnicfWIPSDctNetworkSSID,
            hpnicfWIPSDctNetworkCfg, hpnicfWIPSDctNetworkBSSID }
    ::= { hpnicfWIPSDctSSIDBSSTable 1 }

HpnicfWIPSDctSSIDBSSEntry ::=
    SEQUENCE {
        hpnicfWIPSDctNetworkBSSID
            MacAddress,
        hpnicfWIPSDctNetworkBSSWorkChl
            HpnicfWIPSChannel,
        hpnicfWIPSDctNetworkBSSStaNum
            Integer32
     }

hpnicfWIPSDctNetworkBSSID OBJECT-TYPE
    SYNTAX MacAddress
    MAX-ACCESS not-accessible
    STATUS current
    DESCRIPTION
        "Represents the Basic Service Set."
    ::= { hpnicfWIPSDctSSIDBSSEntry 1 }

hpnicfWIPSDctNetworkBSSWorkChl OBJECT-TYPE
    SYNTAX HpnicfWIPSChannel
    MAX-ACCESS read-only
    STATUS current
    DESCRIPTION
        "Represents on which radio channel that WIPS sensor AP detected
        the BSS."
    ::= { hpnicfWIPSDctSSIDBSSEntry 2 }

hpnicfWIPSDctNetworkBSSStaNum OBJECT-TYPE
    SYNTAX Integer32
    MAX-ACCESS read-only
    STATUS current
    DESCRIPTION
        "Represents the number of clients associated with the detected BSS."
    ::= { hpnicfWIPSDctSSIDBSSEntry 3 }

hpnicfWIPSBlockListTable OBJECT-TYPE
    SYNTAX SEQUENCE OF HpnicfWIPSBlockListEntry
    MAX-ACCESS not-accessible
    STATUS current
    DESCRIPTION
        "The table represents the list of block device MAC address."
    ::= { hpnicfWIPSDetectGroup 8 }

hpnicfWIPSBlockListEntry OBJECT-TYPE
    SYNTAX HpnicfWIPSBlockListEntry
    MAX-ACCESS not-accessible
    STATUS current
    DESCRIPTION
        "Each entry contains block device MAC address information."
    INDEX { hpnicfWIPSBlockListMacAddress }
    ::= { hpnicfWIPSBlockListTable 1 }

HpnicfWIPSBlockListEntry ::=
    SEQUENCE {
        hpnicfWIPSBlockListMacAddress
            MacAddress,
        hpnicfWIPSBlockListStatus
            INTEGER
    }

hpnicfWIPSBlockListMacAddress OBJECT-TYPE
    SYNTAX MacAddress
    MAX-ACCESS not-accessible
    STATUS current
    DESCRIPTION
        "Represents the MAC address of block device."
    ::= { hpnicfWIPSBlockListEntry 1 }

hpnicfWIPSBlockListStatus OBJECT-TYPE
    SYNTAX INTEGER
    {
    static(1),
    dynamic(2),
    staticAndDynamic(3)
    }
    MAX-ACCESS read-only
    STATUS current
    DESCRIPTION
        "Represents the status of block device."
    ::= { hpnicfWIPSBlockListEntry 2 }

hpnicfWIPSChannelTable OBJECT-TYPE
    SYNTAX SEQUENCE OF HpnicfWIPSChannelEntry
    MAX-ACCESS not-accessible
    STATUS current
    DESCRIPTION
        "The table represents the list of channel information."
    ::= { hpnicfWIPSDetectGroup 9 }

hpnicfWIPSChannelEntry OBJECT-TYPE
    SYNTAX HpnicfWIPSChannelEntry
    MAX-ACCESS not-accessible
    STATUS current
    DESCRIPTION
        "Each entry contains channel information."
    INDEX { hpnicfWIPSChannelNum }
    ::= { hpnicfWIPSChannelTable 1 }

HpnicfWIPSChannelEntry ::=
    SEQUENCE {
        hpnicfWIPSChannelNum
            HpnicfWIPSChannel,
        hpnicfWIPSChannelRadioType
            HpnicfWIPSRadioType,
        hpnicfWIPSChannelIsPermitted
            TruthValue,
        hpnicfWIPSChannelLastRptTm
            TimeTicks
    }

hpnicfWIPSChannelNum OBJECT-TYPE
    SYNTAX HpnicfWIPSChannel
    MAX-ACCESS not-accessible
    STATUS current
    DESCRIPTION
        "Represents the channel number."
    ::= { hpnicfWIPSChannelEntry 1 }

hpnicfWIPSChannelRadioType OBJECT-TYPE
    SYNTAX HpnicfWIPSRadioType
    MAX-ACCESS read-only
    STATUS current
    DESCRIPTION
        "Represents the radio type used in the specific channel."
    ::= { hpnicfWIPSChannelEntry 2 }

hpnicfWIPSChannelIsPermitted OBJECT-TYPE
    SYNTAX TruthValue
    MAX-ACCESS read-only
    STATUS current
    DESCRIPTION
        "Represents whether the channel is permitted."
    ::= { hpnicfWIPSChannelEntry 3 }

hpnicfWIPSChannelLastRptTm OBJECT-TYPE
    SYNTAX TimeTicks
    MAX-ACCESS read-only
    STATUS current
    DESCRIPTION
        "Represents the latest time that detecting the channel is active."
    ::= { hpnicfWIPSChannelEntry 4 }

hpnicfWIPSCountermeasureListTable OBJECT-TYPE
    SYNTAX SEQUENCE OF HpnicfWIPSCountermeasureListEntry
    MAX-ACCESS not-accessible
    STATUS current
    DESCRIPTION
        "The table represents the list of global static countermeasure device information."
    ::= { hpnicfWIPSDetectGroup 10 }

hpnicfWIPSCountermeasureListEntry OBJECT-TYPE
    SYNTAX HpnicfWIPSCountermeasureListEntry
    MAX-ACCESS not-accessible
    STATUS current
    DESCRIPTION
        "Each entry contains countermeasure device information."
    INDEX { hpnicfWIPSCtmListMacAddress }
    ::= { hpnicfWIPSCountermeasureListTable 1 }

HpnicfWIPSCountermeasureListEntry ::=
    SEQUENCE {
        hpnicfWIPSCtmListMacAddress
            MacAddress,
        hpnicfWIPSCtmListLastestWorkChl
            HpnicfWIPSChannel,
        hpnicfWIPSCtmListFirstTm
            TimeTicks,
        hpnicfWIPSCtmListLastTm
            TimeTicks,
        hpnicfWIPSCtmListQurCnt
            Integer32,
        hpnicfWIPSCtmListSensorNum
            Integer32
    }

hpnicfWIPSCtmListMacAddress OBJECT-TYPE
    SYNTAX MacAddress
    MAX-ACCESS not-accessible
    STATUS current
    DESCRIPTION
        "Represents the MAC address of the countered device."
    ::= { hpnicfWIPSCountermeasureListEntry 1 }

hpnicfWIPSCtmListLastestWorkChl OBJECT-TYPE
    SYNTAX HpnicfWIPSChannel
    MAX-ACCESS read-only
    STATUS current
    DESCRIPTION
        "Represents the channel on which the countermeasure device was working."
    ::= { hpnicfWIPSCountermeasureListEntry 2 }

hpnicfWIPSCtmListFirstTm OBJECT-TYPE
    SYNTAX TimeTicks
    MAX-ACCESS read-only
    STATUS current
    DESCRIPTION
        "Represents the first time that the device was countered
        since system is up."
    ::= { hpnicfWIPSCountermeasureListEntry 3 }

hpnicfWIPSCtmListLastTm OBJECT-TYPE
    SYNTAX TimeTicks
    MAX-ACCESS read-only
    STATUS current
    DESCRIPTION
        "Represents the last time that the device was countered
        since system is up."
    ::= { hpnicfWIPSCountermeasureListEntry 4 }

hpnicfWIPSCtmListQurCnt OBJECT-TYPE
    SYNTAX Integer32
    MAX-ACCESS read-only
    STATUS current
    DESCRIPTION
        "Represents how many times that the device was countered. "
    ::= { hpnicfWIPSCountermeasureListEntry 5 }

hpnicfWIPSCtmListSensorNum OBJECT-TYPE
    SYNTAX Integer32
    MAX-ACCESS read-only
    STATUS current
    DESCRIPTION
        "Represents the number of sensors detecting the device."
    ::= { hpnicfWIPSCountermeasureListEntry 6 }

hpnicfWIPSIgnoreListTable OBJECT-TYPE
    SYNTAX SEQUENCE OF HpnicfWIPSIgnoreListEntry
    MAX-ACCESS not-accessible
    STATUS current
    DESCRIPTION
        "The table represents the list of ignored device information."
    ::= { hpnicfWIPSDetectGroup 11 }

hpnicfWIPSIgnoreListEntry OBJECT-TYPE
    SYNTAX HpnicfWIPSIgnoreListEntry
    MAX-ACCESS not-accessible
    STATUS current
    DESCRIPTION
        "Each entry contains ignored device information."
    INDEX { hpnicfWIPSIgnoreListMacAddress }
    ::= { hpnicfWIPSIgnoreListTable 1 }

HpnicfWIPSIgnoreListEntry ::=
    SEQUENCE {
        hpnicfWIPSIgnoreListMacAddress
            MacAddress,
        hpnicfWIPSIgnoreListFirstIgnoreTm
            TimeTicks,
        hpnicfWIPSIgnoreListLastIgnoreTm
            TimeTicks,
        hpnicfWIPSIgnoreListIgnoreCnt
            Integer32
     }

hpnicfWIPSIgnoreListMacAddress OBJECT-TYPE
    SYNTAX MacAddress
    MAX-ACCESS not-accessible
    STATUS current
    DESCRIPTION
        "Represents the MAC address of the ignored device."
    ::= { hpnicfWIPSIgnoreListEntry 1 }

hpnicfWIPSIgnoreListFirstIgnoreTm OBJECT-TYPE
    SYNTAX TimeTicks
    MAX-ACCESS read-only
    STATUS current
    DESCRIPTION
        "Represents the first time when the event caused
        by the device was ignored since system is up."
    ::= { hpnicfWIPSIgnoreListEntry 2 }

hpnicfWIPSIgnoreListLastIgnoreTm OBJECT-TYPE
    SYNTAX TimeTicks
    MAX-ACCESS read-only
    STATUS current
    DESCRIPTION
        "Represents the last time when the event caused
        by the device was ignored since system is up."
    ::= { hpnicfWIPSIgnoreListEntry 3 }

hpnicfWIPSIgnoreListIgnoreCnt OBJECT-TYPE
    SYNTAX Integer32
    MAX-ACCESS read-only
    STATUS current
    DESCRIPTION
        "Represents the number of times of the event caused by device has been ignored."
    ::= { hpnicfWIPSIgnoreListEntry 4 }

hpnicfWIPSTrustListTable OBJECT-TYPE
    SYNTAX SEQUENCE OF HpnicfWIPSTrustListEntry
    MAX-ACCESS not-accessible
    STATUS current
    DESCRIPTION
        "The table represents the list of trust device information."
    ::= { hpnicfWIPSDetectGroup 12 }

hpnicfWIPSTrustListEntry OBJECT-TYPE
    SYNTAX HpnicfWIPSTrustListEntry
    MAX-ACCESS not-accessible
    STATUS current
    DESCRIPTION
        "Each entry contains information of a trust device."
    INDEX { hpnicfWIPSTrustListMacAddress }
    ::= { hpnicfWIPSTrustListTable 1 }

HpnicfWIPSTrustListEntry ::=
    SEQUENCE {
        hpnicfWIPSTrustListMacAddress
            MacAddress,
        hpnicfWIPSTrustListStatus
            INTEGER
     }

hpnicfWIPSTrustListMacAddress OBJECT-TYPE
    SYNTAX MacAddress
    MAX-ACCESS not-accessible
    STATUS current
    DESCRIPTION
        "Represents the MAC address of the trust device."
    ::= { hpnicfWIPSTrustListEntry 1 }

hpnicfWIPSTrustListStatus OBJECT-TYPE
    SYNTAX INTEGER
        {
        static(1),
        dynamic(2),
        staticAndDynamic(3)
        }
    MAX-ACCESS read-only
    STATUS current
    DESCRIPTION
        "Represents the status of the trust device."
    ::= { hpnicfWIPSTrustListEntry 2 }

hpnicfWIPSChlStatTable OBJECT-TYPE
    SYNTAX SEQUENCE OF HpnicfWIPSChlStatEntry
    MAX-ACCESS not-accessible
    STATUS current
    DESCRIPTION
        "The table represents the list of channel statistics information."
    ::= { hpnicfWIPSDetectGroup 13 }

hpnicfWIPSChlStatEntry OBJECT-TYPE
    SYNTAX HpnicfWIPSChlStatEntry
    MAX-ACCESS not-accessible
    STATUS current
    DESCRIPTION
        "Each entry contains information of channel statistics."
    INDEX { hpnicfWIPSChlStatSensorMacAddr, hpnicfWIPSChlStatChannel }
    ::= { hpnicfWIPSChlStatTable 1 }

HpnicfWIPSChlStatEntry ::=
    SEQUENCE {
        hpnicfWIPSChlStatSensorMacAddr
            MacAddress,
        hpnicfWIPSChlStatChannel
            HpnicfWIPSChannel,
        hpnicfWIPSChlStatTotalPkt
            Counter64,
        hpnicfWIPSChlStatTotalByte
            Counter64,
        hpnicfWIPSChlStatBmcastPkt
            Counter64,
        hpnicfWIPSChlStatBmcastByte
            Counter64,
        hpnicfWIPSChlStatUnicastPkt
            Counter64,
        hpnicfWIPSChlStatUnicastByte
            Counter64,
        hpnicfWIPSChlStatManagement
            Counter64,
        hpnicfWIPSChlStatControl
            Counter64,
        hpnicfWIPSChlStatData
            Counter64,
        hpnicfWIPSChlStatBeacon
            Counter64,
        hpnicfWIPSChlStatRTS
            Counter64,
        hpnicfWIPSChlStatCTS
            Counter64,
        hpnicfWIPSChlStatProbeRequest
            Counter64,
        hpnicfWIPSChlStatProbeResponse
            Counter64,
        hpnicfWIPSChlStatFragment
            Counter64,
        hpnicfWIPSChlStatRetry
            Counter64,
        hpnicfWIPSChlStatEapSuccess
            Counter64,
        hpnicfWIPSChlStatEapFailure
            Counter64,
        hpnicfWIPSChlStatEapolStart
            Counter64,
        hpnicfWIPSChlStatEapolLogoff
            Counter64,
        hpnicfWIPSChlStatAssocRequest
            Counter64,
        hpnicfWIPSChlStatAssocResponse
            Counter64,
        hpnicfWIPSChlStatUnicastDisassoc
            Counter64,
        hpnicfWIPSChlStatBroadcastDisassoc
            Counter64,
        hpnicfWIPSChlStatAuthentication
            Counter64,
        hpnicfWIPSChlStatUnicastDeauthen
            Counter64,
        hpnicfWIPSChlStatBroadcastDeauthen
            Counter64,
        hpnicfWIPSChlStatMalformed
            Counter64
     }

hpnicfWIPSChlStatSensorMacAddr OBJECT-TYPE
    SYNTAX MacAddress
    MAX-ACCESS not-accessible
    STATUS current
    DESCRIPTION
        "Represents the MAC address of sensor."
    ::= { hpnicfWIPSChlStatEntry 1 }

hpnicfWIPSChlStatChannel OBJECT-TYPE
    SYNTAX HpnicfWIPSChannel
    MAX-ACCESS not-accessible
    STATUS current
    DESCRIPTION
        "Represents the statistics channel."
    ::= { hpnicfWIPSChlStatEntry 2 }

hpnicfWIPSChlStatTotalPkt OBJECT-TYPE
    SYNTAX Counter64
    MAX-ACCESS read-only
    STATUS current
    DESCRIPTION
        "Represents the count of total frames in the channel."
    DEFVAL { 0 }
    ::= { hpnicfWIPSChlStatEntry 3 }

hpnicfWIPSChlStatTotalByte OBJECT-TYPE
    SYNTAX Counter64
    MAX-ACCESS read-only
    STATUS current
    DESCRIPTION
        "Represents the length of total frames in the channel."
    DEFVAL { 0 }
    ::= { hpnicfWIPSChlStatEntry 4 }

hpnicfWIPSChlStatBmcastPkt OBJECT-TYPE
    SYNTAX Counter64
    MAX-ACCESS read-only
    STATUS current
    DESCRIPTION
        "Represents the count of broadcast and multicast frames in the channel."
    DEFVAL { 0 }
    ::= { hpnicfWIPSChlStatEntry 5 }

hpnicfWIPSChlStatBmcastByte OBJECT-TYPE
    SYNTAX Counter64
    MAX-ACCESS read-only
    STATUS current
    DESCRIPTION
        "Represents the total length of broadcast and multicast frames
        in the channel."
    DEFVAL { 0 }
    ::= { hpnicfWIPSChlStatEntry 6 }

hpnicfWIPSChlStatUnicastPkt OBJECT-TYPE
    SYNTAX Counter64
    MAX-ACCESS read-only
    STATUS current
    DESCRIPTION
        "Represents the count of unicast frames in the channel."
    DEFVAL { 0 }
    ::= { hpnicfWIPSChlStatEntry 7 }

hpnicfWIPSChlStatUnicastByte OBJECT-TYPE
    SYNTAX Counter64
    MAX-ACCESS read-only
    STATUS current
    DESCRIPTION
        "Represents the total length of unicast frames in the channel."
    DEFVAL { 0 }
    ::= { hpnicfWIPSChlStatEntry 8 }

hpnicfWIPSChlStatManagement OBJECT-TYPE
    SYNTAX Counter64
    MAX-ACCESS read-only
    STATUS current
    DESCRIPTION
        "Represents the count of management frames in the channel."
    DEFVAL { 0 }
    ::= { hpnicfWIPSChlStatEntry 9 }

hpnicfWIPSChlStatControl OBJECT-TYPE
    SYNTAX Counter64
    MAX-ACCESS read-only
    STATUS current
    DESCRIPTION
        "Represents the count of control frames in the channel."
    DEFVAL { 0 }
    ::= { hpnicfWIPSChlStatEntry 10 }

hpnicfWIPSChlStatData OBJECT-TYPE
    SYNTAX Counter64
    MAX-ACCESS read-only
    STATUS current
    DESCRIPTION
        "Represents the count of data frames in the channel."
    DEFVAL { 0 }
    ::= { hpnicfWIPSChlStatEntry 11 }

hpnicfWIPSChlStatBeacon OBJECT-TYPE
    SYNTAX Counter64
    MAX-ACCESS read-only
    STATUS current
    DESCRIPTION
        "Represents the count of beacon frames in the channel."
    DEFVAL { 0 }
    ::= { hpnicfWIPSChlStatEntry 12 }

hpnicfWIPSChlStatRTS OBJECT-TYPE
    SYNTAX Counter64
    MAX-ACCESS read-only
    STATUS current
    DESCRIPTION
        "Represents the count of RTS frames in the channel."
    DEFVAL { 0 }
    ::= { hpnicfWIPSChlStatEntry 13 }

hpnicfWIPSChlStatCTS OBJECT-TYPE
    SYNTAX Counter64
    MAX-ACCESS read-only
    STATUS current
    DESCRIPTION
        "Represents the count of CTS frames in the channel."
    DEFVAL { 0 }
    ::= { hpnicfWIPSChlStatEntry 14 }

hpnicfWIPSChlStatProbeRequest OBJECT-TYPE
    SYNTAX Counter64
    MAX-ACCESS read-only
    STATUS current
    DESCRIPTION
        "Represents the count of probe request frames in the channel."
    DEFVAL { 0 }
    ::= { hpnicfWIPSChlStatEntry 15 }

hpnicfWIPSChlStatProbeResponse OBJECT-TYPE
    SYNTAX Counter64
    MAX-ACCESS read-only
    STATUS current
    DESCRIPTION
        "Represents the count of probe response frames in the channel."
    DEFVAL { 0 }
    ::= { hpnicfWIPSChlStatEntry 16 }

hpnicfWIPSChlStatFragment OBJECT-TYPE
    SYNTAX Counter64
    MAX-ACCESS read-only
    STATUS current
    DESCRIPTION
        "Represents the count of fragment frames in the channel."
    DEFVAL { 0 }
    ::= { hpnicfWIPSChlStatEntry 17 }

hpnicfWIPSChlStatRetry OBJECT-TYPE
    SYNTAX Counter64
    MAX-ACCESS read-only
    STATUS current
    DESCRIPTION
        "Represents the count of retry frames in the channel."
    DEFVAL { 0 }
    ::= { hpnicfWIPSChlStatEntry 18 }

hpnicfWIPSChlStatEapSuccess OBJECT-TYPE
    SYNTAX Counter64
    MAX-ACCESS read-only
    STATUS current
    DESCRIPTION
        "Represents the count of EAP-Success frames in the channel."
    DEFVAL { 0 }
    ::= { hpnicfWIPSChlStatEntry 19 }

hpnicfWIPSChlStatEapFailure OBJECT-TYPE
    SYNTAX Counter64
    MAX-ACCESS read-only
    STATUS current
    DESCRIPTION
        "Represents the count of EAP-Failure frames in the channel."
    DEFVAL { 0 }
    ::= { hpnicfWIPSChlStatEntry 20 }

hpnicfWIPSChlStatEapolStart OBJECT-TYPE
    SYNTAX Counter64
    MAX-ACCESS read-only
    STATUS current
    DESCRIPTION
        "Represents the count of EAPOL-Start frames in the channel."
    DEFVAL { 0 }
    ::= { hpnicfWIPSChlStatEntry 21 }

hpnicfWIPSChlStatEapolLogoff OBJECT-TYPE
    SYNTAX Counter64
    MAX-ACCESS read-only
    STATUS current
    DESCRIPTION
        "Represents the count of EAPOL-Logoff frames in the channel."
    DEFVAL { 0 }
    ::= { hpnicfWIPSChlStatEntry 22 }

hpnicfWIPSChlStatAssocRequest OBJECT-TYPE
    SYNTAX Counter64
    MAX-ACCESS read-only
    STATUS current
    DESCRIPTION
        "Represents the count of association request frames in the channel."
    DEFVAL { 0 }
    ::= { hpnicfWIPSChlStatEntry 23 }

hpnicfWIPSChlStatAssocResponse OBJECT-TYPE
    SYNTAX Counter64
    MAX-ACCESS read-only
    STATUS current
    DESCRIPTION
        "Represents the count of association response frames in the channel."
    DEFVAL { 0 }
    ::= { hpnicfWIPSChlStatEntry 24 }

hpnicfWIPSChlStatUnicastDisassoc OBJECT-TYPE
    SYNTAX Counter64
    MAX-ACCESS read-only
    STATUS current
    DESCRIPTION
        "Represents the count of unicast disassociation frames in the channel."
    DEFVAL { 0 }
    ::= { hpnicfWIPSChlStatEntry 25 }

hpnicfWIPSChlStatBroadcastDisassoc OBJECT-TYPE
    SYNTAX Counter64
    MAX-ACCESS read-only
    STATUS current
    DESCRIPTION
        "Represents the count of broadcast disassociation frames
        in the channel."
    DEFVAL { 0 }
    ::= { hpnicfWIPSChlStatEntry 26 }

hpnicfWIPSChlStatAuthentication OBJECT-TYPE
    SYNTAX Counter64
    MAX-ACCESS read-only
    STATUS current
    DESCRIPTION
        "Represents the count of authentication frames in the channel."
    DEFVAL { 0 }
    ::= { hpnicfWIPSChlStatEntry 27 }

hpnicfWIPSChlStatUnicastDeauthen OBJECT-TYPE
    SYNTAX Counter64
    MAX-ACCESS read-only
    STATUS current
    DESCRIPTION
        "Represents the count of unicast deauthentication frames
        in the channel."
    DEFVAL { 0 }
    ::= { hpnicfWIPSChlStatEntry 28 }

hpnicfWIPSChlStatBroadcastDeauthen OBJECT-TYPE
    SYNTAX Counter64
    MAX-ACCESS read-only
    STATUS current
    DESCRIPTION
        "Represents the count of broadcast deauthentication frames
        in the channel."
    DEFVAL { 0 }
    ::= { hpnicfWIPSChlStatEntry 29 }

hpnicfWIPSChlStatMalformed OBJECT-TYPE
    SYNTAX Counter64
    MAX-ACCESS read-only
    STATUS current
    DESCRIPTION
        "Represents the count of malformed frames in the channel."
    DEFVAL { 0 }
    ::= { hpnicfWIPSChlStatEntry 30 }

hpnicfWIPSDevStatTable OBJECT-TYPE
    SYNTAX SEQUENCE OF HpnicfWIPSDevStatEntry
    MAX-ACCESS not-accessible
    STATUS current
    DESCRIPTION
        "The table represents the list of device statistics information."
    ::= { hpnicfWIPSDetectGroup 14 }

hpnicfWIPSDevStatEntry OBJECT-TYPE
    SYNTAX HpnicfWIPSDevStatEntry
    MAX-ACCESS not-accessible
    STATUS current
    DESCRIPTION
        "Each entry contains information of device statistics."
    INDEX { hpnicfWIPSDevStatSensorMacAddr, hpnicfWIPSDevStatDevMacAddress, hpnicfWIPSDevStatChannel }
    ::= { hpnicfWIPSDevStatTable 1 }

HpnicfWIPSDevStatEntry ::=
    SEQUENCE {
        hpnicfWIPSDevStatSensorMacAddr
            MacAddress,
        hpnicfWIPSDevStatDevMacAddress
            MacAddress,
        hpnicfWIPSDevStatChannel
            HpnicfWIPSChannel,
        hpnicfWIPSDevStatTxTotalPkt
            Counter64,
        hpnicfWIPSDevStatTxTotalByte
            Counter64,
        hpnicfWIPSDevStatTxBMcastPkt
            Counter64,
        hpnicfWIPSDevStatTxBMcastByte
            Counter64,
        hpnicfWIPSDevStatTxUnicastPkt
            Counter64,
        hpnicfWIPSDevStatTxUnicastByte
            Counter64,
        hpnicfWIPSDevStatTxMgmt
            Counter64,
        hpnicfWIPSDevStatTxCtrl
            Counter64,
        hpnicfWIPSDevStatTxData
            Counter64,
        hpnicfWIPSDevStatTxBeacon
            Counter64,
        hpnicfWIPSDevStatTxRTS
            Counter64,
        hpnicfWIPSDevStatTxProbeRequest
            Counter64,
        hpnicfWIPSDevStatTxProbeResponse
            Counter64,
        hpnicfWIPSDevStatTxFragment
            Counter64,
        hpnicfWIPSDevStatTxRetry
            Counter64,
        hpnicfWIPSDevStatTxAssocRequest
            Counter64,
        hpnicfWIPSDevStatTxAssocResponse
            Counter64,
        hpnicfWIPSDevStatTxUnicastDisassoc
            Counter64,
        hpnicfWIPSDevStatTxBcastDisassoc
            Counter64,
        hpnicfWIPSDevStatTxAuth
            Counter64,
        hpnicfWIPSDevStatTxUnicastDeauth
            Counter64,
        hpnicfWIPSDevStatTxBcastDeauth
            Counter64,
        hpnicfWIPSDevStatTxEAPSuccess
            Counter64,
        hpnicfWIPSDevStatTxEAPFailure
            Counter64,
        hpnicfWIPSDevStatTxEAPOLStart
            Counter64,
        hpnicfWIPSDevStatTxEAPOLLogOff
            Counter64,
        hpnicfWIPSDevStatTxMalformed
            Counter64,
        hpnicfWIPSDevStatRxTotalPkt
            Counter64,
        hpnicfWIPSDevStatRxTotalByte
            Counter64,
        hpnicfWIPSDevStatRxUnicastPkt
            Counter64,
        hpnicfWIPSDevStatRxUnicastByte
            Counter64,
        hpnicfWIPSDevStatRxMgmt
            Counter64,
        hpnicfWIPSDevStatRxCtrl
            Counter64,
        hpnicfWIPSDevStatRxData
            Counter64,
        hpnicfWIPSDevStatRxRTS
            Counter64,
        hpnicfWIPSDevStatRxCTS
            Counter64,
        hpnicfWIPSDevStatRxProbeRequest
            Counter64,
        hpnicfWIPSDevStatRxProbeResponse
            Counter64,
        hpnicfWIPSDevStatRxFragment
            Counter64,
        hpnicfWIPSDevStatRxRetry
            Counter64,
        hpnicfWIPSDevStatRxAssoRequest
            Counter64,
        hpnicfWIPSDevStatRxAssoResponse
            Counter64,
        hpnicfWIPSDevStatRxDisassoc
            Counter64,
        hpnicfWIPSDevStatRxAuth
            Counter64,
        hpnicfWIPSDevStatRxDeauth
            Counter64,
        hpnicfWIPSDevStatRxEAPSuccess
            Counter64,
        hpnicfWIPSDevStatRxEAPFailure
            Counter64,
        hpnicfWIPSDevStatRxEAPOLStart
            Counter64,
        hpnicfWIPSDevStatRxEAPOLLogoff
            Counter64,
        hpnicfWIPSDevStatRxMalformed
            Counter64
     }

hpnicfWIPSDevStatSensorMacAddr OBJECT-TYPE
    SYNTAX MacAddress
    MAX-ACCESS not-accessible
    STATUS current
    DESCRIPTION
        "Represents the MAC address of sensor."
    ::= { hpnicfWIPSDevStatEntry 1 }

hpnicfWIPSDevStatDevMacAddress OBJECT-TYPE
    SYNTAX MacAddress
    MAX-ACCESS not-accessible
    STATUS current
    DESCRIPTION
        "Represents the MAC address of the device detected by the sensor."
    ::= { hpnicfWIPSDevStatEntry 2 }

hpnicfWIPSDevStatChannel OBJECT-TYPE
    SYNTAX HpnicfWIPSChannel
    MAX-ACCESS not-accessible
    STATUS current
    DESCRIPTION
        "Represents the device working channel."
    ::= { hpnicfWIPSDevStatEntry 3 }

hpnicfWIPSDevStatTxTotalPkt OBJECT-TYPE
    SYNTAX Counter64
    MAX-ACCESS read-only
    STATUS current
    DESCRIPTION
        "Represents the count of total frames transmitted by the device
        in one channel."
    DEFVAL { 0 }
    ::= { hpnicfWIPSDevStatEntry 4 }

hpnicfWIPSDevStatTxTotalByte OBJECT-TYPE
    SYNTAX Counter64
    MAX-ACCESS read-only
    STATUS current
    DESCRIPTION
        "Represents the length of total frames transmitted by the device
        in one channel."
    DEFVAL { 0 }
    ::= { hpnicfWIPSDevStatEntry 5 }

hpnicfWIPSDevStatTxBMcastPkt OBJECT-TYPE
    SYNTAX Counter64
    MAX-ACCESS read-only
    STATUS current
    DESCRIPTION
        "Represents the count of broadcast and multicast frames transmitted by
        the device in one channel."
    DEFVAL { 0 }
    ::= { hpnicfWIPSDevStatEntry 6 }

hpnicfWIPSDevStatTxBMcastByte OBJECT-TYPE
    SYNTAX Counter64
    MAX-ACCESS read-only
    STATUS current
    DESCRIPTION
        "Represents the length of broadcast and multicast frames transmitted by
        the device in one channel."
    DEFVAL { 0 }
    ::= { hpnicfWIPSDevStatEntry 7 }

hpnicfWIPSDevStatTxUnicastPkt OBJECT-TYPE
    SYNTAX Counter64
    MAX-ACCESS read-only
    STATUS current
    DESCRIPTION
        "Represents the count of unicast frames transmitted by the device
        in one channel."
    DEFVAL { 0 }
    ::= { hpnicfWIPSDevStatEntry 8 }

hpnicfWIPSDevStatTxUnicastByte OBJECT-TYPE
    SYNTAX Counter64
    MAX-ACCESS read-only
    STATUS current
    DESCRIPTION
        "Represents the length of unicast frames transmitted by the device
        in one channel."
    DEFVAL { 0 }
    ::= { hpnicfWIPSDevStatEntry 9 }

hpnicfWIPSDevStatTxMgmt OBJECT-TYPE
    SYNTAX Counter64
    MAX-ACCESS read-only
    STATUS current
    DESCRIPTION
        "Represents the count of management frames transmitted by the device
        in one channel."
    DEFVAL { 0 }
    ::= { hpnicfWIPSDevStatEntry 10 }

hpnicfWIPSDevStatTxCtrl OBJECT-TYPE
    SYNTAX Counter64
    MAX-ACCESS read-only
    STATUS current
    DESCRIPTION
        "Represents the count of control frames transmitted by the device
        in one channel."
    DEFVAL { 0 }
    ::= { hpnicfWIPSDevStatEntry 11 }

hpnicfWIPSDevStatTxData OBJECT-TYPE
    SYNTAX Counter64
    MAX-ACCESS read-only
    STATUS current
    DESCRIPTION
        "Represents the count of data frames transmitted by the device
        in one channel."
    DEFVAL { 0 }
    ::= { hpnicfWIPSDevStatEntry 12 }

hpnicfWIPSDevStatTxBeacon OBJECT-TYPE
    SYNTAX Counter64
    MAX-ACCESS read-only
    STATUS current
    DESCRIPTION
        "Represents the count of beacon frames transmitted by the device
        in one channel."
    DEFVAL { 0 }
    ::= { hpnicfWIPSDevStatEntry 13 }

hpnicfWIPSDevStatTxRTS OBJECT-TYPE
    SYNTAX Counter64
    MAX-ACCESS read-only
    STATUS current
    DESCRIPTION
        "Represents the count of RTS frames transmitted by the device
        in one channel."
    DEFVAL { 0 }
    ::= { hpnicfWIPSDevStatEntry 14 }

hpnicfWIPSDevStatTxProbeRequest OBJECT-TYPE
    SYNTAX Counter64
    MAX-ACCESS read-only
    STATUS current
    DESCRIPTION
        "Represents the count of probe request frames transmitted by the device
        in one channel."
    DEFVAL { 0 }
    ::= { hpnicfWIPSDevStatEntry 15 }

hpnicfWIPSDevStatTxProbeResponse OBJECT-TYPE
    SYNTAX Counter64
    MAX-ACCESS read-only
    STATUS current
    DESCRIPTION
        "Represents the count of probe response frames transmitted by the device
        in one channel."
    DEFVAL { 0 }
    ::= { hpnicfWIPSDevStatEntry 16 }

hpnicfWIPSDevStatTxFragment OBJECT-TYPE
    SYNTAX Counter64
    MAX-ACCESS read-only
    STATUS current
    DESCRIPTION
        "Represents the count of fragment frames transmitted by the device
        in one channel."
    DEFVAL { 0 }
    ::= { hpnicfWIPSDevStatEntry 17 }

hpnicfWIPSDevStatTxRetry OBJECT-TYPE
    SYNTAX Counter64
    MAX-ACCESS read-only
    STATUS current
    DESCRIPTION
        "Represents the count of retry frames transmitted by the device
        in one channel."
    DEFVAL { 0 }
    ::= { hpnicfWIPSDevStatEntry 18 }

hpnicfWIPSDevStatTxAssocRequest OBJECT-TYPE
    SYNTAX Counter64
    MAX-ACCESS read-only
    STATUS current
    DESCRIPTION
        "Represents the count of association request frames transmitted
        by the device in one channel."
    DEFVAL { 0 }
    ::= { hpnicfWIPSDevStatEntry 19 }

hpnicfWIPSDevStatTxAssocResponse OBJECT-TYPE
    SYNTAX Counter64
    MAX-ACCESS read-only
    STATUS current
    DESCRIPTION
        "Represents the count of association response frames transmitted
        by the device in one channel."
    DEFVAL { 0 }
    ::= { hpnicfWIPSDevStatEntry 20 }

hpnicfWIPSDevStatTxUnicastDisassoc OBJECT-TYPE
    SYNTAX Counter64
    MAX-ACCESS read-only
    STATUS current
    DESCRIPTION
        "Represents the count of unicast disassociation frames transmitted
        by the device in one channel."
    DEFVAL { 0 }
    ::= { hpnicfWIPSDevStatEntry 21 }

hpnicfWIPSDevStatTxBcastDisassoc OBJECT-TYPE
    SYNTAX Counter64
    MAX-ACCESS read-only
    STATUS current
    DESCRIPTION
        "Represents the count of broadcast disassociation frames transmitted
        by the device in one channel."
    DEFVAL { 0 }
    ::= { hpnicfWIPSDevStatEntry 22 }

hpnicfWIPSDevStatTxAuth OBJECT-TYPE
    SYNTAX Counter64
    MAX-ACCESS read-only
    STATUS current
    DESCRIPTION
        "Represents the count of authentication frames transmitted by the device
        in one channel."
    DEFVAL { 0 }
    ::= { hpnicfWIPSDevStatEntry 23 }

hpnicfWIPSDevStatTxUnicastDeauth OBJECT-TYPE
    SYNTAX Counter64
    MAX-ACCESS read-only
    STATUS current
    DESCRIPTION
        "Represents the count of unicast deauthentication frames transmitted
        by the device in one channel."
    DEFVAL { 0 }
    ::= { hpnicfWIPSDevStatEntry 24 }

hpnicfWIPSDevStatTxBcastDeauth OBJECT-TYPE
    SYNTAX Counter64
    MAX-ACCESS read-only
    STATUS current
    DESCRIPTION
        "Represents the count of broadcast deauthentication frames transmitted
        by the device in one channel."
    DEFVAL { 0 }
    ::= { hpnicfWIPSDevStatEntry 25 }

hpnicfWIPSDevStatTxEAPSuccess OBJECT-TYPE
    SYNTAX Counter64
    MAX-ACCESS read-only
    STATUS current
    DESCRIPTION
        "Represents the count of EAP-Success frames transmitted by the device
        in one channel."
    DEFVAL { 0 }
    ::= { hpnicfWIPSDevStatEntry 26 }

hpnicfWIPSDevStatTxEAPFailure OBJECT-TYPE
    SYNTAX Counter64
    MAX-ACCESS read-only
    STATUS current
    DESCRIPTION
        "Represents the count of EAP-Failure frames transmitted by the device
        in one channel."
    DEFVAL { 0 }
    ::= { hpnicfWIPSDevStatEntry 27 }

hpnicfWIPSDevStatTxEAPOLStart OBJECT-TYPE
    SYNTAX Counter64
    MAX-ACCESS read-only
    STATUS current
    DESCRIPTION
        "Represents the count of EAPOL-Start frames transmitted by the device
        in one channel."
    DEFVAL { 0 }
    ::= { hpnicfWIPSDevStatEntry 28 }

hpnicfWIPSDevStatTxEAPOLLogOff OBJECT-TYPE
    SYNTAX Counter64
    MAX-ACCESS read-only
    STATUS current
    DESCRIPTION
        "Represents the count of EAPOL-Logoff frames transmitted by the device
        in one channel."
    DEFVAL { 0 }
    ::= { hpnicfWIPSDevStatEntry 29 }

hpnicfWIPSDevStatTxMalformed OBJECT-TYPE
    SYNTAX Counter64
    MAX-ACCESS read-only
    STATUS current
    DESCRIPTION
        "Represents the count of malformed frames transmitted by the device
        in one channel."
    DEFVAL { 0 }
    ::= { hpnicfWIPSDevStatEntry 30 }

hpnicfWIPSDevStatRxTotalPkt OBJECT-TYPE
    SYNTAX Counter64
    MAX-ACCESS read-only
    STATUS current
    DESCRIPTION
        "Represents the count of total frames received by the device
        in one channel."
    DEFVAL { 0 }
    ::= { hpnicfWIPSDevStatEntry 31 }

hpnicfWIPSDevStatRxTotalByte OBJECT-TYPE
    SYNTAX Counter64
    MAX-ACCESS read-only
    STATUS current
    DESCRIPTION
        "Represents the length of total frames received by the device
        in one channel."
    DEFVAL { 0 }
    ::= { hpnicfWIPSDevStatEntry 32 }

hpnicfWIPSDevStatRxUnicastPkt OBJECT-TYPE
    SYNTAX Counter64
    MAX-ACCESS read-only
    STATUS current
    DESCRIPTION
        "Represents the count of unicast frames received by the device
        in one channel."
    DEFVAL { 0 }
    ::= { hpnicfWIPSDevStatEntry 33 }

hpnicfWIPSDevStatRxUnicastByte OBJECT-TYPE
    SYNTAX Counter64
    MAX-ACCESS read-only
    STATUS current
    DESCRIPTION
        "Represents the length of unicast frames received by the device
        in one channel."
    DEFVAL { 0 }
    ::= { hpnicfWIPSDevStatEntry 34 }

hpnicfWIPSDevStatRxMgmt OBJECT-TYPE
    SYNTAX Counter64
    MAX-ACCESS read-only
    STATUS current
    DESCRIPTION
        "Represents the count of management frames received by the device
        in one channel."
    DEFVAL { 0 }
    ::= { hpnicfWIPSDevStatEntry 35 }

hpnicfWIPSDevStatRxCtrl OBJECT-TYPE
    SYNTAX Counter64
    MAX-ACCESS read-only
    STATUS current
    DESCRIPTION
        "Represents the count of control frames received by the device
        in one channel."
    DEFVAL { 0 }
    ::= { hpnicfWIPSDevStatEntry 36 }

hpnicfWIPSDevStatRxData OBJECT-TYPE
    SYNTAX Counter64
    MAX-ACCESS read-only
    STATUS current
    DESCRIPTION
        "Represents the count of data frames received by the device
        in one channel."
    DEFVAL { 0 }
    ::= { hpnicfWIPSDevStatEntry 37 }

hpnicfWIPSDevStatRxRTS OBJECT-TYPE
    SYNTAX Counter64
    MAX-ACCESS read-only
    STATUS current
    DESCRIPTION
        "Represents the count of RTS frames recieved by the device
        in one channel."
    DEFVAL { 0 }
    ::= { hpnicfWIPSDevStatEntry 38 }

hpnicfWIPSDevStatRxCTS OBJECT-TYPE
    SYNTAX Counter64
    MAX-ACCESS read-only
    STATUS current
    DESCRIPTION
        "Represents the count of CTS frames recieved by the device
        in one channel."
    DEFVAL { 0 }
    ::= { hpnicfWIPSDevStatEntry 39 }

hpnicfWIPSDevStatRxProbeRequest OBJECT-TYPE
    SYNTAX Counter64
    MAX-ACCESS read-only
    STATUS current
    DESCRIPTION
        "Represents the count of probe request frames received by the device
        in one channel."
    DEFVAL { 0 }
    ::= { hpnicfWIPSDevStatEntry 40 }

hpnicfWIPSDevStatRxProbeResponse OBJECT-TYPE
    SYNTAX Counter64
    MAX-ACCESS read-only
    STATUS current
    DESCRIPTION
        "Represents the count of probe response frames received by the device
        in one channel."
    DEFVAL { 0 }
    ::= { hpnicfWIPSDevStatEntry 41 }

hpnicfWIPSDevStatRxFragment OBJECT-TYPE
    SYNTAX Counter64
    MAX-ACCESS read-only
    STATUS current
    DESCRIPTION
        "Represents the count of fragment frames received by the device
        in one channel."
    DEFVAL { 0 }
    ::= { hpnicfWIPSDevStatEntry 42 }

hpnicfWIPSDevStatRxRetry OBJECT-TYPE
    SYNTAX Counter64
    MAX-ACCESS read-only
    STATUS current
    DESCRIPTION
        "Represents the count of retry frames received by the device
        in one channel."
    DEFVAL { 0 }
    ::= { hpnicfWIPSDevStatEntry 43 }

hpnicfWIPSDevStatRxAssoRequest OBJECT-TYPE
    SYNTAX Counter64
    MAX-ACCESS read-only
    STATUS current
    DESCRIPTION
        "Represents the count of association request frames received
        by the device in one channel."
    DEFVAL { 0 }
    ::= { hpnicfWIPSDevStatEntry 44 }

hpnicfWIPSDevStatRxAssoResponse OBJECT-TYPE
    SYNTAX Counter64
    MAX-ACCESS read-only
    STATUS current
    DESCRIPTION
        "Represents the count of association response frames received
        by the device in one channel."
    DEFVAL { 0 }
    ::= { hpnicfWIPSDevStatEntry 45 }

hpnicfWIPSDevStatRxDisassoc OBJECT-TYPE
    SYNTAX Counter64
    MAX-ACCESS read-only
    STATUS current
    DESCRIPTION
        "Represents the count of disassociation frames received by the device
        in one channel."
    DEFVAL { 0 }
    ::= { hpnicfWIPSDevStatEntry 46 }

hpnicfWIPSDevStatRxAuth OBJECT-TYPE
    SYNTAX Counter64
    MAX-ACCESS read-only
    STATUS current
    DESCRIPTION
        "Represents the count of authentication frames received by the device
        in one channel."
    DEFVAL { 0 }
    ::= { hpnicfWIPSDevStatEntry 47 }

hpnicfWIPSDevStatRxDeauth OBJECT-TYPE
    SYNTAX Counter64
    MAX-ACCESS read-only
    STATUS current
    DESCRIPTION
        "Represents the count of deauthentication frames received by the device
        in one channel."
    DEFVAL { 0 }
    ::= { hpnicfWIPSDevStatEntry 48 }

hpnicfWIPSDevStatRxEAPSuccess OBJECT-TYPE
    SYNTAX Counter64
    MAX-ACCESS read-only
    STATUS current
    DESCRIPTION
        "Represents the count of EAP-Success frames received by the device
        in one channel."
    DEFVAL { 0 }
    ::= { hpnicfWIPSDevStatEntry 49 }

hpnicfWIPSDevStatRxEAPFailure OBJECT-TYPE
    SYNTAX Counter64
    MAX-ACCESS read-only
    STATUS current
    DESCRIPTION
        "Represents the count of EAP-Failure frames received by the device
        in one channel."
    DEFVAL { 0 }
    ::= { hpnicfWIPSDevStatEntry 50 }

hpnicfWIPSDevStatRxEAPOLStart OBJECT-TYPE
    SYNTAX Counter64
    MAX-ACCESS read-only
    STATUS current
    DESCRIPTION
        "Represents the count of EAPOL-Start frames received by the device
        in one channel."
    DEFVAL { 0 }
    ::= { hpnicfWIPSDevStatEntry 51 }

hpnicfWIPSDevStatRxEAPOLLogoff OBJECT-TYPE
    SYNTAX Counter64
    MAX-ACCESS read-only
    STATUS current
    DESCRIPTION
        "Represents the count of EAPOL-Logoff frames received by the device
        in one channel."
    DEFVAL { 0 }
    ::= { hpnicfWIPSDevStatEntry 52 }

hpnicfWIPSDevStatRxMalformed OBJECT-TYPE
    SYNTAX Counter64
    MAX-ACCESS read-only
    STATUS current
    DESCRIPTION
        "Represents the count of malformed frames received by the device
        in one channel."
    DEFVAL { 0 }
    ::= { hpnicfWIPSDevStatEntry 53 }

hpnicfWIPSCtmDeviceTable OBJECT-TYPE
    SYNTAX SEQUENCE OF HpnicfWIPSCtmDeviceEntry
    MAX-ACCESS not-accessible
    STATUS current
    DESCRIPTION
        "The table represents the list of device information
        in static and dynamic countermeasure list."
    ::= { hpnicfWIPSDetectGroup 15 }

hpnicfWIPSCtmDeviceEntry OBJECT-TYPE
    SYNTAX HpnicfWIPSCtmDeviceEntry
    MAX-ACCESS not-accessible
    STATUS current
    DESCRIPTION
        "Each entry contains information of countermeasure device."
    INDEX { hpnicfWIPSCtmDeviceVSD, hpnicfWIPSCtmDeviceMAC }
    ::= { hpnicfWIPSCtmDeviceTable 1 }

HpnicfWIPSCtmDeviceEntry ::=
    SEQUENCE {
        hpnicfWIPSCtmDeviceVSD
            OCTET STRING,
        hpnicfWIPSCtmDeviceMAC
            MacAddress,
        hpnicfWIPSCtmDeviceType
            INTEGER,
        hpnicfWIPSCtmDeviceState
            INTEGER,
        hpnicfWIPSCtmDeviceStartTime
            TimeTicks,
        hpnicfWIPSCtmDeviceCategory
            HpnicfWIPSDeviceCategoryType,
        hpnicfWIPSCtmDeviceChl
            Unsigned32,
        hpnicfWIPSCtmDevicePrecedence
            Integer32
     }

hpnicfWIPSCtmDeviceVSD OBJECT-TYPE
    SYNTAX OCTET STRING (SIZE (1..32))
    MAX-ACCESS not-accessible
    STATUS current
    DESCRIPTION
        "Represents the VSD which the device belongs to."
    ::= { hpnicfWIPSCtmDeviceEntry 1 }

hpnicfWIPSCtmDeviceMAC OBJECT-TYPE
    SYNTAX MacAddress
    MAX-ACCESS not-accessible
    STATUS current
    DESCRIPTION
        "Represents the MAC address of countermeasure device."
    ::= { hpnicfWIPSCtmDeviceEntry 2 }

hpnicfWIPSCtmDeviceType OBJECT-TYPE
    SYNTAX INTEGER
        {
        static(1),
        dynamic(2),
        staticAnddynamic(3)
        }
    MAX-ACCESS read-only
    STATUS current
    DESCRIPTION
        "Represents the type of countermeasure device."
    ::= { hpnicfWIPSCtmDeviceEntry 3 }

hpnicfWIPSCtmDeviceState OBJECT-TYPE
    SYNTAX INTEGER
        {
        none(0),
        idle(1),
        pending(2),
        action(3)
        }
    MAX-ACCESS read-only
    STATUS current
    DESCRIPTION
        "Represents the state of countermeasure device."
    ::= { hpnicfWIPSCtmDeviceEntry 4 }

hpnicfWIPSCtmDeviceStartTime OBJECT-TYPE
    SYNTAX TimeTicks
    MAX-ACCESS read-only
    STATUS current
    DESCRIPTION
        "Represents the time when start to counter on the device."
    ::= { hpnicfWIPSCtmDeviceEntry 5 }

hpnicfWIPSCtmDeviceCategory OBJECT-TYPE
    SYNTAX HpnicfWIPSDeviceCategoryType
    MAX-ACCESS read-only
    STATUS current
    DESCRIPTION
        "Represents the category of the device."
    ::= { hpnicfWIPSCtmDeviceEntry 6 }

hpnicfWIPSCtmDeviceChl OBJECT-TYPE
    SYNTAX Unsigned32
    MAX-ACCESS read-only
    STATUS current
    DESCRIPTION
        "Represents the channel on which the device is countered."
    ::= { hpnicfWIPSCtmDeviceEntry 7 }

hpnicfWIPSCtmDevicePrecedence OBJECT-TYPE
    SYNTAX Integer32 (0..10)
    MAX-ACCESS read-only
    STATUS current
    DESCRIPTION
        "Represents the precedence of the device."
    ::= { hpnicfWIPSCtmDeviceEntry 8 }

hpnicfWIPSMalPktStatTable OBJECT-TYPE
    SYNTAX SEQUENCE OF HpnicfWIPSMalPktStatEntry
    MAX-ACCESS not-accessible
    STATUS current
    DESCRIPTION
        "The table represents the list of malformed packet statistics information."
    ::= { hpnicfWIPSDetectGroup 16 }

hpnicfWIPSMalPktStatEntry OBJECT-TYPE
    SYNTAX HpnicfWIPSMalPktStatEntry
    MAX-ACCESS not-accessible
    STATUS current
    DESCRIPTION
        "Each entry contains information of malformed pakcet."
    INDEX { hpnicfWIPSMalPktStatSensorMAC }
    ::= { hpnicfWIPSMalPktStatTable 1 }

HpnicfWIPSMalPktStatEntry ::=
    SEQUENCE {
        hpnicfWIPSMalPktStatSensorMAC
            MacAddress,
        hpnicfWIPSMalPktStatInvalidIELength
            Counter64,
        hpnicfWIPSMalPktStatDuplicatedIE
            Counter64,
        hpnicfWIPSMalPktStatRedundantIE
            Counter64,
        hpnicfWIPSMalPktStatInvalidPktLength
            Counter64,
        hpnicfWIPSMalPktStatIllegalIBSSESS
            Counter64,
        hpnicfWIPSMalPktStatInvalidSourceAddr
            Counter64,
        hpnicfWIPSMalPktStatOverflowEAPOLKey
            Counter64,
        hpnicfWIPSMalPktStatMalAuth
            Counter64,
        hpnicfWIPSMalPktStatMalAssoReq
            Counter64,
        hpnicfWIPSMalPktStatMalHTIE
            Counter64,
        hpnicfWIPSMalPktStatLargeDuration
            Counter64,
        hpnicfWIPSMalPktStatNULLProbeRes
            Counter64,
        hpnicfWIPSMalPktStatInvalidDeAuthCode
            Counter64,
        hpnicfWIPSMalPktStatInvalidDisAssoCode
            Counter64,
        hpnicfWIPSMalPktStatOverflowSSID
            Counter64,
        hpnicfWIPSMalPktStatFatajack
            Counter64
     }

hpnicfWIPSMalPktStatSensorMAC OBJECT-TYPE
    SYNTAX MacAddress
    MAX-ACCESS not-accessible
    STATUS current
    DESCRIPTION
        "Represents the MAC address of sensor."
    ::= { hpnicfWIPSMalPktStatEntry 1 }

hpnicfWIPSMalPktStatInvalidIELength OBJECT-TYPE
    SYNTAX Counter64
    MAX-ACCESS read-only
    STATUS current
    DESCRIPTION
        "Represents the count of the invalid IE length
        malformed packets."
    DEFVAL { 0 }
    ::= { hpnicfWIPSMalPktStatEntry 2 }

hpnicfWIPSMalPktStatDuplicatedIE OBJECT-TYPE
    SYNTAX Counter64
    MAX-ACCESS read-only
    STATUS current
    DESCRIPTION
        "Represents the count of the duplicated IE
        malformed packets."
    DEFVAL { 0 }
    ::= { hpnicfWIPSMalPktStatEntry 3 }

hpnicfWIPSMalPktStatRedundantIE OBJECT-TYPE
    SYNTAX Counter64
    MAX-ACCESS read-only
    STATUS current
    DESCRIPTION
        "Represents the count of the redundant IE
        malformed packets."
    DEFVAL { 0 }
    ::= { hpnicfWIPSMalPktStatEntry 4 }

hpnicfWIPSMalPktStatInvalidPktLength OBJECT-TYPE
    SYNTAX Counter64
    MAX-ACCESS read-only
    STATUS current
    DESCRIPTION
        "Represents the count of the invalide packet length
        malformed packets."
    DEFVAL { 0 }
    ::= { hpnicfWIPSMalPktStatEntry 5 }

hpnicfWIPSMalPktStatIllegalIBSSESS OBJECT-TYPE
    SYNTAX Counter64
    MAX-ACCESS read-only
    STATUS current
    DESCRIPTION
        "Represents the count of the illegal bits of
        representing IBSS and ESS malformed packets."
    DEFVAL { 0 }
    ::= { hpnicfWIPSMalPktStatEntry 6 }

hpnicfWIPSMalPktStatInvalidSourceAddr OBJECT-TYPE
    SYNTAX Counter64
    MAX-ACCESS read-only
    STATUS current
    DESCRIPTION
        "Represents the count of  invalid source address combination
         malformed pakcets."
    DEFVAL { 0 }
    ::= { hpnicfWIPSMalPktStatEntry 7 }

hpnicfWIPSMalPktStatOverflowEAPOLKey OBJECT-TYPE
    SYNTAX Counter64
    MAX-ACCESS read-only
    STATUS current
    DESCRIPTION
        "Represents the count of the overflow EAPOL key
        malformed packets."
    DEFVAL { 0 }
    ::= { hpnicfWIPSMalPktStatEntry 8 }

hpnicfWIPSMalPktStatMalAuth OBJECT-TYPE
    SYNTAX Counter64
    MAX-ACCESS read-only
    STATUS current
    DESCRIPTION
        "Represents the count of the malformed authentication packets."
    DEFVAL { 0 }
    ::= { hpnicfWIPSMalPktStatEntry 9 }

hpnicfWIPSMalPktStatMalAssoReq OBJECT-TYPE
    SYNTAX Counter64
    MAX-ACCESS read-only
    STATUS current
    DESCRIPTION
        "Represents the count of the malformed association request packets."
    DEFVAL { 0 }
    ::= { hpnicfWIPSMalPktStatEntry 10 }

hpnicfWIPSMalPktStatMalHTIE OBJECT-TYPE
    SYNTAX Counter64
    MAX-ACCESS read-only
    STATUS current
    DESCRIPTION
        "Represents the count of the malformed
        High Throughput IE segment packets."
    DEFVAL { 0 }
    ::= { hpnicfWIPSMalPktStatEntry 11 }

hpnicfWIPSMalPktStatLargeDuration OBJECT-TYPE
    SYNTAX Counter64
    MAX-ACCESS read-only
    STATUS current
    DESCRIPTION
        "Represents the count of the malformed
        large duration packets."
    DEFVAL { 0 }
    ::= { hpnicfWIPSMalPktStatEntry 12 }

hpnicfWIPSMalPktStatNULLProbeRes OBJECT-TYPE
    SYNTAX Counter64
    MAX-ACCESS read-only
    STATUS current
    DESCRIPTION
        "Represents the count of the malformed
        null probe response packets."
    DEFVAL { 0 }
    ::= { hpnicfWIPSMalPktStatEntry 13 }

hpnicfWIPSMalPktStatInvalidDeAuthCode OBJECT-TYPE
    SYNTAX Counter64
    MAX-ACCESS read-only
    STATUS current
    DESCRIPTION
        "Represents the count of the malformed
        invalid deauthentication reason code packets."
    DEFVAL { 0 }
    ::= { hpnicfWIPSMalPktStatEntry 14 }

hpnicfWIPSMalPktStatInvalidDisAssoCode OBJECT-TYPE
    SYNTAX Counter64
    MAX-ACCESS read-only
    STATUS current
    DESCRIPTION
        "Represents the count of the malformed
        invalid disassociation reason code packets."
    DEFVAL { 0 }
    ::= { hpnicfWIPSMalPktStatEntry 15 }

hpnicfWIPSMalPktStatOverflowSSID OBJECT-TYPE
    SYNTAX Counter64
    MAX-ACCESS read-only
    STATUS current
    DESCRIPTION
        "Represents the count of the malformed
        SSID length overflow packets."
    DEFVAL { 0 }
    ::= { hpnicfWIPSMalPktStatEntry 16}

hpnicfWIPSMalPktStatFatajack OBJECT-TYPE
    SYNTAX Counter64
    MAX-ACCESS read-only
    STATUS current
    DESCRIPTION
        "Represents the count of FATA-Jack attack pakcets."
    DEFVAL { 0 }
    ::= { hpnicfWIPSMalPktStatEntry 17 }

hpnicfWIPSNotifyGroup OBJECT IDENTIFIER ::= { hpnicfWIPS 3 }

END
