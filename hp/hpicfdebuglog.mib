HP-ICF-DEBUGLOG-MIB DEFINITIONS ::= BEGIN

     IMPORTS
     hpicfDebugLog
                 FROM HP-ICF-OID
     Integer32, MODULE-IDENTITY, OBJECT-TYPE
                 FROM SNMPv2-SMI
     TEXTUAL-CONVENTION, DisplayString, TruthValue
                 FROM SNMPv2-TC
     MODULE-COMPLIANCE, OBJECT-GROUP
                 FROM SNMPv2-CONF;

     hpicfDebugLogMib MODULE-IDENTITY
           LAST-UPDATED "201707040000Z"  --   Jul 04, 2017
           ORGANIZATION "HP Networking"
           CONTACT-INFO "Hewlett Packard Company
                         8000 Foothills Blvd.
                         Roseville, CA 95747"
           DESCRIPTION "The Debug MIB allows to enable / disable debug
                        logging for all debug message types. This
                        HP application enables / disables
                        debug log messages."

           REVISION     "201707040000Z"  --  Jul 04, 2017
           DESCRIPTION  "Added hpicfDebugTimeStamp"

           REVISION     "201603180000Z"  --  Mar 18, 2016
           DESCRIPTION  "Changed description of hpicfDebugLogStatus
                        and hpicfDebugDestStatus"

           REVISION     "201602170000Z"  --  Feb 17, 2016
           DESCRIPTION  "Added hpicfDebugLogPersistent and
                        hpicfDebugDestPersistent"

           REVISION     "200909220000Z"  --  Sep 22, 2009
           DESCRIPTION  "Initial version of this MIB module."
     ::= { hpicfDebugLog 1 }

   -- -------------------------------------------------------------
   -- Textual Conventions
   -- -------------------------------------------------------------

     HpicfDebugDestType ::=  TEXTUAL-CONVENTION
     STATUS  current
     DESCRIPTION "This value specifies the destination for the debug
                  log messages as described below.
                  syslog  -  Send debug messages to syslog server.
                  buffer  -  Print debug messages to a buffer in memory.
                  The destination type will be 'none' by default. The
                  destination for debug logging can be set to Syslog-
                  Server/Debug Buffer or a combination of these."

     SYNTAX    INTEGER
           {
             none            (0),
             syslog          (1),
             buffer          (2)
           }

     HpicfDebugLogLevels ::=  TEXTUAL-CONVENTION
     STATUS  current
     DESCRIPTION "This textual convention enumerates the Log levels for
                  a debug message type such as SSH for debug logging."
     SYNTAX    INTEGER
           {
             quiet           (0),
             fatal           (1),
             error           (2),
             info            (3),
             verbose         (4),
             debug           (5),
             debug2          (6),
             debug3          (7)
           }
   -- -------------------------------------------------------------
   -- hpicfDebugLogMib - the main groups
   -- -------------------------------------------------------------

     hpicfDebugLogObjects     OBJECT IDENTIFIER ::= { hpicfDebugLogMib 1 }
     hpicfDebugLogConformance OBJECT IDENTIFIER ::= { hpicfDebugLogMib 2 }

   -- -------------------------------------------------------------
   -- debug log table
   -- -------------------------------------------------------------
     hpicfDebugLogControlTable OBJECT-TYPE
           SYNTAX      SEQUENCE OF HpicfDebugLogControlEntry
           MAX-ACCESS  not-accessible
           STATUS      current
           DESCRIPTION "This table contains one entry per debug message
                        type for debug logging configuration."
     ::= { hpicfDebugLogObjects 1 }

     hpicfDebugLogControlEntry OBJECT-TYPE
           SYNTAX      HpicfDebugLogControlEntry
           MAX-ACCESS  not-accessible
           STATUS      current
           DESCRIPTION "Debug logging configuration information for a
                        particular debug message type."
     INDEX       { hpicfDebugLogIndex }
     ::= { hpicfDebugLogControlTable 1 }

     HpicfDebugLogControlEntry ::=
           SEQUENCE {
              hpicfDebugLogIndex            Integer32,
              hpicfDebugLogDescr            DisplayString,
              hpicfDebugLogContainedIn      Integer32,
              hpicfDebugLogStatus           TruthValue,
              hpicfDebugLogPersistent       TruthValue
           }

     hpicfDebugLogIndex OBJECT-TYPE
           SYNTAX      Integer32 (1..2147483647)
           MAX-ACCESS  not-accessible
           STATUS      current
           DESCRIPTION "An unique number that identifies the debug
                        message type for debug logging."
     ::= { hpicfDebugLogControlEntry 1 }

     hpicfDebugLogDescr OBJECT-TYPE
           SYNTAX      DisplayString (SIZE (0..255))
           MAX-ACCESS  read-only
           STATUS      current
           DESCRIPTION "This object provides description for the debug
                        message type that can be enabled for
                        debug logging."
     ::= { hpicfDebugLogControlEntry 2 }

     hpicfDebugLogContainedIn OBJECT-TYPE
           SYNTAX      Integer32 (1..2147483647)
           MAX-ACCESS  read-only
           STATUS      current
           DESCRIPTION "The value of hpicfDebugLogIndex for the
                        debug message type which 'contains' this debug
                        message type. Note that the set of
                        'containment' relationships define a
                        strict hierarchy."
     ::= { hpicfDebugLogControlEntry 3 }

     hpicfDebugLogStatus OBJECT-TYPE
           SYNTAX      TruthValue
           MAX-ACCESS  read-write
           STATUS      current
           DESCRIPTION "This object enables or disables a specific debug
                        option. The object 'hpicfDebugLogDescr' can
                        be queried to see which instance corresponds
                        to which debug option.

                        Note that disabling an instance of this object also
                        disables the corresponding instance of the object
                        'hpicfDebugLogPersistent'."
           ::= { hpicfDebugLogControlEntry 4 }

     hpicfDebugLogPersistent OBJECT-TYPE
           SYNTAX      TruthValue
           MAX-ACCESS  read-write
           STATUS      current
           DESCRIPTION "This object determines the status of a
                        debug message type for persistent debug
                        logging."
     ::= { hpicfDebugLogControlEntry 5 }

   -- -------------------------------------------------------------
   -- debug log level scalar
   -- -------------------------------------------------------------

     hpicfDebugLogLevel OBJECT-TYPE
           SYNTAX      HpicfDebugLogLevels
           MAX-ACCESS  read-write
           STATUS      current
           DESCRIPTION "The log level value for debug message type such
                        as SSH.This scalar takes syslog severity values
                        'fatal|error|info|verbose|debug|debug2|debug3'.
                        "
           DEFVAL      { info }
       ::= { hpicfDebugLogObjects 2 }

   -- -------------------------------------------------------------
   -- debug destination table
   -- -------------------------------------------------------------

     hpicfDebugDestControlTable OBJECT-TYPE
           SYNTAX      SEQUENCE OF HpicfDebugDestControlEntry
           MAX-ACCESS  not-accessible
           STATUS      current
           DESCRIPTION "This table contains one entry per debug
                        destination type i.e. Syslog/Buffer."
     ::= { hpicfDebugLogObjects 3 }

     hpicfDebugDestControlEntry OBJECT-TYPE
           SYNTAX      HpicfDebugDestControlEntry
           MAX-ACCESS  not-accessible
           STATUS      current
           DESCRIPTION "Debug logging configuration information for a
                        particular debug destination type."
     INDEX       { hpicfDebugDestIndex }
     ::= { hpicfDebugDestControlTable 1 }

     HpicfDebugDestControlEntry ::=
           SEQUENCE {
              hpicfDebugDestIndex           HpicfDebugDestType,
              hpicfDebugDestStatus          TruthValue,
              hpicfDebugDestPersistent      TruthValue
           }

     hpicfDebugDestIndex OBJECT-TYPE
           SYNTAX      HpicfDebugDestType
           MAX-ACCESS  not-accessible
           STATUS      current
           DESCRIPTION "The index that uniquely identifies each debug
                        destination type for debug logging."
     ::= { hpicfDebugDestControlEntry 1 }

     hpicfDebugDestStatus OBJECT-TYPE
           SYNTAX      TruthValue
           MAX-ACCESS  read-write
           STATUS      current
           DESCRIPTION "This object determines the enable or disable status
                        of a particular debug destination type such as
                        Syslog Server or Buffer.

                        Note that disabling an instance of this object
                        also disables the corrsponding instance of
                        the object 'hpicfDebugDestPersistent'."
     ::= { hpicfDebugDestControlEntry 2 }

     hpicfDebugDestPersistent OBJECT-TYPE
           SYNTAX      TruthValue
           MAX-ACCESS  read-write
           STATUS      current
           DESCRIPTION "This object determines the status
                        of a particular debug destination type
                        for persistent configuration."
     ::= { hpicfDebugDestControlEntry 3 }

   -- -------------------------------------------------------------
   -- debug time stamp scalar
   -- -------------------------------------------------------------

     hpicfDebugTimeStamp OBJECT-TYPE
           SYNTAX      TruthValue
           MAX-ACCESS  read-write
           STATUS      current
           DESCRIPTION "This object is used to enable or disable system time to
                        be associated with the debug log message.
                        true  - enable system time to be associated with
                                the debug logs.
                        false - enable system Uptime to be associated with
                                the debug logs.
                        By default, system Uptime will be associated with
                        the debug logs."
           DEFVAL      { false }
       ::= { hpicfDebugLogObjects 4 }

   ----------------------------------------------------------------
   -- Conformance Information
   ----------------------------------------------------------------

     hpicfDebugLogCompliances OBJECT IDENTIFIER ::=
                                 { hpicfDebugLogConformance 1 }
     hpicfDebugLogGroups      OBJECT IDENTIFIER ::=
                                 { hpicfDebugLogConformance 2 }
     hpicfDebugDestGroups      OBJECT IDENTIFIER ::=
                                 { hpicfDebugLogConformance 3 }
     hpicfDebugTimeStampGroups      OBJECT IDENTIFIER ::=
                                 { hpicfDebugLogConformance 4 }

   -- -------------------------------------------------------------
   -- units of conformance
   -- -------------------------------------------------------------

     hpicfDebugLogGroup OBJECT-GROUP
           OBJECTS {
                     hpicfDebugLogDescr,
                     hpicfDebugLogContainedIn,
                     hpicfDebugLogStatus,
                     hpicfDebugLogLevel,
                     hpicfDebugLogPersistent
                   }
           STATUS  current
           DESCRIPTION "A collection of objects representing the
                        configuration parameters for debug logging."
     ::= { hpicfDebugLogGroups 1}

     hpicfDebugDestGroup OBJECT-GROUP
           OBJECTS {
                     hpicfDebugDestStatus,
                     hpicfDebugDestPersistent
                   }
           STATUS  current
           DESCRIPTION "A collection of objects representing the
                        configuration parameters for debug destination.
                       "
     ::= { hpicfDebugDestGroups 1}

     hpicfDebugTimeStampGroup OBJECT-GROUP
           OBJECTS {
                     hpicfDebugTimeStamp
                   }
           STATUS  current
           DESCRIPTION "An object representing the
                        configuration parameters for debug log time stamp.
                       "
     ::= { hpicfDebugTimeStampGroups 1}
   -- -------------------------------------------------------------
   -- compliance statements
   -- -------------------------------------------------------------

     hpicfDebugLogCompliance MODULE-COMPLIANCE
           STATUS  deprecated
           DESCRIPTION
           "The compliance statement for debug logging entities which
            implement the DEBUGLOG-MIB with support for writable
            objects. Such an implementation can be both monitored and
            configured via SNMP."
           MODULE -- this module
           MANDATORY-GROUPS {
                              hpicfDebugLogGroup,
                              hpicfDebugDestGroup
                            }

     ::= { hpicfDebugLogCompliances 1 }

     hpicfDebugLogCompliance1 MODULE-COMPLIANCE
           STATUS  current
           DESCRIPTION
           "The compliance statement for debug logging entities which
            implement the DEBUGLOG-MIB with support for writable
            objects. Such an implementation can be both monitored and
            configured via SNMP."
           MODULE -- this module
           MANDATORY-GROUPS {
                              hpicfDebugLogGroup,
                              hpicfDebugDestGroup,
                              hpicfDebugTimeStampGroup
                            }

     ::= { hpicfDebugLogCompliances 2 }
  END
