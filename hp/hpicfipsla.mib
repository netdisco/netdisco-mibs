--**MOD+***********************************************************************
--* Module:    hpicfIpSla.mib
--*
--* Copyright (C) 2016 Hewlett Packard Enterprise Development LP
--* All Rights Reserved.
--*
--* The contents of this software are proprietary and confidential
--* to the Hewlett Packard Enterprise Development LP.  No part of this
--* program may be photocopied, reproduced, or translated into another
--* programming language without prior written consent of the
--* Hewlett Packard Enterprise Development LP.
--*
--* Purpose: This file contains MIB definition of HPICF-IPSLA-MIB
--*
--**MOD-***********************************************************************

HPICF-IPSLA-MIB DEFINITIONS ::= BEGIN

   IMPORTS
      hpSwitch
         FROM HP-ICF-OID
      OBJECT-TYPE, MODULE-IDENTITY, Integer32,
      Unsigned32, NOTIFICATION-TYPE
         FROM SNMPv2-SMI
      MODULE-COMPLIANCE, OBJECT-GROUP, NOTIFICATION-GROUP
         FROM SNMPv2-CONF
      InterfaceIndexOrZero
         FROM IF-MIB
      RowStatus, DateAndTime
         FROM SNMPv2-TC
      InetAddressType,InetAddress, InetPortNumber
         FROM INET-ADDRESS-MIB;


   -- 1.3.6.1.4.1.11.2.14.11.5.1.57
   hpicfIpSla MODULE-IDENTITY
      LAST-UPDATED    "201611100000Z"  -- November 10, 2016 at 00:00 GMT
      ORGANIZATION    "HP Networking."
      CONTACT-INFO    "Hewlett Packard Enterprise Development LP.
                      8000 Foothills Blvd.
                      Roseville, CA 95747"
      DESCRIPTION    "This MIB module contains HP proprietary
                      objects for managing IP Service Level
                      Agreement (SLA)."

      REVISION       "201611100000Z"  -- November 10, 2016 at 00:00 GMT
      DESCRIPTION    "Changed the MIB description of PayloadSize"

      REVISION       "201610200000Z"  -- October 20, 2016 at 00:00 GMT
      DESCRIPTION    "Changed the MIB description"

      REVISION       "201610050000Z"  -- October 5, 2016 at 00:00 GMT
      DESCRIPTION    "Added MIB objects for UDP, TCP and ICMP show functions"

      REVISION       "201609290000Z"  -- September 29, 2016 at 00:00 GMT
      DESCRIPTION    "Added Threshold count object."

      REVISION       "201609150000Z"  -- September 15, 2016 at 00:00 GMT
      DESCRIPTION    "Added MIB objects for DNS and DHCP error counts."

      REVISION       "201607250000Z"  -- July 25, 2016 at 00:00 GMT
      DESCRIPTION    "Added Jitter and VoIP objects."

      REVISION       "201607070000Z"  -- July 7, 2016 at 00:00 GMT
      DESCRIPTION    "Added MIB object for status and next schedule value."

      REVISION       "201606200000Z"  -- June 20, 2016 at 00:00 GMT
      DESCRIPTION    "Added DNS and DHCP."

      REVISION       "201603140000Z" -- March 14, 2016 at 00:00 GMT
      DESCRIPTION    "Removed Added codec type and advantage factor."

      REVISION       "201602160000Z"  -- February 16, 2016 at 00:00 GMT
      DESCRIPTION    "Added codec type and advantage factor."

      REVISION       "201506010000Z"  -- June 1, 2015 at 00:00 GMT
      DESCRIPTION    "Initial revision."

      ::= { hpSwitch 127 }

-- -------------------------------------------------------------
-- Start of MIB Objects
-- -------------------------------------------------------------
hpicfIpSlaNotifications OBJECT IDENTIFIER ::= { hpicfIpSla 0 }
hpicfIpSlaObjects       OBJECT IDENTIFIER ::= { hpicfIpSla 1 }
hpicfIpSlaConformance   OBJECT IDENTIFIER ::= { hpicfIpSla 2 }

--
-- MIB objects
--
hpicfIpSlaTable OBJECT-TYPE
   SYNTAX            SEQUENCE OF HpicfIpSlaEntry
   MAX-ACCESS        not-accessible
   STATUS            current
   DESCRIPTION       "This table specifies IP SLA test parameters as SLA entries."
   ::= { hpicfIpSlaObjects 1 }

hpicfIpSlaEntry OBJECT-TYPE
   SYNTAX            HpicfIpSlaEntry
   MAX-ACCESS        not-accessible
   STATUS            current
   DESCRIPTION       "An entry on this table specifies the destination IP address/
                      Hostname, Source address, Source Interface ID & Row status
                      corresponding to each SLA test."
   INDEX { hpicfIpSlaID }
   ::= { hpicfIpSlaTable 1 }

HpicfIpSlaEntry ::= SEQUENCE
   {
      hpicfIpSlaID                  Integer32,
      hpicfIpSlaType                INTEGER,
      hpicfIpSlaAdminState          INTEGER,
      hpicfIpSlaSourceAddressType   InetAddressType,
      hpicfIpSlaSourceAddress       InetAddress,
      hpicfIpSlaL4SourcePort        InetPortNumber,
      hpicfIpSlaSourceInterface     InterfaceIndexOrZero,
      hpicfIpSlaDestAddressType     InetAddressType,
      hpicfIpSlaDestAddress         InetAddress,
      hpicfIpSlaL4DestPort          InetPortNumber,
      hpicfIpSlaRowStatus           RowStatus
   }

hpicfIpSlaID    OBJECT-TYPE
   SYNTAX            Integer32 (1..255)
   MAX-ACCESS        not-accessible
   STATUS            current
   DESCRIPTION       "This is an identifier for the IP SLA."
   ::= { hpicfIpSlaEntry 1 }

hpicfIpSlaType OBJECT-TYPE
   SYNTAX    INTEGER
   {
      icmpEcho(1),
      udpEcho(2),
      udpJitter(3),
      udpJitterVoIP(4),
      tcpConnect(5),
      dhcp(6),
      dns(7)

   }
  MAX-ACCESS         read-create
  STATUS             current
  DESCRIPTION        "SLA Probe Type. IcmpEcho is similar to ping protocol and
                      the destination should be enabled with responder
                      functionality for udpEcho, udpJitter, udpJitterVoIP and
                      tcpConnect. For DHCP and DNS, destination device should be
                      enabled with DHCP and DNS servers, respectively."
  ::= { hpicfIpSlaEntry 2 }

hpicfIpSlaAdminState     OBJECT-TYPE
   SYNTAX  INTEGER
   {
      enable (1),
      disable (2)
   }
   MAX-ACCESS        read-create
   STATUS            current
   DESCRIPTION       "Enable or disable the IP Service Level Agreement (SLA) probe."
   DEFVAL{ disable }
   ::= { hpicfIpSlaEntry 3}

hpicfIpSlaSourceAddressType OBJECT-TYPE
   SYNTAX            InetAddressType
   MAX-ACCESS        read-create
   STATUS            current
   DESCRIPTION       "SLA source address type."
   ::= { hpicfIpSlaEntry 4 }

hpicfIpSlaSourceAddress OBJECT-TYPE
   SYNTAX            InetAddress
   MAX-ACCESS        read-create
   STATUS            current
   DESCRIPTION       "SLA source address."
   ::= { hpicfIpSlaEntry 5 }

hpicfIpSlaL4SourcePort OBJECT-TYPE
   SYNTAX            InetPortNumber
   MAX-ACCESS        read-create
   STATUS            current
   DESCRIPTION       "SLA source port to be used for SLA probes that use a
                      transport layer such as udpEcho, udpJitter, udpJitterVoIP
                      and tcpConnect. The allowed range is from 1024 to 65535."
  ::= { hpicfIpSlaEntry 6 }

hpicfIpSlaSourceInterface OBJECT-TYPE
   SYNTAX            InterfaceIndexOrZero
   MAX-ACCESS        read-create
   STATUS            current
   DESCRIPTION       "SLA source interface."
   ::= { hpicfIpSlaEntry 7 }

hpicfIpSlaDestAddressType OBJECT-TYPE
   SYNTAX            InetAddressType
   MAX-ACCESS        read-create
   STATUS            current
   DESCRIPTION       "SLA destination address type."
   ::= { hpicfIpSlaEntry 8 }

hpicfIpSlaDestAddress OBJECT-TYPE
   SYNTAX            InetAddress
   MAX-ACCESS        read-create
   STATUS            current
   DESCRIPTION       "SLA destination address."
   ::= { hpicfIpSlaEntry 9 }

hpicfIpSlaL4DestPort OBJECT-TYPE
   SYNTAX            InetPortNumber
   MAX-ACCESS        read-create
   STATUS            current
   DESCRIPTION       "Port on target device which responds back to the probe.
                      This is used for SLA probes that use a transport layer
                      such as udpEcho, udpJitter, udpJitterVoIP and tcpConnect
                      SLA types. The allowed range is from 1024 to 65535."
   ::= { hpicfIpSlaEntry 10 }

hpicfIpSlaRowStatus OBJECT-TYPE
   SYNTAX            RowStatus
   MAX-ACCESS        read-create
   STATUS            current
   DESCRIPTION       "SLA row status."
   ::= { hpicfIpSlaEntry 11 }

--
--- SLA to Probe attributes Configuration - Table
--
hpicfIpSlaAttrTable OBJECT-TYPE
   SYNTAX            SEQUENCE OF HpicfIpSlaAttrEntry
   MAX-ACCESS        not-accessible
   STATUS            current
   DESCRIPTION       "This table specifies IP SLA test parameters as SLA
                      entries."
   ::= { hpicfIpSlaObjects 2 }

hpicfIpSlaAttrEntry OBJECT-TYPE
   SYNTAX            HpicfIpSlaAttrEntry
   MAX-ACCESS        not-accessible
   STATUS            current
   DESCRIPTION       "An entry on this table specifies the attributes of SLA
                      test such as scheduling parameters, TOS, payload size,
                      history bucket size and inter packet interval,
                      corresponding to each SLA test."
   INDEX { hpicfIpSlaID }
   ::= { hpicfIpSlaAttrTable 1 }

HpicfIpSlaAttrEntry ::= SEQUENCE
   {
      hpicfIpSlaSchedStartTime      DateAndTime,
      hpicfIpSlaSchedEndTime        DateAndTime,
      hpicfIpSlaSchedFreq           Unsigned32,
      hpicfIpSlaSchedRepeat         Unsigned32,
      hpicfIpSlaAttrTOS             Unsigned32,
      hpicfIpSlaAttrHistorySize     Unsigned32,
      hpicfIpSlaAttrPayloadSize     Unsigned32,
      hpicfIpSlaAttrNumPkts         Unsigned32,
      hpicfIpSlaAttrPktInterval     Unsigned32,
      hpicfIpSlaAttrRowStatus       RowStatus,
      hpicfIpSlaAttrCodecType       INTEGER,
      hpicfIpSlaAttrAdvntgFactr     Unsigned32
   }

hpicfIpSlaSchedStartTime OBJECT-TYPE
   SYNTAX            DateAndTime
   MAX-ACCESS        read-create
   STATUS            current
   DESCRIPTION       "Timestamp to denote when to start this SLA probe."
   ::= { hpicfIpSlaAttrEntry 1 }

hpicfIpSlaSchedEndTime OBJECT-TYPE
   SYNTAX            DateAndTime
   MAX-ACCESS        read-create
   STATUS            current
   DESCRIPTION       "Timestamp to denote when to end this SLA probe."
   ::= { hpicfIpSlaAttrEntry 2 }

hpicfIpSlaSchedFreq OBJECT-TYPE
   SYNTAX            Unsigned32
   MAX-ACCESS        read-create
   STATUS            current
   DESCRIPTION       "Frequency in seconds. This value is used to send probes."
   DEFVAL   { 60 }
   ::= { hpicfIpSlaAttrEntry 3 }

hpicfIpSlaSchedRepeat OBJECT-TYPE
   SYNTAX            Unsigned32
   MAX-ACCESS        read-create
   STATUS            current
   DESCRIPTION       "Number of times this test will be repeated."
   ::= { hpicfIpSlaAttrEntry 4 }

hpicfIpSlaAttrTOS OBJECT-TYPE
   SYNTAX            Unsigned32 (0..255)
   MAX-ACCESS        read-create
   STATUS            current
   DESCRIPTION       "Type of service value to be set for the probe packet."
   ::= { hpicfIpSlaAttrEntry 5 }

hpicfIpSlaAttrHistorySize OBJECT-TYPE
   SYNTAX            Unsigned32
   MAX-ACCESS        read-create
   STATUS            current
   DESCRIPTION       "Number of history records to be maintained for SLA test.
                      Size can vary from 1 to 50."
   DEFVAL          { 25 }
   ::= { hpicfIpSlaAttrEntry 6 }

hpicfIpSlaAttrPayloadSize OBJECT-TYPE
   SYNTAX            Unsigned32
   MAX-ACCESS        read-create
   STATUS            current
   DESCRIPTION       "Size of the packet payload to be sent out for each probe.
                      It can be set from 0 to 1440 for udpEcho, icmpEcho and
                      from 68 to 8100 for udpJitter."
   DEFVAL   { 0 }
   ::= { hpicfIpSlaAttrEntry 7 }

hpicfIpSlaAttrNumPkts OBJECT-TYPE
   SYNTAX            Unsigned32
   MAX-ACCESS        read-create
   STATUS            current
   DESCRIPTION       "Number of packets to be sent out for a single probe for
                      jitter SLA type."
   DEFVAL   { 10 }
   ::= { hpicfIpSlaAttrEntry 8 }

hpicfIpSlaAttrPktInterval OBJECT-TYPE
   SYNTAX            Unsigned32
   MAX-ACCESS        read-create
   STATUS            current
   DESCRIPTION       "Inter packet interval in milli seconds. Which is to be
                      used for packets that are sent out for a single probe for
                      jitter SLA type."
   ::= { hpicfIpSlaAttrEntry 9 }

hpicfIpSlaAttrRowStatus OBJECT-TYPE
   SYNTAX            RowStatus
   MAX-ACCESS        read-create
   STATUS            current
   DESCRIPTION       "SLA attribute row status."
   ::= { hpicfIpSlaAttrEntry 10 }

hpicfIpSlaAttrCodecType OBJECT-TYPE
   SYNTAX  INTEGER
   {
      g711a(1),
      g711u(2),
      g729a(3)
   }
   MAX-ACCESS        read-create
   STATUS            current
   DESCRIPTION       "Codec-type for the VoIP SLA test."
   ::= { hpicfIpSlaAttrEntry 11 }

hpicfIpSlaAttrAdvntgFactr OBJECT-TYPE
   SYNTAX            Unsigned32 (0..20)
   MAX-ACCESS        read-create
   STATUS            current
   DESCRIPTION       "Advantage factor to calculate the MOS and ICPIF values
                      for VoIP SLA type."
   DEFVAL   { 0 }
   ::= { hpicfIpSlaAttrEntry 12 }
--
-- SLA to Threshold Configuration  Table
--
hpicfIpSlaThrTable OBJECT-TYPE
   SYNTAX            SEQUENCE OF HpicfIpSlaThrEntry
   MAX-ACCESS        not-accessible
   STATUS            current
   DESCRIPTION       "This table specifies IP SLA threshold-action parameters as
                      entries. When one of the monitored parameters of an SLA
                      test goes beyond the configured thresholds, notifications
                      are generated either as traps or syslog messages."
   ::= { hpicfIpSlaObjects 3 }

hpicfIpSlaThrEntry OBJECT-TYPE
   SYNTAX            HpicfIpSlaThrEntry
   MAX-ACCESS        not-accessible
   STATUS            current
   DESCRIPTION       "An entry on this table specifies the Metric type, upper
                      and lower limit of thresholds, threshold type and action
                      to be taken."
  INDEX { hpicfIpSlaID,  hpicfIpSlaThrMetricType}
   ::= { hpicfIpSlaThrTable 1 }

HpicfIpSlaThrEntry ::= SEQUENCE
   {
      hpicfIpSlaThrMetricType       INTEGER,
      hpicfIpSlaThrUpper            Integer32,
      hpicfIpSlaThrLower            Integer32,
      hpicfIpSlaThrType             INTEGER,
      hpicfIpSlaThrCount            Unsigned32,
      hpicfIpSlaThrAction           INTEGER,
      hpicfIpSlaThrRowStatus        RowStatus
   }

hpicfIpSlaThrMetricType OBJECT-TYPE
   SYNTAX    INTEGER
   {
      rtt(1),
      jitter(2),
      srcTodstTime(3),
      dstTosrcTime(4),
      mos(5),
      icpif(6),
      packetLoss(7),
      testCompletion(8),
      sdJitterPos(9),
      dsJitterPos(10)
   }
   MAX-ACCESS        not-accessible
   STATUS            current
   DESCRIPTION       "SLA metric type to be monitored. The rtt type is the
                      round trip time of the probe packet. The jitter type is
                      the inter-packet delay variance. The srcTodstTime type is
                      the one-way trip time from source to destination. The
                      dstTosrcTtime type is the one-way trip time from
                      destination to source. The Mean Opinion Scores (MOS) type
                      is derived only for udpJitterVoIP SLA. The Calculated
                      Planning Impairment Factor (ICPIF) type is derived only
                      for udpJitterVoIP SLA. ThepacketLoss type is to monitor
                      loss of communication. The testCompletion type is for
                      notifying about the completion of probe test. The
                      sdJitterPos type is the source-to-destination positive
                      jitter and the dsJitterPos type is the
                      destination-to-source positivejitter."
   ::= { hpicfIpSlaThrEntry 1 }

hpicfIpSlaThrUpper OBJECT-TYPE
   SYNTAX            Integer32
   MAX-ACCESS        read-create
   STATUS            current
   DESCRIPTION       "Acceptable upper-limit of threshold value for SLA. This
                      value is not applicable when hpicfIpSlaThrMetricType
                      is set to packetLoss and testCompletion."
   ::= { hpicfIpSlaThrEntry 2 }

hpicfIpSlaThrLower OBJECT-TYPE
   SYNTAX            Integer32
   MAX-ACCESS        read-create
   STATUS            current
   DESCRIPTION       "Acceptable lower-limit of threshold value for SLA. This
                      value is not applicable when hpicfIpSlaThrMetricType
                      is set to packetLoss and testCompletion."
   ::= { hpicfIpSlaThrEntry 3 }

hpicfIpSlaThrType      OBJECT-TYPE
   SYNTAX   INTEGER
   {
      immediate(1),
      consecutive(2),
      aggregated(3)
   }
   MAX-ACCESS        read-create
   STATUS            current
   DESCRIPTION       "Configure threshold type to trigger action. When a trap/log
                      has to be generated each time the threshold is breached,
                      immediate threshold type can be used. The Consecutive threshold
                      type generates traps/logs when the threshold is violated a
                      certain number of times This value is not applicable when
                      hpicfIpSlaThrMetricType is set to testCompletion. The aggregated
                      threshold type is used to generate traps/logs for aggregated probes."
   ::= { hpicfIpSlaThrEntry 4}

hpicfIpSlaThrCount      OBJECT-TYPE
   SYNTAX            Unsigned32
   MAX-ACCESS        read-create
   STATUS            current
   DESCRIPTION       "The value for the number of consecutive times the upper or lower
                      limit of the threshold is violated. For example, this can be
                      configured to trigger a trap/log when the RTT is more than the
                      upper limit, x number of times consecutively. This value is
                      applicable only if hpicfIpSlaThrType is set to consecutive."
   ::= { hpicfIpSlaThrEntry 5}

hpicfIpSlaThrAction      OBJECT-TYPE
   SYNTAX   INTEGER
   {
      none(0),
      trap(1),
      log(2),
      trapAndLog(3)
   }
   MAX-ACCESS      read-create
   STATUS          current
   DESCRIPTION     "The number of probe packets used to calculate Round Trip Time
                    for jitter test."
   ::= { hpicfIpSlaThrEntry 6}

hpicfIpSlaThrRowStatus OBJECT-TYPE
   SYNTAX            RowStatus
   MAX-ACCESS        read-create
   STATUS            current
   DESCRIPTION       "Threshold table row status."
   ::= { hpicfIpSlaThrEntry 7}

--
-- IP SLA Responder objects
--
hpicfIpSlaRespTable OBJECT-TYPE
   SYNTAX            SEQUENCE OF HpicfIpSlaRespEntry
   MAX-ACCESS        not-accessible
   STATUS            current
   DESCRIPTION       "This table specifies IP SLA responder parameters as entries."
   ::= { hpicfIpSlaObjects 4 }

hpicfIpSlaRespEntry OBJECT-TYPE
   SYNTAX            HpicfIpSlaRespEntry
   MAX-ACCESS        not-accessible
   STATUS            current
   DESCRIPTION       "An entry on this table specifies the local IP address,
                      port number and row status corresponding to each SLA
                      responder config."
   INDEX
   {
      hpicfIpSlaRespType,
      hpicfIpSlaRespAddress,
      hpicfIpSlaRespL4Port
   }
   ::= { hpicfIpSlaRespTable 1 }

   HpicfIpSlaRespEntry ::= SEQUENCE
   {
      hpicfIpSlaRespType            INTEGER,
      hpicfIpSlaRespAddressType     InetAddressType,
      hpicfIpSlaRespAddress         InetAddress,
      hpicfIpSlaRespL4Port          InetPortNumber,
      hpicfIpSlaRespRowStatus       RowStatus
   }

hpicfIpSlaRespType OBJECT-TYPE
   SYNTAX  INTEGER
   {
      udpEcho(1),
      udpJitter(2),
      udpJitterVoIP(3),
      tcpConnect(4)
   }
   MAX-ACCESS        not-accessible
   STATUS            current
   DESCRIPTION       "The SLA responder type. The udpEcho and tcpConnect objects
                      are for UDP and TCP packets, respectively. The udpJitter
                      and udpJitterVoIP values calculate one-way delay, therefore
                      a timestamp has to be embedded while replying back. This is
                      one of the indexes for the hpicfIpSlaRespTable."
   ::= { hpicfIpSlaRespEntry 1 }

hpicfIpSlaRespAddressType OBJECT-TYPE
   SYNTAX            InetAddressType
   MAX-ACCESS        read-create
   STATUS            current
   DESCRIPTION       "SLA responder IP address type."
   ::= { hpicfIpSlaRespEntry 2 }

hpicfIpSlaRespAddress OBJECT-TYPE
   SYNTAX            InetAddress
   MAX-ACCESS        not-accessible
   STATUS            current
   DESCRIPTION       "The local IP address to which the responder is bound.
                      This is one of the indexes for the hpicfIpSlaRespTable."
  ::= { hpicfIpSlaRespEntry 3 }

hpicfIpSlaRespL4Port OBJECT-TYPE
   SYNTAX            InetPortNumber
   MAX-ACCESS        not-accessible
   STATUS            current
   DESCRIPTION       "L4 port number on hpicfIpSlaRespAddress where the responder
                      listens for probe packets from SLA source. This is one of
                      the indexes for the hpicfIpSlaRespTable. The allowed range
                      is from 1024 to 65535."
   ::= { hpicfIpSlaRespEntry 4 }

hpicfIpSlaRespRowStatus OBJECT-TYPE
   SYNTAX            RowStatus
   MAX-ACCESS        read-create
   STATUS            current
   DESCRIPTION       "SLA responder row status."
   ::= { hpicfIpSlaRespEntry 5}

--
-- IP SLA result Table
--
hpicfIpSlaMsgTable OBJECT-TYPE
   SYNTAX            SEQUENCE OF HpicfIpSlaMsgEntry
   MAX-ACCESS        not-accessible
   STATUS            current
   DESCRIPTION       "This table specifies the IP SLA result parameters as entries."
   ::= { hpicfIpSlaObjects 5 }

hpicfIpSlaMsgEntry OBJECT-TYPE
   SYNTAX            HpicfIpSlaMsgEntry
   MAX-ACCESS        not-accessible
   STATUS            current
   DESCRIPTION       "An entry on this table specifies the probe received time,
                      probe error counters and threshold hit counter."
   INDEX { hpicfIpSlaID }
   ::= { hpicfIpSlaMsgTable 1 }

   HpicfIpSlaMsgEntry ::= SEQUENCE
   {
      hpicfIpSlaMsgLastProbeRcvd       Unsigned32,
      hpicfIpSlaMsgLastClrRec          Unsigned32,
      hpicfIpSlaMsgSuccProbe           Unsigned32,
      hpicfIpSlaMsgIntErr              Unsigned32,
      hpicfIpSlaMsgLocIntfDown         Unsigned32,
      hpicfIpSlaMsgResTimeout          Unsigned32,
      hpicfIpSlaMsgDNSFormatErr        Unsigned32,
      hpicfIpSlaMsgServerFaild         Unsigned32,
      hpicfIpSlaMsgDomainNotExist      Unsigned32,
      hpicfIpSlaMsgFunctnNotImpl       Unsigned32,
      hpicfIpSlaMsgServerRefusd        Unsigned32,
      hpicfIpSlaMsgNameNotExist        Unsigned32,
      hpicfIpSlaMsgRRsetNotExist       Unsigned32,
      hpicfIpSlaMsgServerNotInZone     Unsigned32,
      hpicfIpSlaMsgNameNotInZone       Unsigned32,
      hpicfIpSlaMsgDHCPFaildResln      Unsigned32,
      hpicfIpSlaMsgOffrNotRecvd        Unsigned32,
      hpicfIpSlaMsgNACKRecvd           Unsigned32,
      hpicfIpSlaMsgThrHitRTT           Unsigned32,
      hpicfIpSlaMsgStatus              Unsigned32,
      hpicfIpSlaMsgNxtSched            Unsigned32,
      hpicfIpSlaMsgThrHitPostvSDAvg    Unsigned32,
      hpicfIpSlaMsgThrHitPostvDSAvg    Unsigned32,
      hpicfIpSlaMsgThrHitOneWayDSAvg   Unsigned32,
      hpicfIpSlaMsgThrHitOneWaySDAvg   Unsigned32,
      hpicfIpSlaMsgThrHitAvgICPIF      Unsigned32,
      hpicfIpSlaMsgThrHitAvgMOS        Unsigned32,
      hpicfIpSlaMsgNameServUnreach     Unsigned32,
      hpicfIpSlaMsgDHCPReleaseErr      Unsigned32,
      hpicfIpSlaMsgThrHitPktLoss       Unsigned32,
      hpicfIpSlaMsgDstUnreach          Unsigned32,
      hpicfIpSlaMsgProbeSkpd           Unsigned32,
      hpicfIpSlaMsgDNSResolnFailed     Unsigned32,
      hpicfIpSlaMsgNoRoutetoTgt        Unsigned32,
      hpicfIpSlaMsgUnbleToConctHost    Unsigned32,
      hpicfIpSlaMsgSuccConnection      Unsigned32,
      hpicfIpSlaMsgPossTrailDropped    Unsigned32,
      hpicfIpSlaMsgNoRespFrmTgt        Unsigned32,
      hpicfIpSlaMsgProbeRespRecvd      Unsigned32
   }
hpicfIpSlaMsgLastProbeRcvd       OBJECT-TYPE
   SYNTAX            Unsigned32
   MAX-ACCESS        read-only
   STATUS            current
   DESCRIPTION       "Last probe received time."
   ::= { hpicfIpSlaMsgEntry 1}

hpicfIpSlaMsgLastClrRec          OBJECT-TYPE
   SYNTAX            Unsigned32
   MAX-ACCESS        read-only
   STATUS            current
   DESCRIPTION       "Last clear record done time."
   ::= { hpicfIpSlaMsgEntry 2}

hpicfIpSlaMsgSuccProbe           OBJECT-TYPE
   SYNTAX            Unsigned32
   MAX-ACCESS        read-only
   STATUS            current
   DESCRIPTION       "Number of successful probes."
   ::= { hpicfIpSlaMsgEntry 3}

hpicfIpSlaMsgIntErr              OBJECT-TYPE
   SYNTAX            Unsigned32
   MAX-ACCESS        read-only
   STATUS            current
   DESCRIPTION       "Internal error count."
   ::= { hpicfIpSlaMsgEntry 4}

hpicfIpSlaMsgLocIntfDown         OBJECT-TYPE
   SYNTAX            Unsigned32
   MAX-ACCESS        read-only
   STATUS            current
   DESCRIPTION       "Number of probes failed due to local interface failure."
   ::= { hpicfIpSlaMsgEntry 5}

hpicfIpSlaMsgResTimeout          OBJECT-TYPE
   SYNTAX            Unsigned32
   MAX-ACCESS        read-only
   STATUS            current
   DESCRIPTION       "Resolution timed out."
   ::= { hpicfIpSlaMsgEntry 6}

hpicfIpSlaMsgDNSFormatErr        OBJECT-TYPE
   SYNTAX            Unsigned32
   MAX-ACCESS        read-only
   STATUS            current
   DESCRIPTION       "Number of DNS format errors."
   ::= { hpicfIpSlaMsgEntry 7}

hpicfIpSlaMsgServerFaild        OBJECT-TYPE
   SYNTAX            Unsigned32
   MAX-ACCESS        read-only
   STATUS            current
   DESCRIPTION       "Number of server failed errors."
   ::= { hpicfIpSlaMsgEntry 8}

hpicfIpSlaMsgDomainNotExist      OBJECT-TYPE
   SYNTAX            Unsigned32
   MAX-ACCESS        read-only
   STATUS            current
   DESCRIPTION       "Number of domain does not exist errors."
   ::= { hpicfIpSlaMsgEntry 9}

hpicfIpSlaMsgFunctnNotImpl       OBJECT-TYPE
   SYNTAX            Unsigned32
   MAX-ACCESS        read-only
   STATUS            current
   DESCRIPTION       "Number of function not implemented errors."
   ::= { hpicfIpSlaMsgEntry 10}

hpicfIpSlaMsgServerRefusd        OBJECT-TYPE
   SYNTAX            Unsigned32
   MAX-ACCESS        read-only
   STATUS            current
   DESCRIPTION       "Number of server refused errors."
   ::= { hpicfIpSlaMsgEntry 11}

hpicfIpSlaMsgNameNotExist        OBJECT-TYPE
   SYNTAX            Unsigned32
   MAX-ACCESS        read-only
   STATUS            current
   DESCRIPTION       "Number of name does not exist errors."
   ::= { hpicfIpSlaMsgEntry 12}

hpicfIpSlaMsgRRsetNotExist       OBJECT-TYPE
   SYNTAX            Unsigned32
   MAX-ACCESS        read-only
   STATUS            current
   DESCRIPTION       "Number of RRset that should not exist errors."
   ::= { hpicfIpSlaMsgEntry 13}

hpicfIpSlaMsgServerNotInZone     OBJECT-TYPE
   SYNTAX            Unsigned32
   MAX-ACCESS        read-only
   STATUS            current
   DESCRIPTION       "Number of server not in the zone errors."
   ::= { hpicfIpSlaMsgEntry 14}

hpicfIpSlaMsgNameNotInZone       OBJECT-TYPE
   SYNTAX            Unsigned32
   MAX-ACCESS        read-only
   STATUS            current
   DESCRIPTION       "Number of name not in the zone errors."
   ::= { hpicfIpSlaMsgEntry 15}

hpicfIpSlaMsgDHCPFaildResln      OBJECT-TYPE
   SYNTAX            Unsigned32
   MAX-ACCESS        read-only
   STATUS            current
   DESCRIPTION       "Number of DHCP failed resolutions."
   ::= { hpicfIpSlaMsgEntry 16}

hpicfIpSlaMsgOffrNotRecvd        OBJECT-TYPE
   SYNTAX            Unsigned32
   MAX-ACCESS        read-only
   STATUS            current
   DESCRIPTION       "Number of DHCP offer not received errors."
   ::= { hpicfIpSlaMsgEntry 17}

hpicfIpSlaMsgNACKRecvd           OBJECT-TYPE
   SYNTAX            Unsigned32
   MAX-ACCESS        read-only
   STATUS            current
   DESCRIPTION       "Number of NACKs received."
   ::= { hpicfIpSlaMsgEntry 18}

hpicfIpSlaMsgThrHitRTT           OBJECT-TYPE
   SYNTAX            Unsigned32
   MAX-ACCESS        read-only
   STATUS            current
   DESCRIPTION       "Number of round-trip time hits to threshold."
   ::= { hpicfIpSlaMsgEntry 19}

hpicfIpSlaMsgStatus              OBJECT-TYPE
   SYNTAX            Unsigned32
   MAX-ACCESS        read-only
   STATUS            current
   DESCRIPTION       "IP SLA current running status."
   ::= { hpicfIpSlaMsgEntry 20}

hpicfIpSlaMsgNxtSched            OBJECT-TYPE
   SYNTAX            Unsigned32
   MAX-ACCESS        read-only
   STATUS            current
   DESCRIPTION       "Next scheduled time of IP SLA probe."
   ::= { hpicfIpSlaMsgEntry 21}

hpicfIpSlaMsgThrHitPostvSDAvg    OBJECT-TYPE
   SYNTAX            Unsigned32
   MAX-ACCESS        read-only
   STATUS            current
   DESCRIPTION       "The average positive jitter value of packets moving from
                      source to destination that cross the threshold."
  ::= { hpicfIpSlaMsgEntry 22}

hpicfIpSlaMsgThrHitPostvDSAvg    OBJECT-TYPE
   SYNTAX            Unsigned32
   MAX-ACCESS        read-only
   STATUS            current
   DESCRIPTION       "The average positive jitter value of packets moving from
                      destination to source that cross the threshold."
  ::= { hpicfIpSlaMsgEntry 23}

hpicfIpSlaMsgThrHitOneWayDSAvg   OBJECT-TYPE
   SYNTAX            Unsigned32
   MAX-ACCESS        read-only
   STATUS            current
   DESCRIPTION       "The average time taken by packets moving from
                      destination to source that cross the threshold."
   ::= { hpicfIpSlaMsgEntry 24}

hpicfIpSlaMsgThrHitOneWaySDAvg   OBJECT-TYPE
   SYNTAX            Unsigned32
   MAX-ACCESS        read-only
   STATUS            current
   DESCRIPTION       "The average time taken by packets moving from
                      source to destination that cross the threshold."
   ::= { hpicfIpSlaMsgEntry 25}

hpicfIpSlaMsgThrHitAvgICPIF      OBJECT-TYPE
   SYNTAX            Unsigned32
   MAX-ACCESS        read-only
   STATUS            current
   DESCRIPTION       "Average value of the ICPIF of packets that cross
                      the threshold."
   ::= { hpicfIpSlaMsgEntry 26}

hpicfIpSlaMsgThrHitAvgMOS        OBJECT-TYPE
   SYNTAX            Unsigned32
   MAX-ACCESS        read-only
   STATUS            current
   DESCRIPTION       "Average value of the MOS of packets that cross the threshold.
                      The Value of this object is 100 times of the actual value."
   ::= { hpicfIpSlaMsgEntry 27}

hpicfIpSlaMsgNameServUnreach     OBJECT-TYPE
   SYNTAX            Unsigned32
   MAX-ACCESS        read-only
   STATUS            current
   DESCRIPTION       "Number of errors due to name server being unreachable."
   ::= { hpicfIpSlaMsgEntry 28}

hpicfIpSlaMsgDHCPReleaseErr      OBJECT-TYPE
   SYNTAX            Unsigned32
   MAX-ACCESS        read-only
   STATUS            current
   DESCRIPTION       "Number of DHCP release errors."
   ::= { hpicfIpSlaMsgEntry 29}

hpicfIpSlaMsgThrHitPktLoss       OBJECT-TYPE
   SYNTAX            Unsigned32
   MAX-ACCESS        read-only
   STATUS            current
   DESCRIPTION       "Number of packet loss for each probe."
   ::= { hpicfIpSlaMsgEntry 30}

hpicfIpSlaMsgDstUnreach          OBJECT-TYPE
   SYNTAX            Unsigned32
   MAX-ACCESS        read-only
   STATUS            current
   DESCRIPTION       "Number of probes failed due to destination not
                      being reachable."
   ::= { hpicfIpSlaMsgEntry 31}

hpicfIpSlaMsgProbeSkpd           OBJECT-TYPE
   SYNTAX            Unsigned32
   MAX-ACCESS        read-only
   STATUS            current
   DESCRIPTION       "Number of probes skipped due to DNS resolution delay."
   ::= { hpicfIpSlaMsgEntry 32}

hpicfIpSlaMsgDNSResolnFailed     OBJECT-TYPE
   SYNTAX            Unsigned32
   MAX-ACCESS        read-only
   STATUS            current
   DESCRIPTION       "Number of times DNS resolution failed."
   ::= { hpicfIpSlaMsgEntry 33}

hpicfIpSlaMsgNoRoutetoTgt        OBJECT-TYPE
   SYNTAX            Unsigned32
   MAX-ACCESS        read-only
   STATUS            current
   DESCRIPTION       "Number of errors due to no route to target."
   ::= { hpicfIpSlaMsgEntry 34}

hpicfIpSlaMsgUnbleToConctHost    OBJECT-TYPE
   SYNTAX            Unsigned32
   MAX-ACCESS        read-only
   STATUS            current
   DESCRIPTION       "Number of errors due to no host connectivity."
   ::= { hpicfIpSlaMsgEntry 35}

hpicfIpSlaMsgSuccConnection      OBJECT-TYPE
   SYNTAX            Unsigned32
   MAX-ACCESS        read-only
   STATUS            current
   DESCRIPTION       "Number of successful connections."
   ::= { hpicfIpSlaMsgEntry 36}

hpicfIpSlaMsgPossTrailDropped    OBJECT-TYPE
   SYNTAX            Unsigned32
   MAX-ACCESS        read-only
   STATUS            current
   DESCRIPTION       "Number of probes dropped due to resource unavailability."
   ::= { hpicfIpSlaMsgEntry 37}

hpicfIpSlaMsgNoRespFrmTgt        OBJECT-TYPE
   SYNTAX            Unsigned32
   MAX-ACCESS        read-only
   STATUS            current
   DESCRIPTION       "Number of errors due to no response from target."
   ::= { hpicfIpSlaMsgEntry 38}

hpicfIpSlaMsgProbeRespRecvd      OBJECT-TYPE
   SYNTAX            Unsigned32
   MAX-ACCESS        read-only
   STATUS            current
   DESCRIPTION       "Number of probes received."
   ::= { hpicfIpSlaMsgEntry 39}

--
-- IP SLA history Table
--
hpicfIpSlaHistTable OBJECT-TYPE
   SYNTAX            SEQUENCE OF HpicfIpSlaHistEntry
   MAX-ACCESS        not-accessible
   STATUS            current
   DESCRIPTION       "This table specifies the history of IP SLA result."
   ::= { hpicfIpSlaObjects 6 }

hpicfIpSlaHistEntry OBJECT-TYPE
   SYNTAX            HpicfIpSlaHistEntry
   MAX-ACCESS        not-accessible
   STATUS            current
   DESCRIPTION       "An entry on this table specifies the minimum, maximum
                      and the average time taken from source to destination
                      and vice versa."
   INDEX { hpicfIpSlaID }
   ::= { hpicfIpSlaHistTable 1 }

   HpicfIpSlaHistEntry ::= SEQUENCE
   {
      hpicfIpSlaHistMinRTT           Unsigned32,
      hpicfIpSlaHistMaxRTT           Unsigned32,
      hpicfIpSlaHistAvgRTT           Unsigned32,
      hpicfIpSlaHistTotalRTT         Unsigned32,
      hpicfIpSlaHistRTT2             Unsigned32,
      hpicfIpSlaHistNumOfRTT         Unsigned32,
      hpicfIpSlaHistProbID           Unsigned32,
      hpicfIpSlaHistLastSuccProbTime Unsigned32,
      hpicfIpSlaHistPacketLoss       Unsigned32,
      hpicfIpSlaHistSentPktNum       Unsigned32,
      hpicfIpSlaHistRecvdPktNum      Unsigned32,
      hpicfIpSlaHistMinStoDPostv     Unsigned32,
      hpicfIpSlaHistMaxStoDPostv     Unsigned32,
      hpicfIpSlaHistNumOfPosSD       Unsigned32,
      hpicfIpSlaHistSumOfPosSD       Unsigned32,
      hpicfIpSlaHistAvgStoDPostv     Unsigned32,
      hpicfIpSlaHistSum2PositivesSD  Unsigned32,
      hpicfIpSlaHistMinDtoSPostv     Unsigned32,
      hpicfIpSlaHistMaxDtoSPostv     Unsigned32,
      hpicfIpSlaHistNumOfPosDS       Unsigned32,
      hpicfIpSlaHistSumOfPosDS       Unsigned32,
      hpicfIpSlaHistAvgDtoSPostv     Unsigned32,
      hpicfIpSlaHistSum2PositivesDS  Unsigned32,
      hpicfIpSlaHistMinStoDNegtv     Unsigned32,
      hpicfIpSlaHistMaxStoDNegtv     Unsigned32,
      hpicfIpSlaHistNumOfNegSD       Unsigned32,
      hpicfIpSlaHistSumOfNegSD       Unsigned32,
      hpicfIpSlaHistAvgStoDNegtv     Unsigned32,
      hpicfIpSlaHistSum2NegativesSD  Unsigned32,
      hpicfIpSlaHistMinDtoSNegtv     Unsigned32,
      hpicfIpSlaHistMaxDtoSNegtv     Unsigned32,
      hpicfIpSlaHistNumOfNegDS       Unsigned32,
      hpicfIpSlaHistSumOfNegDS       Unsigned32,
      hpicfIpSlaHistAvgDtoSNegtv     Unsigned32,
      hpicfIpSlaHistSum2NegativesDS  Unsigned32,
      hpicfIpSlaHistMinStoDDelay     Unsigned32,
      hpicfIpSlaHistMaxStoDDelay     Unsigned32,
      hpicfIpSlaHistSumStoDDelay     Unsigned32,
      hpicfIpSlaHistNumOfDelaySD     Unsigned32,
      hpicfIpSlaHistSum2DelaySD      Unsigned32,
      hpicfIpSlaHistMinDtoSDelay     Unsigned32,
      hpicfIpSlaHistMaxDtoSDelay     Unsigned32,
      hpicfIpSlaHistNumOfDelayDS     Unsigned32,
      hpicfIpSlaHistSumDtoSDelay     Unsigned32,
      hpicfIpSlaHistSum2DelayDS      Unsigned32,
      hpicfIpSlaHistICPIF            Unsigned32,
      hpicfIpSlaHistMOS              Unsigned32,
      hpicfIpSlaHistAvgStoDDelay     Unsigned32,
      hpicfIpSlaHistAvgDtoSDelay     Unsigned32
   }
hpicfIpSlaHistMinRTT             OBJECT-TYPE
   SYNTAX            Unsigned32
   MAX-ACCESS        read-only
   STATUS            current
   DESCRIPTION       "The minimum probe round-trip time."
   ::= { hpicfIpSlaHistEntry 1}

hpicfIpSlaHistMaxRTT             OBJECT-TYPE
   SYNTAX            Unsigned32
   MAX-ACCESS        read-only
   STATUS            current
   DESCRIPTION       "The maximum probe round-trip time."
   ::= { hpicfIpSlaHistEntry 2}

hpicfIpSlaHistAvgRTT             OBJECT-TYPE
   SYNTAX            Unsigned32
   MAX-ACCESS        read-only
   STATUS            current
   DESCRIPTION       "The average probe round-trip time."
   ::= { hpicfIpSlaHistEntry 3}

hpicfIpSlaHistTotalRTT           OBJECT-TYPE
   SYNTAX            Unsigned32
   MAX-ACCESS        read-only
   STATUS            current
   DESCRIPTION       "The total probe round-trip time."
   ::= { hpicfIpSlaHistEntry 4}

hpicfIpSlaHistRTT2               OBJECT-TYPE
   SYNTAX            Unsigned32
   MAX-ACCESS        read-only
   STATUS            current
   DESCRIPTION       "The sum of the squares of round-trip time."
   ::= { hpicfIpSlaHistEntry 5}

hpicfIpSlaHistNumOfRTT           OBJECT-TYPE
   SYNTAX            Unsigned32
   MAX-ACCESS        read-only
   STATUS            current
   DESCRIPTION       "The number of RTTs that are successfully measured."
   ::= { hpicfIpSlaHistEntry 6}

hpicfIpSlaHistProbID             OBJECT-TYPE
   SYNTAX            Unsigned32
   MAX-ACCESS        read-only
   STATUS            current
   DESCRIPTION       "Probe ID number."
   ::= { hpicfIpSlaHistEntry 7}

hpicfIpSlaHistLastSuccProbTime   OBJECT-TYPE
   SYNTAX            Unsigned32
   MAX-ACCESS        read-only
   STATUS            current
   DESCRIPTION       "Last success probe time."
   ::= { hpicfIpSlaHistEntry 8}

hpicfIpSlaHistPacketLoss         OBJECT-TYPE
   SYNTAX            Unsigned32
   MAX-ACCESS        read-only
   STATUS            current
   DESCRIPTION       "The packet loss value during the jitter test."
   ::= { hpicfIpSlaHistEntry 9}

hpicfIpSlaHistSentPktNum         OBJECT-TYPE
   SYNTAX            Unsigned32
   MAX-ACCESS        read-only
   STATUS            current
   DESCRIPTION       "Number of packets sent to responder."
   ::= { hpicfIpSlaHistEntry 10}

hpicfIpSlaHistRecvdPktNum        OBJECT-TYPE
   SYNTAX            Unsigned32
   MAX-ACCESS        read-only
   STATUS            current
   DESCRIPTION       "Number of packets received from responder."
   ::= { hpicfIpSlaHistEntry 11}

hpicfIpSlaHistMinStoDPostv       OBJECT-TYPE
   SYNTAX            Unsigned32
   MAX-ACCESS        read-only
   STATUS            current
   DESCRIPTION       "The minimal positive jitter value recorded from
                      source to destination."
   ::= { hpicfIpSlaHistEntry 12}

hpicfIpSlaHistMaxStoDPostv       OBJECT-TYPE
   SYNTAX            Unsigned32
   MAX-ACCESS        read-only
   STATUS            current
   DESCRIPTION       "The maximum positive jitter value recorded from
                      source to destination."
   ::= { hpicfIpSlaHistEntry 13}

hpicfIpSlaHistNumOfPosSD         OBJECT-TYPE
   SYNTAX            Unsigned32
   MAX-ACCESS        read-only
   STATUS            current
   DESCRIPTION       "Number of times the source to destination jitter
                      has a positive value."
   ::= { hpicfIpSlaHistEntry 14}

hpicfIpSlaHistSumOfPosSD         OBJECT-TYPE
   SYNTAX            Unsigned32
   MAX-ACCESS        read-only
   STATUS            current
   DESCRIPTION       "The sum of positive jitter values recorded from
                      source to destination."
   ::= { hpicfIpSlaHistEntry 15}

hpicfIpSlaHistAvgStoDPostv       OBJECT-TYPE
   SYNTAX            Unsigned32
   MAX-ACCESS        read-only
   STATUS            current
   DESCRIPTION       "The average positive jitter value recorded from
                      source to destination."
   ::= { hpicfIpSlaHistEntry 16}

hpicfIpSlaHistSum2PositivesSD    OBJECT-TYPE
   SYNTAX            Unsigned32
   MAX-ACCESS        read-only
   STATUS            current
   DESCRIPTION       "The sum of square of positive jitter values recorded from
                      source to destination."
   ::= { hpicfIpSlaHistEntry 17}

hpicfIpSlaHistMinDtoSPostv       OBJECT-TYPE
   SYNTAX            Unsigned32
   MAX-ACCESS        read-only
   STATUS            current
   DESCRIPTION       "The minimal positive jitter value recorded from
                      destination to source."
   ::= { hpicfIpSlaHistEntry 18}

hpicfIpSlaHistMaxDtoSPostv       OBJECT-TYPE
   SYNTAX            Unsigned32
   MAX-ACCESS        read-only
   STATUS            current
   DESCRIPTION       "The maximum positive jitter value recorded from
                      destination to source."
   ::= { hpicfIpSlaHistEntry 19}

hpicfIpSlaHistNumOfPosDS         OBJECT-TYPE
   SYNTAX            Unsigned32
   MAX-ACCESS        read-only
   STATUS            current
   DESCRIPTION       "The positive jitter value recorded from
                      destination to source."
   ::= { hpicfIpSlaHistEntry 20}

hpicfIpSlaHistSumOfPosDS         OBJECT-TYPE
   SYNTAX            Unsigned32
   MAX-ACCESS        read-only
   STATUS            current
   DESCRIPTION        "The sum of positive jitter values recorded from
                       destination to source."
   ::= { hpicfIpSlaHistEntry 21}

hpicfIpSlaHistAvgDtoSPostv       OBJECT-TYPE
   SYNTAX            Unsigned32
   MAX-ACCESS        read-only
   STATUS            current
   DESCRIPTION       "The average positive jitter value recorded from
                      destination to source."
   ::= { hpicfIpSlaHistEntry 22}

hpicfIpSlaHistSum2PositivesDS    OBJECT-TYPE
   SYNTAX            Unsigned32
   MAX-ACCESS        read-only
   STATUS            current
   DESCRIPTION       "The sum of square of positive jitter values recorded
                      from destination-to-source."
   ::= { hpicfIpSlaHistEntry 23}

hpicfIpSlaHistMinStoDNegtv       OBJECT-TYPE
   SYNTAX            Unsigned32
   MAX-ACCESS        read-only
   STATUS            current
   DESCRIPTION       "The minimal negative jitter value recorded from
                      source to destination."
   ::= { hpicfIpSlaHistEntry 24}

hpicfIpSlaHistMaxStoDNegtv       OBJECT-TYPE
   SYNTAX            Unsigned32
   MAX-ACCESS        read-only
   STATUS            current
   DESCRIPTION       "The maximum negative jitter value recorded from
                      source to destination."
   ::= { hpicfIpSlaHistEntry 25}

hpicfIpSlaHistNumOfNegSD         OBJECT-TYPE
   SYNTAX            Unsigned32
   MAX-ACCESS        read-only
   STATUS            current
   DESCRIPTION       "The number of negative jitter values recorded from
                      source to destination."
   ::= { hpicfIpSlaHistEntry 26}

hpicfIpSlaHistSumOfNegSD         OBJECT-TYPE
   SYNTAX            Unsigned32
   MAX-ACCESS        read-only
   STATUS            current
   DESCRIPTION        "The sum of negative jitter values recorded from
                       source to destination."
   ::= { hpicfIpSlaHistEntry 27}

hpicfIpSlaHistAvgStoDNegtv       OBJECT-TYPE
   SYNTAX            Unsigned32
   MAX-ACCESS        read-only
   STATUS            current
   DESCRIPTION       "The average negative jitter value recorded from
                      source to destination."
   ::= { hpicfIpSlaHistEntry 28}

hpicfIpSlaHistSum2NegativesSD    OBJECT-TYPE
   SYNTAX            Unsigned32
   MAX-ACCESS        read-only
   STATUS            current
   DESCRIPTION       "The sum of square of negative jitter values recorded
                      from source to destination."
   ::= { hpicfIpSlaHistEntry 29}

hpicfIpSlaHistMinDtoSNegtv       OBJECT-TYPE
   SYNTAX            Unsigned32
   MAX-ACCESS        read-only
   STATUS            current
   DESCRIPTION       "The minimal negative jitter value recorded from
                      destination to source."
   ::= { hpicfIpSlaHistEntry 30}

hpicfIpSlaHistMaxDtoSNegtv       OBJECT-TYPE
   SYNTAX            Unsigned32
   MAX-ACCESS        read-only
   STATUS            current
   DESCRIPTION       "The maximum negative jitter value recorded from
                      destination to source."
   ::= { hpicfIpSlaHistEntry 31}

hpicfIpSlaHistNumOfNegDS         OBJECT-TYPE
   SYNTAX            Unsigned32
   MAX-ACCESS        read-only
   STATUS            current
   DESCRIPTION       "The number of negative jitter values recorded from
                      destination to source."
   ::= { hpicfIpSlaHistEntry 32}

hpicfIpSlaHistSumOfNegDS         OBJECT-TYPE
   SYNTAX            Unsigned32
   MAX-ACCESS        read-only
   STATUS            current
   DESCRIPTION       "The negative jitter value recorded from
                      destination to source."
   ::= { hpicfIpSlaHistEntry 33}

hpicfIpSlaHistAvgDtoSNegtv       OBJECT-TYPE
   SYNTAX            Unsigned32
   MAX-ACCESS        read-only
   STATUS            current
   DESCRIPTION       "The average negative jitter value recorded from
                      destination to source."
   ::= { hpicfIpSlaHistEntry 34}

hpicfIpSlaHistSum2NegativesDS    OBJECT-TYPE
   SYNTAX            Unsigned32
   MAX-ACCESS        read-only
   STATUS            current
   DESCRIPTION       "The negative jitter value recorded from
                      source to destination."
   ::= { hpicfIpSlaHistEntry 35}

hpicfIpSlaHistMinStoDDelay       OBJECT-TYPE
   SYNTAX            Unsigned32
   MAX-ACCESS        read-only
   STATUS            current
   DESCRIPTION       "The minimum delay recorded from
                      source to destination."
   ::= { hpicfIpSlaHistEntry 36}

hpicfIpSlaHistMaxStoDDelay       OBJECT-TYPE
   SYNTAX            Unsigned32
   MAX-ACCESS        read-only
   STATUS            current
   DESCRIPTION       "The maximum delay recorded from
                      source to destination."
   ::= { hpicfIpSlaHistEntry 37}

hpicfIpSlaHistSumStoDDelay       OBJECT-TYPE
   SYNTAX            Unsigned32
   MAX-ACCESS        read-only
   STATUS            current
   DESCRIPTION       "The sum of all delays recorded from
                      source to destination."
   ::= { hpicfIpSlaHistEntry 38}

hpicfIpSlaHistNumOfDelaySD       OBJECT-TYPE
   SYNTAX            Unsigned32
   MAX-ACCESS        read-only
   STATUS            current
   DESCRIPTION       "The number of delays from source to destination that are
                      successfully measured."
   ::= { hpicfIpSlaHistEntry 39}

hpicfIpSlaHistSum2DelaySD        OBJECT-TYPE
   SYNTAX            Unsigned32
   MAX-ACCESS        read-only
   STATUS            current
   DESCRIPTION       "The sum of squares of all delays recorded from
                      source to destination."
   ::= { hpicfIpSlaHistEntry 40}

hpicfIpSlaHistMinDtoSDelay       OBJECT-TYPE
   SYNTAX            Unsigned32
   MAX-ACCESS        read-only
   STATUS            current
   DESCRIPTION       "The minimum delay recorded from destination to source."
   ::= { hpicfIpSlaHistEntry 41}

hpicfIpSlaHistMaxDtoSDelay       OBJECT-TYPE
   SYNTAX            Unsigned32
   MAX-ACCESS        read-only
   STATUS            current
   DESCRIPTION       "The maximum delay recorded from destination to source."
   ::= { hpicfIpSlaHistEntry 42}

hpicfIpSlaHistNumOfDelayDS       OBJECT-TYPE
   SYNTAX            Unsigned32
   MAX-ACCESS        read-only
   STATUS            current
   DESCRIPTION       "The number of delays from destination to source that are
                      successfully measured."
   ::= { hpicfIpSlaHistEntry 43}

hpicfIpSlaHistSumDtoSDelay       OBJECT-TYPE
   SYNTAX            Unsigned32
   MAX-ACCESS        read-only
   STATUS            current
   DESCRIPTION       "The sum of all delays recorded from destination to source."
   ::= { hpicfIpSlaHistEntry 44}

hpicfIpSlaHistSum2DelayDS        OBJECT-TYPE
   SYNTAX            Unsigned32
   MAX-ACCESS        read-only
   STATUS            current
   DESCRIPTION       "The sum of squares of all delays recorded from
                      destination to source."
   ::= { hpicfIpSlaHistEntry 45}

hpicfIpSlaHistICPIF              OBJECT-TYPE
   SYNTAX            Unsigned32
   MAX-ACCESS        read-only
   STATUS            current
   DESCRIPTION       "The Calculated Planning Impairment Factor (ICPIF) value
                      for the type-specified test."
   ::= { hpicfIpSlaHistEntry 46}

hpicfIpSlaHistMOS                OBJECT-TYPE
   SYNTAX            Unsigned32
   MAX-ACCESS        read-only
   STATUS            current
   DESCRIPTION       "The Mean Opinion Score (MOS) value for the type-specified test.
                      The Value of this object is 100 times of the actual value."
   ::= { hpicfIpSlaHistEntry 47}

hpicfIpSlaHistAvgStoDDelay     OBJECT-TYPE
   SYNTAX            Unsigned32
   MAX-ACCESS        read-only
   STATUS            current
   DESCRIPTION       "The average one-way time from source to destination."
   ::= { hpicfIpSlaHistEntry 48}

hpicfIpSlaHistAvgDtoSDelay     OBJECT-TYPE
   SYNTAX            Unsigned32
   MAX-ACCESS        read-only
   STATUS            current
   DESCRIPTION       "The average one-way time from destination to source."
   ::= { hpicfIpSlaHistEntry 49}

--
-- IP SLA history summary Table
--
hpicfIpSlaHistSummTable OBJECT-TYPE
   SYNTAX            SEQUENCE OF HpicfIpSlaHistSummEntry
   MAX-ACCESS        not-accessible
   STATUS            current
   DESCRIPTION       "This table specifies the history summary of IP SLA result."
   ::= { hpicfIpSlaObjects 7 }

hpicfIpSlaHistSummEntry OBJECT-TYPE
   SYNTAX            HpicfIpSlaHistSummEntry
   MAX-ACCESS        not-accessible
   STATUS            current
   DESCRIPTION       "An entry on this table specifies the minimum, maximum
                      and the average time taken from source to destination
                      and vice versa."
   INDEX {
            hpicfIpSlaID,
            hpicfIpSlaHistSummIndx
         }
   ::= { hpicfIpSlaHistSummTable 1 }

   HpicfIpSlaHistSummEntry ::= SEQUENCE
   {
      hpicfIpSlaHistSummIndx           Integer32,
      hpicfIpSlaHistSummStartTime      Unsigned32,
      hpicfIpSlaHistSummStatus         Unsigned32,
      hpicfIpSlaHistSummRTT            Unsigned32,
      hpicfIpSlaHistSummResolvdIP      Unsigned32,
      hpicfIpSlaHistSummDescription    Unsigned32,
      hpicfIpSlaHistSummStoDDelay      Unsigned32,
      hpicfIpSlaHistSummDtoSDelay      Unsigned32
   }
hpicfIpSlaHistSummIndx           OBJECT-TYPE
   SYNTAX            Integer32 (1..50)
   MAX-ACCESS        not-accessible
   STATUS            current
   DESCRIPTION       "This is an index for history summary. Its value can vary
                      from 1 to 50."
   ::= { hpicfIpSlaHistSummEntry 1 }

hpicfIpSlaHistSummStartTime      OBJECT-TYPE
   SYNTAX            Unsigned32
   MAX-ACCESS        read-only
   STATUS            current
   DESCRIPTION       "Time at which the type-specified test was executed."
   ::= { hpicfIpSlaHistSummEntry 2}

hpicfIpSlaHistSummStatus         OBJECT-TYPE
   SYNTAX            Unsigned32
   MAX-ACCESS        read-only
   STATUS            current
   DESCRIPTION       "The status of the IP SLA test."
   ::= { hpicfIpSlaHistSummEntry 3}

hpicfIpSlaHistSummRTT            OBJECT-TYPE
   SYNTAX            Unsigned32
   MAX-ACCESS        read-only
   STATUS            current
   DESCRIPTION       "The round-trip time for a successfully measured test."
   ::= { hpicfIpSlaHistSummEntry 4}

hpicfIpSlaHistSummResolvdIP      OBJECT-TYPE
   SYNTAX            Unsigned32
   MAX-ACCESS        read-only
   STATUS            current
   DESCRIPTION       "Resolved IP address."
   ::= { hpicfIpSlaHistSummEntry 5}

hpicfIpSlaHistSummDescription    OBJECT-TYPE
   SYNTAX            Unsigned32
   MAX-ACCESS        read-only
   STATUS            current
   DESCRIPTION       "Error description."
   ::= { hpicfIpSlaHistSummEntry 6}

hpicfIpSlaHistSummStoDDelay      OBJECT-TYPE
   SYNTAX            Unsigned32
   MAX-ACCESS        read-only
   STATUS            current
   DESCRIPTION       "Source to destination delay."
   ::= { hpicfIpSlaHistSummEntry 7}

hpicfIpSlaHistSummDtoSDelay      OBJECT-TYPE
   SYNTAX            Unsigned32
   MAX-ACCESS        read-only
   STATUS            current
   DESCRIPTION       "Destination to source delay."
   ::= { hpicfIpSlaHistSummEntry 8}

--
-- IP SLA history aggregate Table
--
hpicfIpSlaHistAggrTable          OBJECT-TYPE
   SYNTAX            SEQUENCE OF HpicfIpSlaHistAggrEntry
   MAX-ACCESS        not-accessible
   STATUS            current
   DESCRIPTION       "This table specifies the aggregate value of IP SLA result.
                      The average value is calculating on last 25 probes.
                      Or the calculation will do on the number of probes
                      if the probe count is less than 25"
::= { hpicfIpSlaObjects 8 }

hpicfIpSlaHistAggrEntry          OBJECT-TYPE
   SYNTAX            HpicfIpSlaHistAggrEntry
   MAX-ACCESS        not-accessible
   STATUS            current
   DESCRIPTION       "An entry on this table specifies aggregate value of minimum,
                      maximum and the average time taken from source to destination
                      and vice versa."
   INDEX { hpicfIpSlaID }
::= { hpicfIpSlaHistAggrTable 1 }

HpicfIpSlaHistAggrEntry ::= SEQUENCE
   {
      hpicfIpSlaHistAggrMinRTT            Unsigned32,
      hpicfIpSlaHistAggrMaxRTT            Unsigned32,
      hpicfIpSlaHistAggrNumOfRTT          Unsigned32,
      hpicfIpSlaHistAggrAvgRTT            Unsigned32,
      hpicfIpSlaHistAggrTotalRTT          Unsigned32,
      hpicfIpSlaHistAggrRTT2              Unsigned32,
      hpicfIpSlaHistAggrFrstProbStTime    Unsigned32,
      hpicfIpSlaHistAggrProbFailReason    Unsigned32,
      hpicfIpSlaHistAggrPacketLoss        Unsigned32,
      hpicfIpSlaHistAggrSentPktNum        Unsigned32,
      hpicfIpSlaHistAggrRecvdPktNum       Unsigned32,
      hpicfIpSlaHistAggrMinStoDPostv      Unsigned32,
      hpicfIpSlaHistAggrMaxStoDPostv      Unsigned32,
      hpicfIpSlaHistAggrNumOfPosSD        Unsigned32,
      hpicfIpSlaHistAggrSumOfPosSD        Unsigned32,
      hpicfIpSlaHistAggrAvgStoDPostv      Unsigned32,
      hpicfIpSlaHistAggrSum2PostvSD       Unsigned32,
      hpicfIpSlaHistAggrMinDtoSPostv      Unsigned32,
      hpicfIpSlaHistAggrMaxDtoSPostv      Unsigned32,
      hpicfIpSlaHistAggrNumOfPosDS        Unsigned32,
      hpicfIpSlaHistAggrSumOfPosDS        Unsigned32,
      hpicfIpSlaHistAggrAvgDtoSPostv      Unsigned32,
      hpicfIpSlaHistAggrSum2PostvDS       Unsigned32,
      hpicfIpSlaHistAggrMinStoDNegtv      Unsigned32,
      hpicfIpSlaHistAggrMaxStoDNegtv      Unsigned32,
      hpicfIpSlaHistAggrNumOfNegSD        Unsigned32,
      hpicfIpSlaHistAggrSumOfNegSD        Unsigned32,
      hpicfIpSlaHistAggrAvgStoDNegtv      Unsigned32,
      hpicfIpSlaHistAggrSum2NegtvSD       Unsigned32,
      hpicfIpSlaHistAggrMinDtoSNegtv      Unsigned32,
      hpicfIpSlaHistAggrMaxDtoSNegtv      Unsigned32,
      hpicfIpSlaHistAggrNumOfNegDS        Unsigned32,
      hpicfIpSlaHistAggrSumOfNegDS        Unsigned32,
      hpicfIpSlaHistAggrAvgDtoSNegtv      Unsigned32,
      hpicfIpSlaHistAggrSum2NegtvDS       Unsigned32,
      hpicfIpSlaHistAggrMinStoDDelay      Unsigned32,
      hpicfIpSlaHistAggrMaxStoDDelay      Unsigned32,
      hpicfIpSlaHistAggrSumStoDDelay      Unsigned32,
      hpicfIpSlaHistAggrNumOfDelaySD      Unsigned32,
      hpicfIpSlaHistAggrSum2DelaySD       Unsigned32,
      hpicfIpSlaHistAggrMinDtoSDelay      Unsigned32,
      hpicfIpSlaHistAggrMaxDtoSDelay      Unsigned32,
      hpicfIpSlaHistAggrNumOfDelayDS      Unsigned32,
      hpicfIpSlaHistAggrSumDtoSDelay      Unsigned32,
      hpicfIpSlaHistAggrSum2DelayDS       Unsigned32,
      hpicfIpSlaHistAggrMinICPIF          Unsigned32,
      hpicfIpSlaHistAggrMaxICPIF          Unsigned32,
      hpicfIpSlaHistAggrMinMOS            Unsigned32,
      hpicfIpSlaHistAggrMaxMOS            Unsigned32
   }

hpicfIpSlaHistAggrMinRTT         OBJECT-TYPE
   SYNTAX            Unsigned32
   MAX-ACCESS        read-only
   STATUS            current
   DESCRIPTION       "The minimum round-trip time for the last 25 probes."
  ::= { hpicfIpSlaHistAggrEntry 1}

hpicfIpSlaHistAggrMaxRTT         OBJECT-TYPE
   SYNTAX            Unsigned32
   MAX-ACCESS        read-only
   STATUS            current
   DESCRIPTION       "The maximum round-trip time for the last 25 probes."
   ::= { hpicfIpSlaHistAggrEntry 2}

hpicfIpSlaHistAggrNumOfRTT       OBJECT-TYPE
   SYNTAX            Unsigned32
   MAX-ACCESS        read-only
   STATUS            current
   DESCRIPTION       "The number of RTTs that are successfully measured for
                      last 25 probes."
  ::= { hpicfIpSlaHistAggrEntry 3}

hpicfIpSlaHistAggrAvgRTT         OBJECT-TYPE
   SYNTAX            Unsigned32
   MAX-ACCESS        read-only
   STATUS            current
   DESCRIPTION       "The average round-trip time of last 25 probes."
  ::= { hpicfIpSlaHistAggrEntry 4}

hpicfIpSlaHistAggrTotalRTT       OBJECT-TYPE
   SYNTAX            Unsigned32
   MAX-ACCESS        read-only
   STATUS            current
   DESCRIPTION       "The total round-trip time of last 25 probes."
   ::= { hpicfIpSlaHistAggrEntry 5}

hpicfIpSlaHistAggrRTT2           OBJECT-TYPE
   SYNTAX            Unsigned32
   MAX-ACCESS        read-only
   STATUS            current
   DESCRIPTION       "The average of the sum of squares of RTTs for
                      the last 25 probes."
   ::= { hpicfIpSlaHistAggrEntry 6}

hpicfIpSlaHistAggrFrstProbStTime OBJECT-TYPE
   SYNTAX            Unsigned32
   MAX-ACCESS        read-only
   STATUS            current
   DESCRIPTION       "First probe start time."
   ::= { hpicfIpSlaHistAggrEntry  7}

hpicfIpSlaHistAggrProbFailReason OBJECT-TYPE
   SYNTAX            Unsigned32
   MAX-ACCESS        read-only
   STATUS            current
   DESCRIPTION       "Probe failure reason."
   ::= { hpicfIpSlaHistAggrEntry  8}

hpicfIpSlaHistAggrPacketLoss     OBJECT-TYPE
   SYNTAX            Unsigned32
   MAX-ACCESS        read-only
   STATUS            current
   DESCRIPTION       "The percentage of packet loss in last 25 probes."
   ::= { hpicfIpSlaHistAggrEntry  9}

hpicfIpSlaHistAggrSentPktNum     OBJECT-TYPE
   SYNTAX            Unsigned32
   MAX-ACCESS        read-only
   STATUS            current
   DESCRIPTION       "The total number of packets sent."
   ::= { hpicfIpSlaHistAggrEntry  10}

hpicfIpSlaHistAggrRecvdPktNum    OBJECT-TYPE
   SYNTAX            Unsigned32
   MAX-ACCESS        read-only
   STATUS            current
   DESCRIPTION       "The total number of packets received."
   ::= { hpicfIpSlaHistAggrEntry  11}

hpicfIpSlaHistAggrMinStoDPostv   OBJECT-TYPE
   SYNTAX            Unsigned32
   MAX-ACCESS        read-only
   STATUS            current
   DESCRIPTION       "The minimum positive jitter value from source to
                      destination for last 25 probes."
   ::= { hpicfIpSlaHistAggrEntry  12}

hpicfIpSlaHistAggrMaxStoDPostv   OBJECT-TYPE
   SYNTAX            Unsigned32
   MAX-ACCESS        read-only
   STATUS            current
   DESCRIPTION       "The maximum positive jitter value from source to
                      destination for last 25 probes."
   ::= { hpicfIpSlaHistAggrEntry  13}

hpicfIpSlaHistAggrNumOfPosSD     OBJECT-TYPE
   SYNTAX            Unsigned32
   MAX-ACCESS        read-only
   STATUS            current
   DESCRIPTION       "The number of times source to destination jitter value
                      became positive."
   ::= { hpicfIpSlaHistAggrEntry  14}

hpicfIpSlaHistAggrSumOfPosSD     OBJECT-TYPE
   SYNTAX            Unsigned32
   MAX-ACCESS        read-only
   STATUS            current
   DESCRIPTION       "The average of the sum of positive jitter value from
                      source to destination for last 25 probes."
   ::= { hpicfIpSlaHistAggrEntry  15}

hpicfIpSlaHistAggrAvgStoDPostv   OBJECT-TYPE
   SYNTAX            Unsigned32
   MAX-ACCESS        read-only
   STATUS            current
   DESCRIPTION       "The average of the positive jitter value from source to
                      destination for last 25 probes."
   ::= { hpicfIpSlaHistAggrEntry  16}

hpicfIpSlaHistAggrSum2PostvSD    OBJECT-TYPE
   SYNTAX            Unsigned32
   MAX-ACCESS        read-only
   STATUS            current
   DESCRIPTION       "The aggregate of square sum of positive jitter value
                      from source to destination for last 25 probes."
   ::= { hpicfIpSlaHistAggrEntry  17}

hpicfIpSlaHistAggrMinDtoSPostv   OBJECT-TYPE
   SYNTAX            Unsigned32
   MAX-ACCESS        read-only
   STATUS            current
   DESCRIPTION       "The minimum positive jitter value from destination
                      to source for last 25 probes."
   ::= { hpicfIpSlaHistAggrEntry  18}

hpicfIpSlaHistAggrMaxDtoSPostv   OBJECT-TYPE
   SYNTAX            Unsigned32
   MAX-ACCESS        read-only
   STATUS            current
   DESCRIPTION       "The maximum positive jitter value from destination
                      to source for last 25 probes."
   ::= { hpicfIpSlaHistAggrEntry  19}

hpicfIpSlaHistAggrNumOfPosDS     OBJECT-TYPE
   SYNTAX            Unsigned32
   MAX-ACCESS        read-only
   STATUS            current
   DESCRIPTION       "The number of times destination to source
                      jitter was positive."
   ::= { hpicfIpSlaHistAggrEntry  20}

hpicfIpSlaHistAggrSumOfPosDS     OBJECT-TYPE
   SYNTAX            Unsigned32
   MAX-ACCESS        read-only
   STATUS            current
   DESCRIPTION        "The sum of positive jitter value from destination
                       to source for last 25 probes."
   ::= { hpicfIpSlaHistAggrEntry  21}

hpicfIpSlaHistAggrAvgDtoSPostv   OBJECT-TYPE
   SYNTAX            Unsigned32
   MAX-ACCESS        read-only
   STATUS            current
   DESCRIPTION       "The sum of average positive jitter values from
                      destination to source for last 25 probes."
   ::= { hpicfIpSlaHistAggrEntry  22}

hpicfIpSlaHistAggrSum2PostvDS    OBJECT-TYPE
   SYNTAX            Unsigned32
   MAX-ACCESS        read-only
   STATUS            current
   DESCRIPTION       "The aggregate of square sum of positive jitter value
                      from destination to source for last 25 probes."
   ::= { hpicfIpSlaHistAggrEntry  23}

hpicfIpSlaHistAggrMinStoDNegtv   OBJECT-TYPE
   SYNTAX            Unsigned32
   MAX-ACCESS        read-only
   STATUS            current
   DESCRIPTION       "The minimum negative jitter value from source to
                      destination for last 25 probes."
   ::= { hpicfIpSlaHistAggrEntry  24}

hpicfIpSlaHistAggrMaxStoDNegtv   OBJECT-TYPE
   SYNTAX            Unsigned32
   MAX-ACCESS        read-only
   STATUS            current
   DESCRIPTION       "The maximum negative jitter value from source to
                      destination for last 25 probes."
   ::= { hpicfIpSlaHistAggrEntry  25}

hpicfIpSlaHistAggrNumOfNegSD     OBJECT-TYPE
   SYNTAX            Unsigned32
   MAX-ACCESS        read-only
   STATUS            current
   DESCRIPTION       "The number of times jitter value from source to
                      destination became negative."
   ::= { hpicfIpSlaHistAggrEntry  26}

hpicfIpSlaHistAggrSumOfNegSD     OBJECT-TYPE
   SYNTAX            Unsigned32
   MAX-ACCESS        read-only
   STATUS            current
   DESCRIPTION        "The sum of negative jitter value from source to
                       destination for last 25 probes."
   ::= { hpicfIpSlaHistAggrEntry  27}

hpicfIpSlaHistAggrAvgStoDNegtv   OBJECT-TYPE
   SYNTAX            Unsigned32
   MAX-ACCESS        read-only
   STATUS            current
   DESCRIPTION       "The average of the negative jitter value from source
                      to destination for last 25 probes."
   ::= { hpicfIpSlaHistAggrEntry  28}

hpicfIpSlaHistAggrSum2NegtvSD    OBJECT-TYPE
   SYNTAX            Unsigned32
   MAX-ACCESS        read-only
   STATUS            current
   DESCRIPTION       "The aggregate of square sum of negative jitter value
                      from source to destination for last 25 probes."
   ::= { hpicfIpSlaHistAggrEntry  29}

hpicfIpSlaHistAggrMinDtoSNegtv   OBJECT-TYPE
   SYNTAX            Unsigned32
   MAX-ACCESS        read-only
   STATUS            current
   DESCRIPTION       "The minimum negative jitter value from destination to
                      source for last 25 probes."
   ::= { hpicfIpSlaHistAggrEntry  30}

hpicfIpSlaHistAggrMaxDtoSNegtv   OBJECT-TYPE
   SYNTAX            Unsigned32
   MAX-ACCESS        read-only
   STATUS            current
   DESCRIPTION       "The maximum negative jitter value from destination
                      to source for last 25 probes."
   ::= { hpicfIpSlaHistAggrEntry  31}

hpicfIpSlaHistAggrNumOfNegDS     OBJECT-TYPE
   SYNTAX            Unsigned32
   MAX-ACCESS        read-only
   STATUS            current
   DESCRIPTION       "The number of times jitter value from destination
                      to source became negative."
   ::= { hpicfIpSlaHistAggrEntry  32}

hpicfIpSlaHistAggrSumOfNegDS     OBJECT-TYPE
   SYNTAX            Unsigned32
   MAX-ACCESS        read-only
   STATUS            current
   DESCRIPTION       "The sum of negative jitter value from destination
                      to source for last 25 probes."
   ::= { hpicfIpSlaHistAggrEntry  33}

hpicfIpSlaHistAggrAvgDtoSNegtv   OBJECT-TYPE
   SYNTAX            Unsigned32
   MAX-ACCESS        read-only
   STATUS            current
   DESCRIPTION       "The average of the negative jitter value from
                      destination to source for last 25 probes."
   ::= { hpicfIpSlaHistAggrEntry  34}

hpicfIpSlaHistAggrSum2NegtvDS    OBJECT-TYPE
   SYNTAX            Unsigned32
   MAX-ACCESS        read-only
   STATUS            current
   DESCRIPTION       "The aggregate of square sum of negative jitter value
                      from destination to source for last 25 probes."
   ::= { hpicfIpSlaHistAggrEntry  35}

hpicfIpSlaHistAggrMinStoDDelay   OBJECT-TYPE
   SYNTAX            Unsigned32
   MAX-ACCESS        read-only
   STATUS            current
   DESCRIPTION       "The minimum one-way time from source to destination
                      for last 25 probes."
   ::= { hpicfIpSlaHistAggrEntry  36}

hpicfIpSlaHistAggrMaxStoDDelay   OBJECT-TYPE
   SYNTAX            Unsigned32
   MAX-ACCESS        read-only
   STATUS            current
   DESCRIPTION       "The maximum one-way time from source to destination
                      for last 25 probes."
   ::= { hpicfIpSlaHistAggrEntry  37}

hpicfIpSlaHistAggrSumStoDDelay   OBJECT-TYPE
   SYNTAX            Unsigned32
   MAX-ACCESS        read-only
   STATUS            current
   DESCRIPTION       "The sum of one-way time from source to destination
                      for last 25 probes."
   ::= { hpicfIpSlaHistAggrEntry  38}

hpicfIpSlaHistAggrNumOfDelaySD   OBJECT-TYPE
   SYNTAX            Unsigned32
   MAX-ACCESS        read-only
   STATUS            current
   DESCRIPTION       "The number of times source to destination delay occurred
                      for the last 25 probes."
   ::= { hpicfIpSlaHistAggrEntry  39}

hpicfIpSlaHistAggrSum2DelaySD    OBJECT-TYPE
   SYNTAX            Unsigned32
   MAX-ACCESS        read-only
   STATUS            current
   DESCRIPTION       "The sum of squares of one-way delay from source
                      to destination for last 25 probes."
   ::= { hpicfIpSlaHistAggrEntry  40}

hpicfIpSlaHistAggrMinDtoSDelay   OBJECT-TYPE
   SYNTAX            Unsigned32
   MAX-ACCESS        read-only
   STATUS            current
   DESCRIPTION       "The minimum one-way delay from destination to source
                      for last 25 probes."
   ::= { hpicfIpSlaHistAggrEntry  41}

hpicfIpSlaHistAggrMaxDtoSDelay   OBJECT-TYPE
   SYNTAX            Unsigned32
   MAX-ACCESS        read-only
   STATUS            current
   DESCRIPTION       "The maximum one-way delay from destination to source
                      for last 25 probes."
   ::= { hpicfIpSlaHistAggrEntry  42}

hpicfIpSlaHistAggrNumOfDelayDS   OBJECT-TYPE
   SYNTAX            Unsigned32
   MAX-ACCESS        read-only
   STATUS            current
   DESCRIPTION       "The number of times destination to source delay occurred
                      for the last 25 probes."
   ::= { hpicfIpSlaHistAggrEntry  43}

hpicfIpSlaHistAggrSumDtoSDelay   OBJECT-TYPE
   SYNTAX            Unsigned32
   MAX-ACCESS        read-only
   STATUS            current
   DESCRIPTION       "The sum of one-way delay from destination to source for
                      last 25 probes."
   ::= { hpicfIpSlaHistAggrEntry  44}

hpicfIpSlaHistAggrSum2DelayDS    OBJECT-TYPE
   SYNTAX            Unsigned32
   MAX-ACCESS        read-only
   STATUS            current
   DESCRIPTION       "The sum of squares of one-way delay from destination
                      to source for last 25 probes."
   ::= { hpicfIpSlaHistAggrEntry  45}

hpicfIpSlaHistAggrMinICPIF       OBJECT-TYPE
   SYNTAX            Unsigned32
   MAX-ACCESS        read-only
   STATUS            current
   DESCRIPTION       "The minimum ICPIF value for last 25 probes."
   ::= { hpicfIpSlaHistAggrEntry  46}

hpicfIpSlaHistAggrMaxICPIF       OBJECT-TYPE
   SYNTAX            Unsigned32
   MAX-ACCESS        read-only
   STATUS            current
   DESCRIPTION       "The maximum ICPIF value for last 25 probes."
   ::= { hpicfIpSlaHistAggrEntry  47}

hpicfIpSlaHistAggrMinMOS         OBJECT-TYPE
   SYNTAX            Unsigned32
   MAX-ACCESS        read-only
   STATUS            current
   DESCRIPTION       "The minimum MOS value for last 25 probes.
                      The Value of this object is 100 times of the actual value."
   ::= { hpicfIpSlaHistAggrEntry  48}

hpicfIpSlaHistAggrMaxMOS         OBJECT-TYPE
   SYNTAX            Unsigned32
   MAX-ACCESS        read-only
   STATUS            current
   DESCRIPTION       "The maximum MOS value for last 25 probes.
                      The Value of this object is 100 times of the actual value."
   ::= { hpicfIpSlaHistAggrEntry  49}

--
-- IP SLA responder result Table
--
hpicfIpSlaRespResultTable        OBJECT-TYPE
   SYNTAX            SEQUENCE OF HpicfIpSlaRespResultEntry
   MAX-ACCESS        not-accessible
   STATUS            current
   DESCRIPTION       "This table specifies the IP SLA responder result parameters as
                      entries."
   ::= { hpicfIpSlaObjects 9 }

hpicfIpSlaRespResultEntry        OBJECT-TYPE
   SYNTAX            HpicfIpSlaRespResultEntry
   MAX-ACCESS        not-accessible
   STATUS            current
   DESCRIPTION       "An entry on this table specifies responder status and
                      number of packets received and responded."
   INDEX
   {
      hpicfIpSlaJitterRespType,
      hpicfIpSlaJitterRespAddress,
      hpicfIpSlaJitterRespL4Port,
      hpicfIpSlaJitterRespSrcAddress
   }
   ::= { hpicfIpSlaRespResultTable 1 }

   HpicfIpSlaRespResultEntry ::= SEQUENCE
   {
      hpicfIpSlaRespStatus          Unsigned32,
      hpicfIpSlaRespnumPktRcvd      Unsigned32,
      hpicfIpSlaRespNumPktRespnd    Unsigned32
   }
hpicfIpSlaRespStatus             OBJECT-TYPE
   SYNTAX            Unsigned32
   MAX-ACCESS        read-only
   STATUS            current
   DESCRIPTION       "The status of the responder."
   ::= { hpicfIpSlaRespResultEntry 1}

hpicfIpSlaRespnumPktRcvd         OBJECT-TYPE
   SYNTAX            Unsigned32
   MAX-ACCESS        read-only
   STATUS            current
   DESCRIPTION       "The number of packets received by the responder."
   ::= { hpicfIpSlaRespResultEntry 2}

hpicfIpSlaRespNumPktRespnd       OBJECT-TYPE
   SYNTAX            Unsigned32
   MAX-ACCESS        read-only
   STATUS            current
   DESCRIPTION       "The number of packets sent by the responder."
   ::= { hpicfIpSlaRespResultEntry 3}

--
-- IP SLA Responder objects for jitter
--
hpicfIpSlaJitterRespTable OBJECT-TYPE
   SYNTAX            SEQUENCE OF HpicfIpSlaJitterRespEntry
   MAX-ACCESS        not-accessible
   STATUS            current
   DESCRIPTION       "This table specifies IP SLA jitter responder parameters
                      as entries."
   ::= { hpicfIpSlaObjects 10 }

hpicfIpSlaJitterRespEntry OBJECT-TYPE
   SYNTAX            HpicfIpSlaJitterRespEntry
   MAX-ACCESS        not-accessible
   STATUS            current
   DESCRIPTION       "An entry on this table specifies the local IP address,
                      port number and row status corresponding to each SLA
                      responder config."
   INDEX
   {
      hpicfIpSlaJitterRespType,
      hpicfIpSlaJitterRespAddress,
      hpicfIpSlaJitterRespL4Port,
      hpicfIpSlaJitterRespSrcAddress
   }
   ::= { hpicfIpSlaJitterRespTable 1 }

   HpicfIpSlaJitterRespEntry ::= SEQUENCE
   {
      hpicfIpSlaJitterRespType            INTEGER,
      hpicfIpSlaJitterRespAddressType     InetAddressType,
      hpicfIpSlaJitterRespAddress         InetAddress,
      hpicfIpSlaJitterRespL4Port          InetPortNumber,
      hpicfIpSlaJitterRespSrcAddrType     InetAddressType,
      hpicfIpSlaJitterRespSrcAddress      InetAddress,
      hpicfIpSlaJitterRespRowStatus       RowStatus
   }

hpicfIpSlaJitterRespType OBJECT-TYPE
   SYNTAX  INTEGER
   {
      udpJitter(2),
      udpJitterVoIP(3)
   }
   MAX-ACCESS        not-accessible
   STATUS            current
   DESCRIPTION       "The SLA jitter responder type. The udpJitter and
                      udpJitterVoIP values calculate one-way delay, therefore
                      a timestamp has to be embedded while replying back.
                      This is one of the indexes for hpicfIpSlaJitterRespTable."
   ::= { hpicfIpSlaJitterRespEntry 1 }

hpicfIpSlaJitterRespAddressType OBJECT-TYPE
   SYNTAX            InetAddressType
   MAX-ACCESS        read-create
   STATUS            current
   DESCRIPTION       "SLA jitter responder IP address type."
   ::= { hpicfIpSlaJitterRespEntry 2 }

hpicfIpSlaJitterRespAddress OBJECT-TYPE
   SYNTAX            InetAddress
   MAX-ACCESS        not-accessible
   STATUS            current
   DESCRIPTION       "The local IP address to which the responder is bound.
                      This is one of the indexes for hpicfIpSlaJitterRespTable."
  ::= { hpicfIpSlaJitterRespEntry 3 }

hpicfIpSlaJitterRespL4Port OBJECT-TYPE
   SYNTAX            InetPortNumber
   MAX-ACCESS        not-accessible
   STATUS            current
   DESCRIPTION       "L4 port number on hpicfIpSlaJitterRespAddress where the
                      responder listens for probe packets from SLA source.
                      This is one of the indexes for hpicfIpSlaJitterRespTable.
                      The allowed range is 1024 to 65535."
   ::= { hpicfIpSlaJitterRespEntry 4 }

hpicfIpSlaJitterRespSrcAddrType  OBJECT-TYPE
   SYNTAX            InetAddressType
   MAX-ACCESS        read-create
   STATUS            current
   DESCRIPTION       "SLA jitter responder source IP address type."
   ::= { hpicfIpSlaJitterRespEntry 5 }

hpicfIpSlaJitterRespSrcAddress      OBJECT-TYPE
   SYNTAX            InetAddress
   MAX-ACCESS        not-accessible
   STATUS            current
   DESCRIPTION       "The source IP address to which the responder is responding."
  ::= { hpicfIpSlaJitterRespEntry 6 }

hpicfIpSlaJitterRespRowStatus OBJECT-TYPE
   SYNTAX            RowStatus
   MAX-ACCESS        read-create
   STATUS            current
   DESCRIPTION       "SLA jitter responder row status."
   ::= { hpicfIpSlaJitterRespEntry 7}

--*************************************************************
--*    hpicfIpSlaNotifications
--*************************************************************

hpicfIpSlaThresholdexceeded  NOTIFICATION-TYPE
   OBJECTS
   {
      hpicfIpSlaThrUpper
   }
   STATUS            current
   DESCRIPTION       "This notification is generated when the metric calculated
                      from the SLA result exceeds the configured threshold value.
                      The hpicfIpSlaThrUpper is not applicable when
                      hpicfIpSlaThrMetricType is set to packetLoss or
                      testCompletion."
  ::= { hpicfIpSlaNotifications 1 }

hpicfIpSlaTestCompletion  NOTIFICATION-TYPE
   OBJECTS
   {
      hpicfIpSlaThrType
   }
   STATUS            current
   DESCRIPTION       "This notification is generated when the SLA test is
                      completed either by reaching stopTime or
                      hpicfIpSlaAttrNumPkts. This notification is sent only
                      when the action type is set to trap or trap-log."
  ::= { hpicfIpSlaNotifications 2 }

hpicfIpSlaThresholdPktLoss  NOTIFICATION-TYPE
   OBJECTS
   {
      hpicfIpSlaThrCount
   }
   STATUS            current
   DESCRIPTION       "This notification is generated when SLA test probe reply
                      packets are lost consecutively for the configured number
                      of hpicfIpSlaThrCount. This notification is sent only when
                      the action type is set to trap or trap-log."
  ::= { hpicfIpSlaNotifications 3 }

------------------------------------------------------------------------------
-- Conformance Information
------------------------------------------------------------------------------

hpicfIpSlaGroups        OBJECT IDENTIFIER    ::= { hpicfIpSlaConformance 1 }
hpicfIpSlaCompliances   OBJECT IDENTIFIER    ::= { hpicfIpSlaConformance 2 }

-- compliance statements

hpicfIpSlaCompliance MODULE-COMPLIANCE
   STATUS            deprecated
   DESCRIPTION       "The compliance statement for HP switches that support IP SLA."
   MODULE            -- this module
   MANDATORY-GROUPS
   {
      hpicfIpSlaGroup,
      hpicfIpSlaAttrGroup,
      hpicfIpSlaThrGroup,
      hpicfIpSlaRespGroup,
      hpicfIpSlaNotificationsGroup
   }
   ::= { hpicfIpSlaCompliances 1 }

hpicfIpSlaCompliance1 MODULE-COMPLIANCE
   STATUS            current
   DESCRIPTION       "The compliance statement for HP switches that support IP SLA."
   MODULE            -- this module
   MANDATORY-GROUPS
   {
      hpicfIpSlaGroup,
      hpicfIpSlaAttrGroup1,
      hpicfIpSlaThrGroup,
      hpicfIpSlaRespGroup,
      hpicfIpSlaNotificationsGroup,
      hpicfIpSlaMsgGroup,
      hpicfIpSlaHistGroup,
      hpicfIpSlaHistSummGroup,
      hpicfIpSlaHistAggrGroup,
      hpicfIpSlaRespResultGroup,
      hpicfIpSlaJitterRespGroup
   }
   ::= { hpicfIpSlaCompliances 2 }
-- MIB Groupings

hpicfIpSlaGroup OBJECT-GROUP
   OBJECTS
   {
      hpicfIpSlaType,
      hpicfIpSlaAdminState,
      hpicfIpSlaSourceAddressType,
      hpicfIpSlaSourceAddress,
      hpicfIpSlaL4SourcePort,
      hpicfIpSlaSourceInterface,
      hpicfIpSlaDestAddressType,
      hpicfIpSlaDestAddress,
      hpicfIpSlaL4DestPort,
      hpicfIpSlaRowStatus
  }
   STATUS            current
   DESCRIPTION       "A mandatory group with a set of IP SLA objects."
   ::= { hpicfIpSlaGroups 1 }

hpicfIpSlaAttrGroup OBJECT-GROUP
   OBJECTS
   {
      hpicfIpSlaSchedStartTime,
      hpicfIpSlaSchedEndTime,
      hpicfIpSlaSchedFreq,
      hpicfIpSlaSchedRepeat,
      hpicfIpSlaAttrTOS,
      hpicfIpSlaAttrHistorySize,
      hpicfIpSlaAttrPayloadSize,
      hpicfIpSlaAttrNumPkts,
      hpicfIpSlaAttrPktInterval,
      hpicfIpSlaAttrRowStatus
   }
   STATUS            deprecated
   DESCRIPTION       "A group with a set of IP SLA attribute objects."
   ::= { hpicfIpSlaGroups 2 }

hpicfIpSlaThrGroup OBJECT-GROUP
   OBJECTS
   {
      hpicfIpSlaThrUpper,
      hpicfIpSlaThrLower,
      hpicfIpSlaThrType,
      hpicfIpSlaThrCount,
      hpicfIpSlaThrAction,
      hpicfIpSlaThrRowStatus
   }
   STATUS            current
   DESCRIPTION       "A group with a set of IP SLA threshold objects."
   ::= { hpicfIpSlaGroups 3 }

hpicfIpSlaRespGroup OBJECT-GROUP
   OBJECTS
   {
      hpicfIpSlaRespAddressType,
      hpicfIpSlaRespRowStatus
   }
   STATUS            current
   DESCRIPTION       "A group with a set of IP SLA responder objects."
   ::= { hpicfIpSlaGroups 4 }

hpicfIpSlaNotificationsGroup NOTIFICATION-GROUP
   NOTIFICATIONS
   {
      hpicfIpSlaThresholdexceeded,
      hpicfIpSlaTestCompletion,
      hpicfIpSlaThresholdPktLoss
   }
   STATUS            current
   DESCRIPTION       "A collection of IP SLA source and responder notifications
                      objects."
   ::= { hpicfIpSlaGroups 5 }

hpicfIpSlaMsgGroup OBJECT-GROUP
   OBJECTS
   {
      hpicfIpSlaMsgLastProbeRcvd,
      hpicfIpSlaMsgLastClrRec,
      hpicfIpSlaMsgSuccProbe,
      hpicfIpSlaMsgIntErr,
      hpicfIpSlaMsgLocIntfDown,
      hpicfIpSlaMsgResTimeout,
      hpicfIpSlaMsgDNSFormatErr,
      hpicfIpSlaMsgServerFaild,
      hpicfIpSlaMsgDomainNotExist,
      hpicfIpSlaMsgFunctnNotImpl,
      hpicfIpSlaMsgServerRefusd,
      hpicfIpSlaMsgNameNotExist,
      hpicfIpSlaMsgRRsetNotExist,
      hpicfIpSlaMsgServerNotInZone,
      hpicfIpSlaMsgNameNotInZone,
      hpicfIpSlaMsgDHCPFaildResln,
      hpicfIpSlaMsgOffrNotRecvd,
      hpicfIpSlaMsgNACKRecvd,
      hpicfIpSlaMsgThrHitRTT,
      hpicfIpSlaMsgStatus,
      hpicfIpSlaMsgNxtSched,
      hpicfIpSlaMsgThrHitPostvSDAvg,
      hpicfIpSlaMsgThrHitPostvDSAvg,
      hpicfIpSlaMsgThrHitOneWayDSAvg,
      hpicfIpSlaMsgThrHitOneWaySDAvg,
      hpicfIpSlaMsgThrHitAvgICPIF,
      hpicfIpSlaMsgThrHitAvgMOS,
      hpicfIpSlaMsgNameServUnreach,
      hpicfIpSlaMsgDHCPReleaseErr,
      hpicfIpSlaMsgThrHitPktLoss,
      hpicfIpSlaMsgDstUnreach,
      hpicfIpSlaMsgProbeSkpd,
      hpicfIpSlaMsgDNSResolnFailed,
      hpicfIpSlaMsgNoRoutetoTgt,
      hpicfIpSlaMsgUnbleToConctHost,
      hpicfIpSlaMsgSuccConnection,
      hpicfIpSlaMsgPossTrailDropped,
      hpicfIpSlaMsgNoRespFrmTgt,
      hpicfIpSlaMsgProbeRespRecvd
   }
   STATUS            current
   DESCRIPTION       "A mandatory group with a set of IP SLA result objects."
   ::= { hpicfIpSlaGroups 6 }
hpicfIpSlaHistGroup OBJECT-GROUP
   OBJECTS
   {
      hpicfIpSlaHistMinRTT,
      hpicfIpSlaHistMaxRTT,
      hpicfIpSlaHistAvgRTT,
      hpicfIpSlaHistTotalRTT,
      hpicfIpSlaHistRTT2,
      hpicfIpSlaHistNumOfRTT,
      hpicfIpSlaHistProbID,
      hpicfIpSlaHistLastSuccProbTime,
      hpicfIpSlaHistPacketLoss,
      hpicfIpSlaHistSentPktNum,
      hpicfIpSlaHistRecvdPktNum,
      hpicfIpSlaHistMinStoDPostv,
      hpicfIpSlaHistMaxStoDPostv,
      hpicfIpSlaHistNumOfPosSD,
      hpicfIpSlaHistSumOfPosSD,
      hpicfIpSlaHistAvgStoDPostv,
      hpicfIpSlaHistSum2PositivesSD,
      hpicfIpSlaHistMinDtoSPostv,
      hpicfIpSlaHistMaxDtoSPostv,
      hpicfIpSlaHistNumOfPosDS,
      hpicfIpSlaHistSumOfPosDS,
      hpicfIpSlaHistAvgDtoSPostv,
      hpicfIpSlaHistSum2PositivesDS,
      hpicfIpSlaHistMinStoDNegtv,
      hpicfIpSlaHistMaxStoDNegtv,
      hpicfIpSlaHistNumOfNegSD,
      hpicfIpSlaHistSumOfNegSD,
      hpicfIpSlaHistAvgStoDNegtv,
      hpicfIpSlaHistSum2NegativesSD,
      hpicfIpSlaHistMinDtoSNegtv,
      hpicfIpSlaHistMaxDtoSNegtv,
      hpicfIpSlaHistNumOfNegDS,
      hpicfIpSlaHistSumOfNegDS,
      hpicfIpSlaHistAvgDtoSNegtv,
      hpicfIpSlaHistSum2NegativesDS,
      hpicfIpSlaHistMinStoDDelay,
      hpicfIpSlaHistMaxStoDDelay,
      hpicfIpSlaHistSumStoDDelay,
      hpicfIpSlaHistNumOfDelaySD,
      hpicfIpSlaHistSum2DelaySD,
      hpicfIpSlaHistMinDtoSDelay,
      hpicfIpSlaHistMaxDtoSDelay,
      hpicfIpSlaHistNumOfDelayDS,
      hpicfIpSlaHistSumDtoSDelay,
      hpicfIpSlaHistSum2DelayDS,
      hpicfIpSlaHistICPIF,
      hpicfIpSlaHistMOS,
      hpicfIpSlaHistAvgStoDDelay,
      hpicfIpSlaHistAvgDtoSDelay

   }
   STATUS            current
   DESCRIPTION       "A mandatory group with a set of IP SLA history objects."
   ::= { hpicfIpSlaGroups 7 }
hpicfIpSlaHistSummGroup OBJECT-GROUP
   OBJECTS
   {
      hpicfIpSlaHistSummStartTime,
      hpicfIpSlaHistSummStatus,
      hpicfIpSlaHistSummRTT,
      hpicfIpSlaHistSummResolvdIP,
      hpicfIpSlaHistSummDescription,
      hpicfIpSlaHistSummStoDDelay,
      hpicfIpSlaHistSummDtoSDelay
   }
   STATUS            current
   DESCRIPTION       "A mandatory group with a set of IP SLA history
                      summary objects."
   ::= { hpicfIpSlaGroups 8 }

hpicfIpSlaAttrGroup1 OBJECT-GROUP
   OBJECTS
   {
      hpicfIpSlaSchedStartTime,
      hpicfIpSlaSchedEndTime,
      hpicfIpSlaSchedFreq,
      hpicfIpSlaSchedRepeat,
      hpicfIpSlaAttrTOS,
      hpicfIpSlaAttrHistorySize,
      hpicfIpSlaAttrPayloadSize,
      hpicfIpSlaAttrNumPkts,
      hpicfIpSlaAttrPktInterval,
      hpicfIpSlaAttrRowStatus,
      hpicfIpSlaAttrCodecType,
      hpicfIpSlaAttrAdvntgFactr
   }
   STATUS            current
   DESCRIPTION       "A group with a set of IP SLA attribute objects."
   ::= { hpicfIpSlaGroups 9 }

hpicfIpSlaHistAggrGroup OBJECT-GROUP
   OBJECTS
   {
      hpicfIpSlaHistAggrMinRTT,
      hpicfIpSlaHistAggrMaxRTT,
      hpicfIpSlaHistAggrNumOfRTT,
      hpicfIpSlaHistAggrAvgRTT,
      hpicfIpSlaHistAggrTotalRTT,
      hpicfIpSlaHistAggrRTT2,
      hpicfIpSlaHistAggrFrstProbStTime,
      hpicfIpSlaHistAggrProbFailReason,
      hpicfIpSlaHistAggrPacketLoss,
      hpicfIpSlaHistAggrSentPktNum,
      hpicfIpSlaHistAggrRecvdPktNum,
      hpicfIpSlaHistAggrMinStoDPostv,
      hpicfIpSlaHistAggrMaxStoDPostv,
      hpicfIpSlaHistAggrNumOfPosSD,
      hpicfIpSlaHistAggrSumOfPosSD,
      hpicfIpSlaHistAggrAvgStoDPostv,
      hpicfIpSlaHistAggrSum2PostvSD,
      hpicfIpSlaHistAggrMinDtoSPostv,
      hpicfIpSlaHistAggrMaxDtoSPostv,
      hpicfIpSlaHistAggrNumOfPosDS,
      hpicfIpSlaHistAggrSumOfPosDS,
      hpicfIpSlaHistAggrAvgDtoSPostv,
      hpicfIpSlaHistAggrSum2PostvDS,
      hpicfIpSlaHistAggrMinStoDNegtv,
      hpicfIpSlaHistAggrMaxStoDNegtv,
      hpicfIpSlaHistAggrNumOfNegSD,
      hpicfIpSlaHistAggrSumOfNegSD,
      hpicfIpSlaHistAggrAvgStoDNegtv,
      hpicfIpSlaHistAggrSum2NegtvSD,
      hpicfIpSlaHistAggrMinDtoSNegtv,
      hpicfIpSlaHistAggrMaxDtoSNegtv,
      hpicfIpSlaHistAggrNumOfNegDS,
      hpicfIpSlaHistAggrSumOfNegDS,
      hpicfIpSlaHistAggrAvgDtoSNegtv,
      hpicfIpSlaHistAggrSum2NegtvDS,
      hpicfIpSlaHistAggrMinStoDDelay,
      hpicfIpSlaHistAggrMaxStoDDelay,
      hpicfIpSlaHistAggrSumStoDDelay,
      hpicfIpSlaHistAggrNumOfDelaySD,
      hpicfIpSlaHistAggrSum2DelaySD,
      hpicfIpSlaHistAggrMinDtoSDelay,
      hpicfIpSlaHistAggrMaxDtoSDelay,
      hpicfIpSlaHistAggrNumOfDelayDS,
      hpicfIpSlaHistAggrSumDtoSDelay,
      hpicfIpSlaHistAggrSum2DelayDS,
      hpicfIpSlaHistAggrMinICPIF,
      hpicfIpSlaHistAggrMaxICPIF,
      hpicfIpSlaHistAggrMinMOS,
      hpicfIpSlaHistAggrMaxMOS
   }
   STATUS            current
   DESCRIPTION       "A mandatory group with a set of IP SLA aggregate result
                      summary objects."
::= { hpicfIpSlaGroups 10 }
hpicfIpSlaRespResultGroup OBJECT-GROUP
   OBJECTS
   {
      hpicfIpSlaRespStatus,
      hpicfIpSlaRespnumPktRcvd,
      hpicfIpSlaRespNumPktRespnd

   }
   STATUS            current
   DESCRIPTION       "A mandatory group with a set of IP SLA responder objects."
   ::= { hpicfIpSlaGroups 11 }

hpicfIpSlaJitterRespGroup OBJECT-GROUP
   OBJECTS
   {
      hpicfIpSlaJitterRespAddressType,
      hpicfIpSlaJitterRespSrcAddrType,
      hpicfIpSlaJitterRespRowStatus
   }
   STATUS            current
   DESCRIPTION       "A group with a set of IP SLA jitter responder objects."
   ::= { hpicfIpSlaGroups 12 }
END
