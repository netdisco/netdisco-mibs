-- =============================================================================
-- Copyright (c) 2010-2014 Hewlett-Packard Development Company, L.P.
--
-- Description:
--   The file defines a MIB to provide WLAN configuration information.
-- Reference:
-- Version: V3.2
-- History:
--   V1.0 2006-05-10 Initial version, created by shiyang (Richard)
--   V1.1 2007-02-01 modified by xingjichen(Daniel)
--        Added hpnicfDot11RadioIntfConfigTable,hpnicfDot11RadioIntfBindTable,
--        hpnicfDot11StaKeepALiveTimerIntvl,hpnicfDot11StaIdleTimerIntvl,
--        hpnicfDot11BroadcastProbeReply.
--   V1.2 2007-04-27 modified by shiyang(Richard)
--        Replace hpnicfDot11UnicastCipherKeyIndex, hpnicfDot11UnicastCipherKey,
--        hpnicfDot11BroadcastCipherKeyIndex and hpnicfDot11BroadcastCipherKey
--        with hpnicfDot11CipherKeyIndex, hpnicfDot11CipherKey as per CLI change.
--        Delete hpnicfDot11MaxTxLifetime as per CLI change.
--        Add hpnicfDot11GlobalCountryCode,hpnicfDot11APScanMode.
--        hpnicfDot11ACCtrlTunnelSecSupport and hpnicfDot11ACDataTunnelSecSupport.
--        Move hpnicfDot11StaKeepALiveTimerIntvl,hpnicfDot11StaIdleTimerIntvl
--        and so on to hpnicfDot11GlobeConfigGroup.
--        Split hpnicfDot11ServicePolicyTable into hpnicfDot11ServicePolicyTable
--        and hpnicfDot11ServicePolicyExtTable.
--        For hpnicfDot11SecurityCiphers node,update its description for case of
--        value equals to zero.
--   V1.3 2007-06-19 modified by Vikas K
--        Add new table of hpnicfDot11DataRateConfigTable for AP Configuration
--        Group.
--        Add new node of hpnicfDot11APName for hpnicfDot11APTemplateTable.
--        Modify the hpnicfDot11APScanMode from read-only to read-write.
--        Add undo functionality to node hpnicfDot11WlanInfBindingID and
--        hpnicfDot11Description.
--        Add hpnicfDot11StatisInterv to the hpnicfDot11APTemplateTable.
--   V1.4 2007-10-9 modified by Jagan K
--        Add new table hpnicfDot11WlanBssIfTable for WLAN BSS interface
--        configuration.
--        Add new table hpnicfDot11WlanEssIfTable for WLAN ESS interface
--        configuration.
--        Add new table hpnicfDot11WlanEthernetIfTable for WLAN Ethernet interface
--        configuration.
--   V1.5 2007-12-21 modified by wanghao (Kumar)
--        Add hpnicfDot11ACAutoAPSupport, hpnicfDot11AutoAPName,
--        hpnicfDot11PersistentName to hpnicfDot11GlobeConfigGroup
--        Add hpnicfDot11ClientMaxCount to hpnicfDot11ServicePolicyTable
--        Add hpnicfDot11APBroadcastProbeReply, hpnicfDot11StaIdleTimerInterv,
--        hpnicfDot11StaKeepAliveTimerInterv, hpnicfDot11APCir, hpnicfDot11APCbs
--        to hpnicfDot11APTemplateTable.
--   V1.6 2008-02-25 modified by wanghao (Kumar)
--        Add hpnicfDot11RdoClientMaxCount to hpnicfDot11RadioPolicyTable.
--   V1.7 2008-04-01 modified by wangbin
--        Add hpnicfDot11PortSecurityTable to hpnicfDot11InterfaceConfigGroup.
--        Add hpnicfDot11PortSecurityMode, hpnicfDot11SecurityUserLoginTxKeyType,
--        hpnicfDot11SecurityPskKeyMode, hpnicfDot11SecurityPskKeyString
--        to hpnicfDot11PortSecurityTable.
--   V1.8 2008-08-01 modified by ChangHuifeng
--        Add hpnicfDot11ACBackupGroup and
--        hpnicfDot11RadioElementConfigGroup.
--        Add hpnicfDot11WlanMeshIfTable to hpnicfDot11InterfaceConfigGroup.
--        Add hpnicfDot11APPriorityLevel and hpnicfDot11APElementID to
--        hpnicfDot11APTemplateTable.
--        Add hpnicfDot11CfgRdElementID to hpnicfDot11RadioToConfigTable.
--        Add hpnicfDot11APDevDetectEnable to hpnicfDot11APTemplateEntry.
--        Obsolete hpnicfDot11StatisInterv
--        Change default value of hpnicfDot11APScanMode to passive.
--        Change units of hpnicfDot11BeaconInterval and
--        hpnicfDot11RadioCfgBeaconIntvl to TU.
--        Remove default value of hpnicfDot11SSIDEncryptionMode.
--        Change MAC-ACCESS of objects in hpnicfDot11RadioToConfigTable
--        from read-create to read-write.
--        Change name of hpnicfDot11IWlanEssRowStatus to hpnicfDot11WlanEssRowStatus.
--        Change description of hpnicfDot11PortSecurityTable.
--   V1.9 2008-11-07 modified by Wang Lu and Li Yugang
--        Add hpnicfDot11IntfTrapThreshold to hpnicfDot11GlobeConfigGroup
--        Add hpnicfDot11SPInCirMode, hpnicfDot11SPInCirValue, hpnicfDot11SPOutCirMode,
--        hpnicfDot11SPOutCirValue to hpnicfDot11ServicePolicyTable
--        Add hpnicfDot11CfgWorkMode to hpnicfDot11RadioToConfigTable
--        Add hpnicfDot11RadioCfgWorkMode to hpnicfDot11RadioIntfConfigTable.
--        Add new traps hpnicfDot11CfgCipherChange and hpnicfDot11CfgPSKChange.
--        Add hpnicfDot11MonitorInterval, hpnicfDot11SampleInterval,
--        hpnicfDot11ChnlSwitChkInterval, hpnicfDot11APUserUplimit,
--        hpnicfDot11APL2IsolateEnable to hpnicfDot11GlobeConfigGroup.
--        Add hpnicfDot11RadioCfgOnly11gEnable to hpnicfDot11RadioIntfConfigTable.
--        Add hpnicfDot11RadioWDSTable to hpnicfDot11RadioElementConfigGroup.
--   V2.0 2009-03-20 modified by caizibin
--        Add value ext(6) to hpnicfDot11PortSecurityMode
--   V2.1 2009-05-07 modified by Li Yugang, Wang Shaojie, Jin Yi
--        Add hpnicfDot11APBSSIDSupportNum, hpnicfDot11APLastUpdateStatTime,
--        hpnicfDot11APDoSProtectEnable, hpnicfDot11MaxAPPerIf to
--        hpnicfDot11GlobeConfigGroup.
--        Add hpnicfDot11WlanInfPVID to hpnicfDot11ServicePolicyTable.
--        Add hpnicfDot11CipherKeyType to hpnicfDot11ServicePolicyExtTable.
--        Add hpnicfDot11CfgPwrAttValue to hpnicfDot11RadioToConfigTable.
--        Add new table hpnicfDot11APSysInfoSetTable to hpnicfDot11APConfigGroup.
--        Add hpnicfDot11SSIDWepIDConflictTrap to hpnicfDot11CfgNotifications.
--        Add new table hpnicfDot11CfgTrapVarObjects to hpnicfDot11CfgNotifyGroup.
--   V2.2 2009-07-29 modified by Heziqi
--        Add new node hpnicfDot11ServiceSetVlanId for hpnicfDot11APServiceSetTable.
--        Add hpnicfDot11UplinkTrackId to hpnicfDot11GlobeConfigGroup.
--        Add hpnicfDot11APLimitTable.
--        Change description of hpnicfDot11StaKeepALiveTimerIntvl.
--        Add new node hpnicfDot11RadioTxArithmetic for HpnicfDot11RadioToConfigTable.
--   V2.3 2009-07-29 modified by Jinyi
--        Add new table hpnicfDot11APIfSetTable
--   V2.4 2009-12-01 modified by Wang Shaojie
--        Add new node hpnicfDot11APGetIPMethod for hpnicfDot11APTemplateTable.
--        Add new group hpnicfDot11CfgTrapConfigGroup.
--        Add new table hpnicfDot11CfgSwitchTrapTable to hpnicfDot11CfgTrapConfigGroup.
--        Add new node hpnicfDot11BeaconIntervalMs to hpnicfDot11RadioPolicyTable.
--        Add new node hpnicfDot11SPInCirStaticValue, hpnicfDot11SPOutCirStaticValue
--        to hpnicfDot11ServicePolicyTable.
--        Modify description of hpnicfDot11SecurityCiphers.
--        Add new node hpnicfDot11StatisIntervMode to hpnicfDot11APTemplateTable.
--        Modify SYNTAX of hpnicfDot11APWorkMode.
--        Modify STATUS of hpnicfDot11StatisInterv.
--        Add new node hpnicfDot11SmartRateSet to hpnicfDot11DataRateConfigTable.
--        2010-02-22 modified by Wang Chunsheng
--        Add new node hpnicfDot11CfgChannelLockStat, hpnicfDot11CfgPowerLockStat,
--        hpnicfDot11CfgLBRdGroupId, hpnicfDot11CfgRRMSDRdGroupId to hpnicfDot11RadioToConfigTable.
--        2010-03-15 modified by Wang Lu
--        Add hpnicfDot11RtCollectSwitch, hpnicfDot11RglCollectIntvl, and
--        hpnicfDot11RtCollectIntvl to hpnicfDot11GlobeConfigGroup
--        Add hpnicfDot11SPIsolate to hpnicfDot11ServicePolicyTable
--        Add hpnicfDot11APServiceVlanTable, hpnicfDot11RadioConfigTable,
--        hpnicfDot11RadioPolicyExtTable and hpnicfDot11RadioSSIDCfgTable
--        Remove hpnicfDot11CfgTrapConfigGroup
--        Add hpnicfDot11SrvPortSecurityTable
--        2010-06-01 Modified by Wang Shaojie, Yin Junjie
--        Add hpnicfDot11RCApPowerLevel, hpnicfDot11RCDynamicChlState,
--        hpnicfDot11RCDynamicPowerState to hpnicfDot11RadioConfigTable.
--        Add hpnicfDot11APSerialIDTable
--        Add hpnicfDot11APSTVlanTable
--        2010-07-08 Modified the index of hpnicfDot11APSysInfoSetTable by jinyi
--        2010-08-05 Modified by Yin Junjie
--        Add new table hpnicfDot11SrvPolicyExtendTable
--        Add hpnicfDot11SPEnable to hpnicfDot11SrvPolicyExtendTable
--        2010-09-02 Modified by Yin Junjie
--        Add new node hpnicfDot11AdjIntfTrapThreshold
--        to hpnicfDot11GlobeConfigGroup
--        Add hpnicfDot11RCRadioStatus to hpnicfDot11RadioConfigTable
--   V2.5 2010-09-25 Modified by Wu Xiaopeng
--        Remove Size list of hpnicfDot11APName.
--   V2.6 2011-05-23 Modified by Cui Kai
--        Add new node hpnicfDot11WlanexAuthServerIP to hpnicfDot11ServicePolicyTable
--        2011-07-08 Modified by Niu Jian
--        Change type of hpnicfDot11CfgSTNASPortID to OCTET STRING
--   V2.7 2011-07-13 Modified by Yu Bo
--        Add new node hpnicfDot11RCRadioRate to hpnicfDot11RadioConfigTable
--        Add new node hpnicfDot11RCPwrAdjustStepLength to hpnicfDot11RadioConfigTable
--        2011-08-08 Modified by Xiao Min
--        Add new table hpnicfDot11nRadioCfg2Table
--        2011-08-10 Modified by limingjin
--        Add hpnicfDot11RadioCfgType2 to hpnicfDot11RadioIntfConfigTable
--        Add hpnicfDot11RCRadioType2 to hpnicfDot11RadioConfigTable
--        Add hpnicfDot11CfgRadioType2 to hpnicfDot11RadioToConfigTable
--   V2.8 2011-09-28 Modified by zhanghu
--        Add hpnicfDot11ApTrapEnabled to hpnicfDot11APTemplateTable
--        Add hpnicfDot11AllAPMonitorMode to hpnicfDot11APTemplateTable
--        Add hpnicfDot11SIDAPTemplateName, hpnicfDot11SIDModelAlias, hpnicfDot11SIDAPDescription, hpnicfDot11SIDRowStatus,
--        hpnicfDot11SIDAPName, hpnicfDot11SIDStatisInterv, hpnicfDot11SIDAPBroadcastProbeReply,
--        hpnicfDot11SIDAPStaIdleTimerInterv, hpnicfDot11SIDStaKeepAliveTimerInterv,
--        hpnicfDot11SIDAPCir, hpnicfDot11SIDAPCbs, hpnicfDot11SIDAPPriorityLevel,
--        hpnicfDot11SIDAPElementID, hpnicfDot11SIDAPDevDetectEnable, hpnicfDot11SIDAPStatisIntervMode
--        to hpnicfDot11APSerialIDTable
--        2011-08-28 Modified by Wang Lu
--        Add hpnicfDot11CfgSaEnable, hpnicfDot11CfgSaBand, hpnicfDot11CfgIDSEnable,
--        hpnicfDot11CfgSaCltRtFFTData to hpnicfDot11RadioToConfigTable
--   V2.9 2012-08-10 by Zhang Cong cong
--        Add new node   hpnicfDot11ConfigureAPMacAddress to hpnicfDot11CfgTrapVarObjects
--        Add new object hpnicfDot11ConfigureAPMacAddress to hpnicfDot11SSIDWepIDConflictTrap
--   V3.0 2013-04-15 by Shao Pengfei & Li Shihao
--        Add new node hpnicfDot11GlobalApFmwUpdState to hpnicfDot11GlobeConfigGroup
--        Add new node hpnicfDot11ApFmwUpdState to hpnicfDot11APTemplateTable
--        Add new node hpnicfDot11SPBeaconMeasEnable to hpnicfDot11ServicePolicyTable
--        Add new node hpnicfDot11SPBeaconMeasType to hpnicfDot11ServicePolicyTable
--        Add new node hpnicfDot11SPBeaconMeasInterval to hpnicfDot11ServicePolicyTable
--   V3.1 2013-08-30 by Xiao Mengmeng & Li Qian & Ji Chunyu & Liu Yawen
--        Add hpnicfDot11AuthenModeCM to hpnicfDot11ServicePolicyTable
--        Add hpnicfDot11SecIEStatusCM to hpnicfDot11ServicePolicyTable
--        Add hpnicfDot11SecurityCiphersCM to hpnicfDot11ServicePolicyTable
--        Add hpnicfDot11SrvPolicyStatusCM to hpnicfDot11ServicePolicyTable
--        Add hpnicfDot11CfgSTNASID to hpnicfDot11APSTVlanTable
--        Add hpnicfDot11RCPreambleLenCM to hpnicfDot11RadioConfigTable
--        Add hpnicfDot11RCDynamicChlStateCM to hpnicfDot11RadioConfigTable
--        Add hpnicfDot11RCRadioStatusCM to hpnicfDot11RadioConfigTable
--        Add hpnicfDot11SIDAPWorkModeCM to hpnicfDot11APSerialIDTable
--        Add hpnicfDot11nRadioCfg2AMpduEnableCM to hpnicfDot11nRadioCfg2Table
--        Add hpnicfDot11nRadioCfg2ChannelBandCM to hpnicfDot11nRadioCfg2Table
--        Add hpnicfDot11nRadioCfg2ShortGiEnableCM to hpnicfDot11nRadioCfg2Table
--        2013-12-24 Modified by Chen Guoxi
--        Add mode80 to hpnicfDot11nChanelBand and hpnicfDot11nRadioCfg2ChannelBand
--        Add new node hpnicfDot11nClientDot11acOnly to hpnicfDot11nRadioCfgTable
--        Add new node hpnicfDot11nRadioCfg2ClientDot11acOnly to hpnicfDot11nRadioCfg2Table
--   V3.2 2014-02-10 by Zhou Weichao
--        Add hpnicfDot11ACNasIDCM to hpnicfDot11GlobeConfigGroup
--        Add hpnicfDot11SSIDHiddenCM to hpnicfDot11ServicePolicyTable
--        Add hpnicfDot11SPIsolateCM to hpnicfDot11ServicePolicyTable
--        Add hpnicfDot11RPBeaconIntervalCM to hpnicfDot11RadioPolicyExtTable
--        Add hpnicfDot11StatisIntervModeCM to hpnicfDot11APTemplateTable
--        Add hpnicfDot11APNasIDCM to hpnicfDot11APTemplateTable
--        Add hpnicfDot11RCDynamicPowerStateCM to hpnicfDot11RadioConfigTable
--        Add hpnicfDot11RCRadioRateCM to hpnicfDot11RadioConfigTable
--        Add hpnicfDot11nRadioCfg2ClientDot11nOnlyCM to hpnicfDot11nRadioCfg2Table
--        Modify hpnicfDot11WlanexAuthServerIP
--        Add hpnicfDot11RadioCfgRssithresholdCM to hpnicfDot11RadioIntfConfigTable
--        Add hpnicfDot11SrvPortSecurityModeCM to hpnicfDot11SrvPortSecurityTable
-- =============================================================================
HPN-ICF-DOT11-CFG-MIB DEFINITIONS ::= BEGIN

IMPORTS
        TruthValue,
        RowStatus,
        DisplayString,
        DateAndTime,
        MacAddress
    FROM SNMPv2-TC
        ifIndex
    FROM RFC1213-MIB
        MODULE-IDENTITY,
        NOTIFICATION-TYPE,
        OBJECT-TYPE,
        Integer32,
        Unsigned32,
        IpAddress
    FROM SNMPv2-SMI
        InetAddress
    FROM INET-ADDRESS-MIB
        hpnicfDot11,
        HpnicfDot11RadioType,
        HpnicfDot11TxPwrLevelScopeType,
        HpnicfDot11ChannelScopeType,
        HpnicfDot11SSIDStringType,
        HpnicfDot11AuthenType,
        HpnicfDot11RadioScopeType,
        HpnicfDot11SSIDEncryptModeType,
        HpnicfDot11SecIEStatusType,
        HpnicfDot11PreambleType,
        HpnicfDot11ServicePolicyIDType,
        HpnicfDot11TunnelSecSchemType,
        HpnicfDot11RadioElementIndex,
        HpnicfDot11WorkMode,
        HpnicfDot11CirMode,
        hpnicfDot11APElementIndex,
        HpnicfDot11ObjectIDType,
        HpnicfDot11RadioType2,
        HpnicfDot11TruthValueCM
    FROM HPN-ICF-DOT11-REF-MIB;

hpnicfDot11CFG MODULE-IDENTITY
    LAST-UPDATED "201009251800Z"        -- Sep 25, 2010 at 18:00 GMT
    ORGANIZATION
        ""
    CONTACT-INFO
        ""
    DESCRIPTION
        "This MIB provides information about WLAN configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell). The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."
    REVISION "201009251800Z"        -- Sep 25, 2010 at 18:00 GMT
    DESCRIPTION
        "Modified to remove some issue."
    REVISION "201009021800Z"        -- Sep 2, 2010 at 18:00 GMT
    DESCRIPTION
        "Modified to add new node."
    REVISION "200907291800Z"        -- Jul 29, 2009 at 18:00 GMT
    DESCRIPTION
        "Modified to add new nodes and new table."
    REVISION "200905072000Z"        -- May 7, 2009 at 20:00 GMT
    DESCRIPTION
        "Modified to add new nodes and new table."
    REVISION "200903201530Z"        -- Mar 20, 2009 at 15:30 GMT
    DESCRIPTION
        "Modified to add new value for appointed node."
    REVISION "200811071530Z"        -- Nov 07, 2008 at 15:30 GMT
    DESCRIPTION
        "Modified to add new nodes and new table."
    REVISION "200807091800Z"        -- July 09, 2008 at 18:00 GMT
    DESCRIPTION
        "Modified to add new groups."
    REVISION "200802251800Z"        -- Feb 25, 2008 at 18:00 GMT
    DESCRIPTION
        "Modified to add new nodes."
    REVISION "200712211800Z"        -- Dec 21, 2007 at 18:00 GMT
    DESCRIPTION
        "Modified to add new nodes."
    REVISION "200710091655Z"    -- October 09, 2007 at 16:55 GMT
    DESCRIPTION
        "changed for new requirements"
    REVISION "200706191800Z"        -- June 19, 2007 at 18:00 GMT
    DESCRIPTION
        "Modified to add new table."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { hpnicfDot11 4 }

-- *****************************************************************************
-- *  Major sections
-- *****************************************************************************
--  AP Configuration Group
--  DEFINED AS "The group to provide the configuration information
--  for APs.
hpnicfDot11GlobeConfigGroup OBJECT IDENTIFIER  ::= { hpnicfDot11CFG 1 }

hpnicfDot11PolicyConfigGroup OBJECT IDENTIFIER ::= { hpnicfDot11CFG 2 }
--  Policy Configuration Group has the following children:
--  hpnicfDot11RadioPolicyTable            ::= { hpnicfDot11PolicyConfigGroup 1 }
--  hpnicfDot11ServicePolicyTable          ::= { hpnicfDot11PolicyConfigGroup 2 }
--  hpnicfDot11ServicePolicyExtTable       ::= { hpnicfDot11PolicyConfigGroup 3 }
--  hpnicfDot11RadioPolicyExtTable         ::= { hpnicfDot11PolicyConfigGroup 4 }

hpnicfDot11APConfigGroup OBJECT IDENTIFIER     ::= { hpnicfDot11CFG 3 }
--  AP Configuration Group has the following children:
--  hpnicfDot11APTemplateTable                 ::= { hpnicfDot11APConfigGroup 1 }
--  hpnicfDot11RadioToConfigTable              ::= { hpnicfDot11APConfigGroup 2 }
--  hpnicfDot11APServiceSetTable               ::= { hpnicfDot11APConfigGroup 3 }
--  hpnicfDot11APSysInfoSetTable               ::= { hpnicfDot11APConfigGroup 4 }
--  hpnicfDot11APLimitTable                    ::= { hpnicfDot11APConfigGroup 5 }
--  hpnicfDot11APSerialIDTable                 ::= { hpnicfDot11APConfigGroup 10 }
--  hpnicfDot11APSTVlanTable                   ::= { hpnicfDot11APConfigGroup 11 }
hpnicfDot11RadioIntfConfigGroup OBJECT IDENTIFIER ::= { hpnicfDot11CFG 4 }
--  Radio Interface Group has the following children:
--  hpnicfDot11RadioIntfConfigTable          ::= { hpnicfDot11RadioIntfConfigGroup 1 }
--  hpnicfDot11RadioIntfBindTable            ::= { hpnicfDot11RadioIntfConfigGroup 2 }

hpnicfDot11DataRateConfigGroup OBJECT IDENTIFIER ::= { hpnicfDot11CFG 5 }
--  Data Rate Config Group has the following children:
--  hpnicfDot11DataRateConfigTable           ::= { hpnicfDot11DataRateConfigGroup 1 }

hpnicfDot11InterfaceConfigGroup OBJECT IDENTIFIER ::= { hpnicfDot11CFG 6 }
--  Interface Config Group has the following children:
--  hpnicfDot11WlanEssIfTable               ::= { hpnicfDot11InterfaceConfigGroup 1 }
--  hpnicfDot11WlanBssIfTable               ::= { hpnicfDot11InterfaceConfigGroup 2 }
--  hpnicfDot11WLANEthernetIfTable          ::= { hpnicfDot11InterfaceConfigGroup 3 }
--  hpnicfDot11PortSecurityTable            ::= { hpnicfDot11InterfaceConfigGroup 4 }
--  hpnicfDot11WlanMeshIfTable              ::= { hpnicfDot11InterfaceConfigGroup 5 }

hpnicfDot11ACBackupGroup OBJECT IDENTIFIER ::= { hpnicfDot11CFG 7 }

hpnicfDot11RadioElementConfigGroup OBJECT IDENTIFIER ::= { hpnicfDot11CFG 8 }
--  Radio Element Config Group has the following children:
--  hpnicfDot11nRadioCfgTable           ::= { hpnicfDot11RadioElementConfigGroup 1 }
--  hpnicfDot11RadioWDSTable            ::= { hpnicfDot11RadioElementConfigGroup 2 }
--  hpnicfDot11nRadioCfg2Table          ::= { hpnicfDot11RadioElementConfigGroup 3 }

hpnicfDot11CfgNotifyGroup OBJECT IDENTIFIER ::= { hpnicfDot11CFG 9 }

-- *****************************************************************************
-- *  hpnicfDot11GlobeConfigGroup Definition
-- *****************************************************************************
hpnicfDot11GlobalCountryCode OBJECT-TYPE
    SYNTAX      OCTET STRING(SIZE(3))
    MAX-ACCESS  read-write
    STATUS      current
    DESCRIPTION
        "Represents the country code for wireless network."
    ::= { hpnicfDot11GlobeConfigGroup 1 }

hpnicfDot11StaKeepALiveTimerIntvl OBJECT-TYPE
    SYNTAX      Unsigned32
    UNITS       "second"
    MAX-ACCESS  read-write
    STATUS      current
    DESCRIPTION
        "Represents the interval of the keep alive requests sent between
        AP and STA.
        Default value 0 : The keep alive function is disabled."
    DEFVAL      { 0 }
    ::= { hpnicfDot11GlobeConfigGroup 2 }

hpnicfDot11StaIdleTimerIntvl OBJECT-TYPE
    SYNTAX      Integer32
    UNITS       "second"
    MAX-ACCESS  read-write
    STATUS      current
    DESCRIPTION
        "Represents the interval for which the link between AP and STA
        ( power-save or awake ) can be idle."
    ::= { hpnicfDot11GlobeConfigGroup 3 }

hpnicfDot11BroadcastProbeReply OBJECT-TYPE
    SYNTAX      TruthValue
    MAX-ACCESS  read-write
    STATUS      current
    DESCRIPTION
        "Represents enable the AP to reply broadcast probe or not.
        'true' : The AP to reply broadcast probe is enabled.
        'false': The AP to reply broadcast probe is disabled"
    DEFVAL      { true }
    ::= { hpnicfDot11GlobeConfigGroup 4 }

hpnicfDot11APScanMode OBJECT-TYPE
    SYNTAX      INTEGER
        {
            active(1),
            passive(2)
        }
    MAX-ACCESS  read-write
    STATUS      current
    DESCRIPTION
        "Represents the scanning mode for AP.
        The following values are supported:
        active   - AP will actively do scan.
        passive  - AP will passively do scan."
    DEFVAL      { passive }
    ::= { hpnicfDot11GlobeConfigGroup 5 }

hpnicfDot11ACCtrlTunnelSecSupport OBJECT-TYPE
    SYNTAX      HpnicfDot11TunnelSecSchemType
    MAX-ACCESS  read-write
    STATUS      current
    DESCRIPTION
        "Represents what security schemes are supported for CAPWAP Control
        tunnel."
    ::= { hpnicfDot11GlobeConfigGroup 6 }

hpnicfDot11ACDataTunnelSecSupport OBJECT-TYPE
    SYNTAX      HpnicfDot11TunnelSecSchemType
    MAX-ACCESS  read-write
    STATUS      current
    DESCRIPTION
        "Represents what security schemes are supported for CAPWAP data
        tunnel. The cleartxt is the default scheme."
    DEFVAL      { cleartxt }
    ::= { hpnicfDot11GlobeConfigGroup 7 }

hpnicfDot11ACAutoAPSupport OBJECT-TYPE
    SYNTAX      TruthValue
    MAX-ACCESS  read-write
    STATUS      current
    DESCRIPTION
        "Represents enable the auto AP functionality or not.
        'true' : The auto AP functionality is enabled.
        'false': The auto AP functionality is disabled"
    DEFVAL      { false }
    ::= { hpnicfDot11GlobeConfigGroup 8 }

hpnicfDot11AutoAPName OBJECT-TYPE
    SYNTAX      OCTET STRING(SIZE(0..127))
    MAX-ACCESS  read-write
    STATUS      current
    DESCRIPTION
        "Represents the name of auto AP that needs to be made persistent.
        When read the value from the node, NULL value be returned."
    ::= { hpnicfDot11GlobeConfigGroup 9 }

hpnicfDot11PersistentName OBJECT-TYPE
    SYNTAX      OCTET STRING(SIZE(0..127))
    MAX-ACCESS  read-write
    STATUS      current
    DESCRIPTION
        "Represents the new name of auto AP after being made persistent.
        When read the value from the node, NULL value be returned."
    ::= { hpnicfDot11GlobeConfigGroup 10 }

hpnicfDot11IntfTrapThreshold OBJECT-TYPE
    SYNTAX      Integer32
    UNITS       "dbm"
    MAX-ACCESS  read-write
    STATUS      current
    DESCRIPTION
        "Represents threshold of interference trap. If signal strength of
        the device exceeds this threshold, corresponding trap will
        be sent."
    ::= { hpnicfDot11GlobeConfigGroup 11 }

hpnicfDot11MonitorInterval OBJECT-TYPE
    SYNTAX      Unsigned32(0 | 5..15)
    UNITS       "minute"
    MAX-ACCESS  read-write
    STATUS      current
    DESCRIPTION
        "Represents the monitoring interval.
        Default value 0 : The monitoring functionality is changed to
        real-time mode."
    DEFVAL      { 0 }
    ::= { hpnicfDot11GlobeConfigGroup 12 }

hpnicfDot11SampleInterval OBJECT-TYPE
    SYNTAX      Unsigned32(0 | 10..300)
    UNITS       "second"
    MAX-ACCESS  read-write
    STATUS      current
    DESCRIPTION
        "Represents the sampling interval.
        Default value 0 : The sampling functionality is disabled."
    DEFVAL      { 0 }
    ::= { hpnicfDot11GlobeConfigGroup 13 }

hpnicfDot11ChnlSwitChkInterval OBJECT-TYPE
    SYNTAX      Unsigned32(8..180)
    UNITS       "minute"
    MAX-ACCESS  read-write
    STATUS      current
    DESCRIPTION
        "Represents the checking interval of channel switch."
    DEFVAL      { 8 }
    ::= { hpnicfDot11GlobeConfigGroup 14 }

hpnicfDot11APUserUplimit OBJECT-TYPE
    SYNTAX      Unsigned32(0..65535)
    MAX-ACCESS  read-write
    STATUS      current
    DESCRIPTION
        "Represents the upper limit of user which has access to this AP."
    ::= { hpnicfDot11GlobeConfigGroup 15 }

hpnicfDot11APL2IsolateEnable OBJECT-TYPE
    SYNTAX      TruthValue
    MAX-ACCESS  read-write
    STATUS      current
    DESCRIPTION
        "Represents enable the layer2 isolation or not.
        'true' : The layer2 isolation functionality is enabled.
        'false': The layer2 isolation functionality is disabled."
    DEFVAL      { false }
    ::= { hpnicfDot11GlobeConfigGroup 16 }

hpnicfDot11APBSSIDSupportNum OBJECT-TYPE
    SYNTAX      Integer32
    MAX-ACCESS  read-only
    STATUS      current
    DESCRIPTION
        "Represents the max number of BSSID supported by Current AP."
    ::= { hpnicfDot11GlobeConfigGroup 17 }

hpnicfDot11APLastUpdateStatTime OBJECT-TYPE
    SYNTAX      DateAndTime
    MAX-ACCESS  read-only
    STATUS      current
    DESCRIPTION
        "Represents date and time update statistic information lately."
    ::= { hpnicfDot11GlobeConfigGroup 18 }

hpnicfDot11APDoSProtectEnable OBJECT-TYPE
    SYNTAX      TruthValue
    MAX-ACCESS  read-write
    STATUS      current
    DESCRIPTION
        "Represents enable the DOS protection or not.
        'true' : The DOS protection functionality is enabled.
        'false': The DOS protection functionality is disabled."
    DEFVAL      { false }
    ::= { hpnicfDot11GlobeConfigGroup 19 }

hpnicfDot11MaxAPPerIf OBJECT-TYPE
    SYNTAX      Unsigned32(0..65535)
    MAX-ACCESS  read-write
    STATUS      current
    DESCRIPTION
        "Represents max AP number that can be connected to AC interface."
    ::= { hpnicfDot11GlobeConfigGroup 20 }

hpnicfDot11SampleTimeStamp OBJECT-TYPE
    SYNTAX      DateAndTime
    MAX-ACCESS  read-only
    STATUS      current
    DESCRIPTION
        "Represents the start time of current sample period."
    ::= { hpnicfDot11GlobeConfigGroup 21 }

hpnicfDot11UplinkTrackId OBJECT-TYPE
    SYNTAX      Unsigned32
    MAX-ACCESS  read-write
    STATUS      current
    DESCRIPTION
        "Represents the track id of AP.
        Default value 0 : The uplink track function for AP is disabled."
    DEFVAL      { 0 }
    ::= { hpnicfDot11GlobeConfigGroup 22 }

hpnicfDot11RtCollectSwitch OBJECT-TYPE
    SYNTAX      TruthValue
    MAX-ACCESS  read-write
    STATUS      current
    DESCRIPTION
        "This object is used to turn on/off real-time statistics collection
         between AC and AP. If the value is true, hpnicfDot11RtCollectIntvl will
         take effect. Otherwise, hpnicfDot11RglCollectIntvl will take effect."
    DEFVAL      { false }
    ::= { hpnicfDot11GlobeConfigGroup 23 }

hpnicfDot11RglCollectIntvl OBJECT-TYPE
    SYNTAX      Integer32
    UNITS       "second"
    MAX-ACCESS  read-write
    STATUS      current
    DESCRIPTION
        "This object represents interval to regularly collect statistics from
         AC to AP."
    ::= { hpnicfDot11GlobeConfigGroup 24 }

hpnicfDot11RtCollectIntvl OBJECT-TYPE
    SYNTAX      Integer32
    UNITS       "second"
    MAX-ACCESS  read-write
    STATUS      current
    DESCRIPTION
        "This object represents interval to collect real-time statistics from
         AC to AP."
    ::= { hpnicfDot11GlobeConfigGroup 25 }

hpnicfDot11AllAPCpuUsageThreshold OBJECT-TYPE
    SYNTAX      Integer32(0..100)
    UNITS       "onepercent"
    MAX-ACCESS  read-write
    STATUS      current
    DESCRIPTION
        "The CPU usage threshold for all AP."
    ::= { hpnicfDot11GlobeConfigGroup 26 }

hpnicfDot11AllAPMemUsageThreshold OBJECT-TYPE
    SYNTAX      Integer32(0..100)
    UNITS       "onepercent"
    MAX-ACCESS  read-write
    STATUS      current
    DESCRIPTION
        "The memory usage threshold for all AP."
    ::= { hpnicfDot11GlobeConfigGroup 27 }

hpnicfDot11AdjIntfTrapThreshold OBJECT-TYPE
    SYNTAX      Integer32
    UNITS       "dbm"
    MAX-ACCESS  read-write
    STATUS      current
    DESCRIPTION
        "Represents threshold of adjacent interference trap. If signal strength
        of the device exceeds this threshold, corresponding trap will be sent."
    ::= { hpnicfDot11GlobeConfigGroup 28 }

hpnicfDot11AllAPMonitorMode OBJECT-TYPE
    SYNTAX      INTEGER
        {
            normal(1),
            monitor(2),
            hybrid(3)
        }
    MAX-ACCESS  read-write
    STATUS      current
    DESCRIPTION
        "Represents what work mode for All AP.
        The following values are supported:
        normal,     - AP will supply WLAN service.
        monitor     - AP will be a monitor to find attack.
        hybrid      - AP will supply WLAN service and Device detection is
        enabled."
    DEFVAL      { normal }
    ::= { hpnicfDot11GlobeConfigGroup 29 }

hpnicfDot11GlobalApFmwUpdState OBJECT-TYPE
    SYNTAX      INTEGER
        {
            enable(1),
            disable(2)
        }
    MAX-ACCESS  read-write
    STATUS      current
    DESCRIPTION
        "Represents the status of version auto-update for an AP.
        The following values are supported:
        enable      - AP version will be updated automatically.
        disable     - AP version will not be updated automatically."
    DEFVAL      { enable }
    ::= { hpnicfDot11GlobeConfigGroup 30 }

hpnicfDot11ACNasIDCM OBJECT-TYPE
    SYNTAX      OCTET STRING
    MAX-ACCESS  read-write
    STATUS      current
    DESCRIPTION
        "Represents the NAS-ID of current AC."
    ::= { hpnicfDot11GlobeConfigGroup 31 }

-- *****************************************************************************
-- * End of hpnicfDot11GlobeConfigGroup Definition
-- *****************************************************************************

-- *****************************************************************************
-- *  hpnicfDot11RadioPolicyTable Definition
-- *****************************************************************************
hpnicfDot11RadioPolicyTable OBJECT-TYPE
    SYNTAX      SEQUENCE OF HpnicfDot11RadioPolicyEntry
    MAX-ACCESS  not-accessible
    STATUS      current
    DESCRIPTION
        "The table defines the parameters for radio policy, as per
        radio policy of CLI.
        One radio policy could be assigned to the different radios (AP)."
    ::= { hpnicfDot11PolicyConfigGroup 1 }

hpnicfDot11RadioPolicyEntry OBJECT-TYPE
    SYNTAX      HpnicfDot11RadioPolicyEntry
    MAX-ACCESS  not-accessible
    STATUS      current
    DESCRIPTION
        "Each entry contains information of each radio policy."
    INDEX
        {
            IMPLIED hpnicfDot11RadioPolicyName
        }
    ::= { hpnicfDot11RadioPolicyTable 1 }

HpnicfDot11RadioPolicyEntry ::= SEQUENCE
    {
        hpnicfDot11RadioPolicyName        OCTET STRING,
        hpnicfDot11BeaconInterval         Integer32,
        hpnicfDot11DtimInterval           Integer32,
        hpnicfDot11RtsThreshold           Integer32,
        hpnicfDot11FragThreshold          Integer32,
        hpnicfDot11ShortRetryThreshold    Integer32,
        hpnicfDot11LongRetryThreshold     Integer32,
        hpnicfDot11MaxRxLifetime          Unsigned32,
        hpnicfDot11RdoPolicyRowStatus     RowStatus,
        hpnicfDot11RdoClientMaxCount      Integer32,
        hpnicfDot11BeaconIntervalMs       Integer32
    }

hpnicfDot11RadioPolicyName OBJECT-TYPE
    SYNTAX      OCTET STRING(SIZE(0..127))
    MAX-ACCESS  not-accessible
    STATUS      current
    DESCRIPTION
        "Represents the name of radio policy."
    ::= { hpnicfDot11RadioPolicyEntry 1 }

hpnicfDot11BeaconInterval OBJECT-TYPE
    SYNTAX      Integer32
    UNITS       "TU"
    MAX-ACCESS  read-create
    STATUS      current
    DESCRIPTION
        "Represents the interval for Beacon management frame."
    DEFVAL      { 100 }
    ::= { hpnicfDot11RadioPolicyEntry 2 }

hpnicfDot11DtimInterval OBJECT-TYPE
    SYNTAX      Integer32
    MAX-ACCESS  read-create
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL      { 1 }
    ::= { hpnicfDot11RadioPolicyEntry 3 }

hpnicfDot11RtsThreshold OBJECT-TYPE
    SYNTAX      Integer32
    UNITS       "byte"
    MAX-ACCESS  read-create
    STATUS      current
    DESCRIPTION
        "Represents the current minimum size, in octets, of the MAC
        protocol data unit (MPDU), below which a Request to send/Clear
        to send (RTS/CTS) handshake shall not be performed."
    DEFVAL      { 2346 }
    ::= { hpnicfDot11RadioPolicyEntry 4 }

hpnicfDot11FragThreshold OBJECT-TYPE
    SYNTAX      Integer32
    UNITS       "byte"
    MAX-ACCESS  read-create
    STATUS      current
    DESCRIPTION
        "Represents the current maximum size, in octets, of the MPDU that
        may be delivered to the PHY. A MSDU shall be broken into
        fragments if its size exceeds the value of this attribute after
        adding MAC headers and trailers."
    DEFVAL      { 2346 }
    ::= { hpnicfDot11RadioPolicyEntry 5 }

hpnicfDot11ShortRetryThreshold OBJECT-TYPE
    SYNTAX      Integer32
    MAX-ACCESS  read-create
    STATUS      current
    DESCRIPTION
        "Represents the maximum number of transmission attempts of a
        frame, the length of which is less than or equal to
        hpnicfDot11RTSThreshold, which shall be made before a failure
        condition is indicated."
    DEFVAL      { 7 }
    ::= { hpnicfDot11RadioPolicyEntry 6 }

hpnicfDot11LongRetryThreshold OBJECT-TYPE
    SYNTAX      Integer32
    MAX-ACCESS  read-create
    STATUS      current
    DESCRIPTION
        "Represents the maximum number of transmission attempts of a
        frame, the length of which is longer than hpnicfDot11RTSThreshold,
        that shall be made before a failure condition is indicated."
    DEFVAL      { 4 }
    ::= { hpnicfDot11RadioPolicyEntry 7 }

hpnicfDot11MaxRxLifetime OBJECT-TYPE
    SYNTAX      Unsigned32
    UNITS       "millisecond"
    MAX-ACCESS  read-create
    STATUS      current
    DESCRIPTION
        "Represents the elapsed time. After the time specified by
        hpnicfDot11MaxRxLifetime, the further attempts to reassemble the
        MSDU shall be terminated."
    DEFVAL      { 2000 }
    ::= { hpnicfDot11RadioPolicyEntry 8 }

hpnicfDot11RdoPolicyRowStatus OBJECT-TYPE
    SYNTAX      RowStatus
    MAX-ACCESS  read-create
    STATUS      current
    DESCRIPTION
        "The status of this table entry."
    ::= { hpnicfDot11RadioPolicyEntry 9 }

hpnicfDot11RdoClientMaxCount OBJECT-TYPE
    SYNTAX      Integer32(0..2147483647)
    MAX-ACCESS  read-create
    STATUS      current
    DESCRIPTION
        "Represent the maximum number of stations supported by
        this radio policy."
    ::= { hpnicfDot11RadioPolicyEntry 10 }

hpnicfDot11BeaconIntervalMs OBJECT-TYPE
    SYNTAX      Integer32
    UNITS       "ms"
    MAX-ACCESS  read-create
    STATUS      current
    DESCRIPTION
        "Represents the interval for Beacon management frame."
    ::= { hpnicfDot11RadioPolicyEntry 11 }
-- *****************************************************************************
-- * End of hpnicfDot11RadioPolicyTable Definition
-- *****************************************************************************

-- *****************************************************************************
-- *  hpnicfDot11ServicePolicyTable Definition
-- *****************************************************************************
hpnicfDot11ServicePolicyTable OBJECT-TYPE
    SYNTAX      SEQUENCE OF HpnicfDot11ServicePolicyEntry
    MAX-ACCESS  not-accessible
    STATUS      current
    DESCRIPTION
        "The table defines the parameters for ESS, as per service policy
        of CLI.
        One service policy could be assigned to the different radios
        (AP)."
    ::= { hpnicfDot11PolicyConfigGroup 2 }

hpnicfDot11ServicePolicyEntry OBJECT-TYPE
    SYNTAX      HpnicfDot11ServicePolicyEntry
    MAX-ACCESS  not-accessible
    STATUS      current
    DESCRIPTION
        "Each entry contains information of each service policy."
    INDEX
        {
            hpnicfDot11ServicePolicyID
        }
    ::= { hpnicfDot11ServicePolicyTable 1 }

HpnicfDot11ServicePolicyEntry ::= SEQUENCE
    {
        hpnicfDot11ServicePolicyID       HpnicfDot11ServicePolicyIDType,
        hpnicfDot11SSIDName              HpnicfDot11SSIDStringType,
        hpnicfDot11SSIDHidden            TruthValue,
        hpnicfDot11AuthenMode            HpnicfDot11AuthenType,
        hpnicfDot11SSIDEncryptionMode    HpnicfDot11SSIDEncryptModeType,
        hpnicfDot11WlanInfBindingType    OCTET STRING,
        hpnicfDot11WlanInfBindingID      Integer32,
        hpnicfDot11SrvPolicyRowStatus    RowStatus,
        hpnicfDot11ClientMaxCount        Integer32,
        hpnicfDot11SPInCirMode           HpnicfDot11CirMode,
        hpnicfDot11SPInCirValue          Integer32,
        hpnicfDot11SPOutCirMode          HpnicfDot11CirMode,
        hpnicfDot11SPOutCirValue         Integer32,
        hpnicfDot11WlanInfPVID           Integer32,
        hpnicfDot11SPInCirStaticValue    Integer32,
        hpnicfDot11SPOutCirStaticValue   Integer32,
        hpnicfDot11SPIsolate             TruthValue,
        hpnicfDot11WlanexAuthServerIP    IpAddress,
        hpnicfDot11SPBeaconMeasEnable    TruthValue,
        hpnicfDot11SPBeaconMeasType      INTEGER,
        hpnicfDot11SPBeaconMeasInterval  Integer32,
        hpnicfDot11AuthenModeCM          INTEGER,
        hpnicfDot11SecIEStatusCM         INTEGER,
        hpnicfDot11SecurityCiphersCM     INTEGER,
        hpnicfDot11SrvPolicyStatusCM     INTEGER,
        hpnicfDot11SSIDHiddenCM          HpnicfDot11TruthValueCM,
        hpnicfDot11SPIsolateCM           HpnicfDot11TruthValueCM
    }

hpnicfDot11ServicePolicyID OBJECT-TYPE
    SYNTAX      HpnicfDot11ServicePolicyIDType
    MAX-ACCESS  not-accessible
    STATUS      current
    DESCRIPTION
        "Represents the ID of each service policy."
    ::= { hpnicfDot11ServicePolicyEntry 1 }

hpnicfDot11SSIDName OBJECT-TYPE
    SYNTAX      HpnicfDot11SSIDStringType
    MAX-ACCESS  read-create
    STATUS      current
    DESCRIPTION
        "Represents the ESS. As per CLI, the value of
        service policy name will be SSID."
    ::= { hpnicfDot11ServicePolicyEntry 2 }

hpnicfDot11SSIDHidden OBJECT-TYPE
    SYNTAX      TruthValue
    MAX-ACCESS  read-create
    STATUS      current
    DESCRIPTION
        "This attribute controls whether the SSID will be advertised in
        the beacon frame.
        If it is true, then SSID will not be advertised in the beacon
        frame."
    DEFVAL      { false }
    ::= { hpnicfDot11ServicePolicyEntry 3 }

hpnicfDot11AuthenMode OBJECT-TYPE
    SYNTAX      HpnicfDot11AuthenType
    MAX-ACCESS  read-create
    STATUS      current
    DESCRIPTION
        "Represents the Authentication mode defined by 802.11."
    ::= { hpnicfDot11ServicePolicyEntry 4 }

hpnicfDot11SSIDEncryptionMode OBJECT-TYPE
    SYNTAX      HpnicfDot11SSIDEncryptModeType
    MAX-ACCESS  read-create
    STATUS      current
    DESCRIPTION
        "Represents the encryption mode for this ESS."
    ::= { hpnicfDot11ServicePolicyEntry 5 }

hpnicfDot11WlanInfBindingType OBJECT-TYPE
    SYNTAX      OCTET STRING
    MAX-ACCESS  read-create
    STATUS      current
    DESCRIPTION
        "Represents the service policy will bind to what kind of
        data forwarding interface."
    DEFVAL      { "WLAN-ESS" }
    ::= { hpnicfDot11ServicePolicyEntry 6 }

hpnicfDot11WlanInfBindingID OBJECT-TYPE
    SYNTAX      Integer32
    MAX-ACCESS  read-create
    STATUS      current
    DESCRIPTION
        "Represents the interface ID of the interface that ESS will
        bind to.
        If the value is set to -1, the binding will be removed."
    ::= { hpnicfDot11ServicePolicyEntry 7 }

hpnicfDot11SrvPolicyRowStatus OBJECT-TYPE
    SYNTAX      RowStatus
    MAX-ACCESS  read-create
    STATUS      current
    DESCRIPTION
        "The status of this table entry."
    ::= { hpnicfDot11ServicePolicyEntry 8 }

hpnicfDot11ClientMaxCount OBJECT-TYPE
    SYNTAX      Integer32(0..2147483647)
    MAX-ACCESS  read-create
    STATUS      current
    DESCRIPTION
        "Represent the maximum number of stations supported by
        this service policy."
    ::= { hpnicfDot11ServicePolicyEntry 9 }

hpnicfDot11SPInCirMode OBJECT-TYPE
    SYNTAX      HpnicfDot11CirMode
    MAX-ACCESS  read-create
    STATUS      current
    DESCRIPTION
        "
        CIR(committed information rate) mode of inbound direction.
        This object is useful only when the corresponding CIR is nonzero.
        If value of this object is changed, corresponding CIR will be reset."
    DEFVAL      { static }
    ::= { hpnicfDot11ServicePolicyEntry 10 }

hpnicfDot11SPInCirValue OBJECT-TYPE
    SYNTAX      Integer32
    UNITS       "Kbps"
    MAX-ACCESS  read-create
    STATUS      current
    DESCRIPTION
        "Represents the CIR of inbound direction of this service policy.
        If the value is 0, it means that no flow control is applied to
        the service policy, and the corresponding CIR mode is meaningless."
    DEFVAL      { 0 }
    ::= { hpnicfDot11ServicePolicyEntry 11 }

hpnicfDot11SPOutCirMode OBJECT-TYPE
    SYNTAX      HpnicfDot11CirMode
    MAX-ACCESS  read-create
    STATUS      current
    DESCRIPTION
        "
        CIR(committed information rate) mode of outbound direction.
        This object is useful only when the corresponding CIR is nonzero.
        If value of this object is changed, corresponding CIR will be reset."
    DEFVAL      { static }
    ::= { hpnicfDot11ServicePolicyEntry 12 }

hpnicfDot11SPOutCirValue OBJECT-TYPE
    SYNTAX      Integer32
    UNITS       "Kbps"
    MAX-ACCESS  read-create
    STATUS      current
    DESCRIPTION
        "Represents the CIR of outbound direction of this service policy.
        If the value is 0, it means that no flow control is applied to
        the service policy, and the corresponding CIR mode is meaningless."
    DEFVAL      { 0 }
    ::= { hpnicfDot11ServicePolicyEntry 13 }

hpnicfDot11WlanInfPVID OBJECT-TYPE
    SYNTAX      Integer32
    MAX-ACCESS  read-create
    STATUS      current
    DESCRIPTION
        "Represents the VLAN ID of SSID."
    DEFVAL      { 1 }
    ::= { hpnicfDot11ServicePolicyEntry 14 }

hpnicfDot11SPInCirStaticValue  OBJECT-TYPE
    SYNTAX      Integer32
    UNITS       "Kbps"
    MAX-ACCESS  read-create
    STATUS      current
    DESCRIPTION
        "Represents the CIR of inbound direction for static CIR mode."
    DEFVAL      { 0 }
        ::= { hpnicfDot11ServicePolicyEntry 15 }

hpnicfDot11SPOutCirStaticValue  OBJECT-TYPE
    SYNTAX      Integer32
    UNITS       "Kbps"
    MAX-ACCESS  read-create
    STATUS      current
    DESCRIPTION
        "Represents the CIR of outbound direction for static CIR mode."
    DEFVAL      { 0 }
        ::= { hpnicfDot11ServicePolicyEntry 16 }

hpnicfDot11SPIsolate OBJECT-TYPE
    SYNTAX      TruthValue
    MAX-ACCESS  read-create
    STATUS      current
    DESCRIPTION
        "If it is true, then stations connected with the service policy are
         isolated."
    DEFVAL      { false }
    ::= { hpnicfDot11ServicePolicyEntry 17 }

hpnicfDot11WlanexAuthServerIP OBJECT-TYPE
    SYNTAX     IpAddress
    MAX-ACCESS read-create
    STATUS     current
    DESCRIPTION
        "Represents the IP address of the Wlanex Authentication server"
    ::= {  hpnicfDot11ServicePolicyEntry 18 }

hpnicfDot11SPBeaconMeasEnable OBJECT-TYPE
    SYNTAX      TruthValue
    MAX-ACCESS  read-create
    STATUS      current
    DESCRIPTION
        "If it is true, then beacon-measurement is enabled."
    DEFVAL      { false }
    ::= { hpnicfDot11ServicePolicyEntry 19  }

hpnicfDot11SPBeaconMeasType OBJECT-TYPE
      SYNTAX      INTEGER
        {
            passive(1),
            active(2),
            beaconTable(3)
        }
    MAX-ACCESS  read-create
    STATUS      current
    DESCRIPTION
        "Represents what the work mode for BeaconMeasurement type.
        The following values are supported:
        passive,      - BeaconMeasurement will use the passive type.
        active        - BeaconMeasurement will use the active type.
        beaconTable   - BeaconMeasurement will use the beacon table type."
    DEFVAL      { beaconTable }
    ::= { hpnicfDot11ServicePolicyEntry 20 }

hpnicfDot11SPBeaconMeasInterval OBJECT-TYPE
    SYNTAX      Integer32(10..200)
    UNITS       "second"
    MAX-ACCESS  read-create
    STATUS      current
    DESCRIPTION
        "Represents the beacon-measurement interval."
    DEFVAL      { 60 }
    ::= { hpnicfDot11ServicePolicyEntry 21 }

hpnicfDot11AuthenModeCM OBJECT-TYPE
    SYNTAX      INTEGER
        {
            opensystem(0),
            sharedkey(1)
        }
    MAX-ACCESS  read-create
    STATUS      current
    DESCRIPTION
        "Represents the Authentication mode defined by 802.11."
    ::= { hpnicfDot11ServicePolicyEntry 22 }

hpnicfDot11SecIEStatusCM OBJECT-TYPE
    SYNTAX      INTEGER
        {
            none(0),
            wpa(1),
            wpa2(2),
            wlanex(3)
        }
    MAX-ACCESS  read-create
    STATUS      current
    DESCRIPTION
        "To enable the security Information element in the beacon and
        probe response frames sent by AP."
    ::= { hpnicfDot11ServicePolicyEntry 23 }

hpnicfDot11SecurityCiphersCM OBJECT-TYPE
    SYNTAX      INTEGER
        {
            none(0),
            wep40(1),
            wep104(2),
            tkip(3),
            aesccmp(4),
            wpisms4(5)
        }
    MAX-ACCESS  read-create
    STATUS      current
    DESCRIPTION
        "The WLAN system support the following cipher type for data frame
        encryption.
        none
        wep40
        wep104
        tkip
        aesccmp
        wpi-SMS4
        When the value of node equals to zero, it means no configuration or
        undo operation."
    ::= { hpnicfDot11ServicePolicyEntry 24 }

hpnicfDot11SrvPolicyStatusCM OBJECT-TYPE
    SYNTAX      INTEGER
        {
            off(0),
            on(1)
        }
    MAX-ACCESS read-create
    STATUS     current
    DESCRIPTION
        "The status of the Service Policy."
    ::= {  hpnicfDot11ServicePolicyEntry 25 }

hpnicfDot11SSIDHiddenCM OBJECT-TYPE
    SYNTAX      HpnicfDot11TruthValueCM
    MAX-ACCESS  read-create
    STATUS      current
    DESCRIPTION
        "This attribute controls whether the SSID will be advertised in
        beacon frames.
        If it is dot11true, the SSID will not be advertised in beacon
        frames."
    DEFVAL      { dot11false }
    ::= { hpnicfDot11ServicePolicyEntry 26 }

hpnicfDot11SPIsolateCM OBJECT-TYPE
    SYNTAX      HpnicfDot11TruthValueCM
    MAX-ACCESS  read-create
    STATUS      current
    DESCRIPTION
        "If it is dot11true, the clients connected with the service policy are
        isolated to each other."
    DEFVAL      { dot11false }
    ::= { hpnicfDot11ServicePolicyEntry 27 }
-- *****************************************************************************
-- * End of hpnicfDot11ServicePolicyTable Definition
-- *****************************************************************************

-- *****************************************************************************
-- *  hpnicfDot11ServicePolicyExtTable Definition
-- *****************************************************************************
hpnicfDot11ServicePolicyExtTable OBJECT-TYPE
    SYNTAX      SEQUENCE OF HpnicfDot11ServicePolicyExtEntry
    MAX-ACCESS  not-accessible
    STATUS      current
    DESCRIPTION
        "The table defines the parameters for ESS, as per service policy
        of CLI.
        When the value of hpnicfDot11SSIDEncryptionMode equals to cipher(2),
        more configuration for a ESS will be put into the table."
    ::= { hpnicfDot11PolicyConfigGroup 3 }

hpnicfDot11ServicePolicyExtEntry OBJECT-TYPE
    SYNTAX      HpnicfDot11ServicePolicyExtEntry
    MAX-ACCESS  not-accessible
    STATUS      current
    DESCRIPTION
        "Each entry contains information of each service policy under cipher(2)
        mode."
    INDEX
        {
            hpnicfDot11ServicePolicyExtID
        }
    ::= { hpnicfDot11ServicePolicyExtTable 1 }

HpnicfDot11ServicePolicyExtEntry ::= SEQUENCE
    {
        hpnicfDot11ServicePolicyExtID       HpnicfDot11ServicePolicyIDType,
        hpnicfDot11SecIEStatus              HpnicfDot11SecIEStatusType,
        hpnicfDot11SecurityCiphers          Integer32,
        hpnicfDot11CipherKeyIndex           Integer32,
        hpnicfDot11CipherKey                OCTET STRING,
        hpnicfDot11SrvPolicyExtRowStatus    RowStatus,
        hpnicfDot11CipherKeyType            INTEGER
    }

hpnicfDot11ServicePolicyExtID OBJECT-TYPE
    SYNTAX      HpnicfDot11ServicePolicyIDType
    MAX-ACCESS  not-accessible
    STATUS      current
    DESCRIPTION
        "Represents the ID of each service policy."
    ::= { hpnicfDot11ServicePolicyExtEntry 1 }

hpnicfDot11SecIEStatus OBJECT-TYPE
    SYNTAX      HpnicfDot11SecIEStatusType
    MAX-ACCESS  read-create
    STATUS      current
    DESCRIPTION
        "To enable the security Information element in the beacon and
        probe response frames sent by AP."
    ::= { hpnicfDot11ServicePolicyExtEntry 2 }

hpnicfDot11SecurityCiphers OBJECT-TYPE
    SYNTAX      Integer32
    MAX-ACCESS  read-create
    STATUS      current
    DESCRIPTION
        "The WLAN system support the following cipher type for data frame
        encryption.
        wep40(2)
        tkip(4)
        aesccmp(16)
        wep104(32)
        wpisms4(64)
        wep128(128)
        For each service policy, it could support multiple cipher types at
        the same time. So the value of object could combine multiple value
        of cipher type above.
        When the value of node equals to zero, it means no configuration or
        undo operation."
    ::= { hpnicfDot11ServicePolicyExtEntry 3 }

hpnicfDot11CipherKeyIndex OBJECT-TYPE
    SYNTAX      Integer32
    MAX-ACCESS  read-create
    STATUS      current
    DESCRIPTION
        "Represents the key index of cipher key for packet.
        When hpnicfDot11SecurityCiphers value is wep40 or wep104,
        the configuration will take effective."
    DEFVAL      { 1 }
    ::= { hpnicfDot11ServicePolicyExtEntry 4 }

hpnicfDot11CipherKey OBJECT-TYPE
    SYNTAX      OCTET STRING
    MAX-ACCESS  read-create
    STATUS      current
    DESCRIPTION
        "Represents the cipher key for packet.
        When hpnicfDot11SecurityCiphers value is wep40 or wep104,
        the configuration will take effective."
    ::= { hpnicfDot11ServicePolicyExtEntry 5 }

hpnicfDot11SrvPolicyExtRowStatus OBJECT-TYPE
    SYNTAX      RowStatus
    MAX-ACCESS  read-create
    STATUS      current
    DESCRIPTION
        "The status of this table entry."
    ::= { hpnicfDot11ServicePolicyExtEntry 6 }

hpnicfDot11CipherKeyType OBJECT-TYPE
    SYNTAX      INTEGER
    {
        char(1),
        hex(2)
    }
    MAX-ACCESS  read-create
    STATUS      current
    DESCRIPTION
        "Represents the cipher key type of hpnicfDot11CipherKey."
    DEFVAL    {1}
    ::= { hpnicfDot11ServicePolicyExtEntry 7 }

-- *****************************************************************************
-- * End of hpnicfDot11ServicePolicyExtTable Definition
-- *****************************************************************************

-- *****************************************************************************
-- *  hpnicfDot11RadioPolicyExtTable Definition
-- *****************************************************************************
hpnicfDot11RadioPolicyExtTable OBJECT-TYPE
    SYNTAX      SEQUENCE OF HpnicfDot11RadioPolicyExtEntry
    MAX-ACCESS  not-accessible
    STATUS      current
    DESCRIPTION
        "The table defines the radio policy of each radio.
        It can't be modified if the radio policy is a default radio policy."
    ::= { hpnicfDot11PolicyConfigGroup 4 }

hpnicfDot11RadioPolicyExtEntry OBJECT-TYPE
    SYNTAX      HpnicfDot11RadioPolicyExtEntry
    MAX-ACCESS  not-accessible
    STATUS      current
    DESCRIPTION
        "Each entry contains information of each radio policy."
    INDEX
        {
            hpnicfDot11RPAPSerialID,
            hpnicfDot11RPRadioID
        }
    ::= { hpnicfDot11RadioPolicyExtTable 1 }

HpnicfDot11RadioPolicyExtEntry ::= SEQUENCE
    {
        hpnicfDot11RPAPSerialID             OCTET STRING,
        hpnicfDot11RPRadioID                HpnicfDot11RadioScopeType,
        hpnicfDot11RPBeaconInterval         Integer32,
        hpnicfDot11RPDtimInterval           Integer32,
        hpnicfDot11RPRtsThreshold           Integer32,
        hpnicfDot11RPFragThreshold          Integer32,
        hpnicfDot11RPShortRetryThreshold    Integer32,
        hpnicfDot11RPLongRetryThreshold     Integer32,
        hpnicfDot11RPClientMaxCount         Integer32,
        hpnicfDot11RPBeaconIntervalCM       Integer32
    }

hpnicfDot11RPAPSerialID OBJECT-TYPE
    SYNTAX      OCTET STRING(SIZE(0..127))
    MAX-ACCESS  not-accessible
    STATUS      current
    DESCRIPTION
        "This object represents the Serial ID of AP."
    ::= { hpnicfDot11RadioPolicyExtEntry 1 }

hpnicfDot11RPRadioID OBJECT-TYPE
    SYNTAX      HpnicfDot11RadioScopeType
    MAX-ACCESS  not-accessible
    STATUS      current
    DESCRIPTION
        "This object represents each radio."
    ::= { hpnicfDot11RadioPolicyExtEntry 2 }

hpnicfDot11RPBeaconInterval OBJECT-TYPE
    SYNTAX      Integer32
    UNITS       "milliseconds"
    MAX-ACCESS  read-write
    STATUS      current
    DESCRIPTION
        "This object represents the interval for Beacon management frame."
    DEFVAL      { 100 }
    ::= { hpnicfDot11RadioPolicyExtEntry 3 }

hpnicfDot11RPDtimInterval OBJECT-TYPE
    SYNTAX      Integer32
    MAX-ACCESS  read-write
    STATUS      current
    DESCRIPTION
        "This object represents the number of beacon intervals that shall elapse
        between transmissions of Beacons frames containing a Traffic
        Indication Map (TIM) element whose DTIM count field is 0.
        This value is transmitted in the Delivery TIM (DTIM) Period
        field of Beacon frames."
    DEFVAL      { 1 }
    ::= { hpnicfDot11RadioPolicyExtEntry 4 }

hpnicfDot11RPRtsThreshold OBJECT-TYPE
    SYNTAX      Integer32
    UNITS       "byte"
    MAX-ACCESS  read-write
    STATUS      current
    DESCRIPTION
        "This object represents the current minimum size, in octets, of the MAC
        protocol data unit (MPDU), below which a Request to send/Clear
        to send (RTS/CTS) handshake shall not be performed."
    DEFVAL      { 2346 }
    ::= { hpnicfDot11RadioPolicyExtEntry 5 }

hpnicfDot11RPFragThreshold OBJECT-TYPE
    SYNTAX      Integer32
    UNITS       "byte"
    MAX-ACCESS  read-write
    STATUS      current
    DESCRIPTION
        "This object represents the current maximum size, in octets, of the MPDU
         that may be delivered to the PHY. A MSDU shall be broken into
        fragments if its size exceeds the value of this attribute after
        adding MAC headers and trailers."
    DEFVAL      { 2346 }
    ::= { hpnicfDot11RadioPolicyExtEntry 6 }

hpnicfDot11RPShortRetryThreshold OBJECT-TYPE
    SYNTAX      Integer32
    MAX-ACCESS  read-write
    STATUS      current
    DESCRIPTION
        "This object represents the maximum number of transmission attempts of a
        frame, the length of which is less than or equal to
        hpnicfDot11RTSThreshold, that shall be made before a failure
        condition is indicated."
    DEFVAL      { 7 }
    ::= { hpnicfDot11RadioPolicyExtEntry 7 }

hpnicfDot11RPLongRetryThreshold OBJECT-TYPE
    SYNTAX      Integer32
    MAX-ACCESS  read-write
    STATUS      current
    DESCRIPTION
        "This object represents the maximum number of transmission attempts of a
        frame, the length of which is longer than hpnicfDot11RTSThreshold,
        and that shall be made before a failure condition is indicated."
    DEFVAL      { 4 }
    ::= { hpnicfDot11RadioPolicyExtEntry 8 }

hpnicfDot11RPClientMaxCount OBJECT-TYPE
    SYNTAX      Integer32(0..2147483647)
    MAX-ACCESS  read-write
    STATUS      current
    DESCRIPTION
        "This object represents the maximum number of stations supported by
        this radio policy."
    ::= { hpnicfDot11RadioPolicyExtEntry 9 }

hpnicfDot11RPBeaconIntervalCM OBJECT-TYPE
    SYNTAX      Integer32
    UNITS       "timeunit"
    MAX-ACCESS  read-write
    STATUS      current
    DESCRIPTION
        "This object represents beacon interval."
    DEFVAL      { 100 }
    ::= { hpnicfDot11RadioPolicyExtEntry 10 }

-- *****************************************************************************
-- * End of hpnicfDot11RadioPolicyTable Definition
-- *****************************************************************************
-- *****************************************************************************
-- *  hpnicfDot11ServicePolicyPortSecurityTable Definition
-- *****************************************************************************
hpnicfDot11SrvPortSecurityTable OBJECT-TYPE
    SYNTAX      SEQUENCE OF HpnicfDot11SrvPortSecurityEntry
    MAX-ACCESS  not-accessible
    STATUS      current
    DESCRIPTION
        "This table defines the WLAN security status for ESS, BSS and
        WLAN-Ethernet interface which binding the crypto service-template.
        Otherwise, when binding the clear service-template,
        hpnicfPortSecurityTables should be used to configure port security."
    ::= { hpnicfDot11PolicyConfigGroup 5 }

hpnicfDot11SrvPortSecurityEntry OBJECT-TYPE
    SYNTAX      HpnicfDot11SrvPortSecurityEntry
    MAX-ACCESS  not-accessible
    STATUS      current
    DESCRIPTION
        "There is a row in this table for service policy."
    INDEX
        {
            hpnicfDot11SecurityServicePolicyID
        }
    ::= { hpnicfDot11SrvPortSecurityTable 1 }

HpnicfDot11SrvPortSecurityEntry ::= SEQUENCE
    {
        hpnicfDot11SecurityServicePolicyID           HpnicfDot11ServicePolicyIDType,
        hpnicfDot11SrvPortSecurityMode               INTEGER,
        hpnicfDot11SrvSecurityKeyType                INTEGER,
        hpnicfDot11SrvSecurityPskKeyMode             INTEGER,
        hpnicfDot11SrvSecurityPskKeyString           DisplayString,
        hpnicfDot11SrvPortSecurityModeCM             INTEGER
    }

hpnicfDot11SecurityServicePolicyID OBJECT-TYPE
    SYNTAX      HpnicfDot11ServicePolicyIDType
    MAX-ACCESS  not-accessible
    STATUS      current
    DESCRIPTION
        "Represents the ID of each service policy."
    ::= { hpnicfDot11SrvPortSecurityEntry 1 }

hpnicfDot11SrvPortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  The default value, no any security mode is set.

        userLoginSecureExt  Access to the port is denied until the port
        client is authorized (by 802.1X).

        psk  Access to the port is denied until the port client is
        authorized (by 802.1X key negotiation).

        macAddressAndPsk  The MAC address is first authenticated and only if
        this succeeds does the psk then attempt user authentication.

        userLoginSecureExtOrPsk  This selects both the userLoginSecureExt and
        psk modes together such that either is allowed to authorized access.
        Which mode works for client depends on the client's choice.

        ext  Access to the port is denied until the port client is
        authenticated (by ext)."
    ::= { hpnicfDot11SrvPortSecurityEntry 2 }

hpnicfDot11SrvSecurityKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { hpnicfDot11SrvPortSecurityEntry 3 }

hpnicfDot11SrvSecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode. When input as pskKeyModePassPhrase,
        hpnicfDot11SrvSecurityPskKeyString must be 8 to 63 characters;
        when input as pskKeyModeRawKey, hpnicfDot11SrvSecurityPskKeyString
        must be 64 characters and each character must be '0'-'9', 'a'-'f' and
        'A'-'F'."
    ::= { hpnicfDot11SrvPortSecurityEntry 4 }

hpnicfDot11SrvSecurityPskKeyString OBJECT-TYPE
    SYNTAX      DisplayString(SIZE(0..64))
    MAX-ACCESS  read-write
    STATUS      current
    DESCRIPTION
        "This is the password string used for psk authentication."
    ::= { hpnicfDot11SrvPortSecurityEntry 5 }

hpnicfDot11SrvPortSecurityModeCM OBJECT-TYPE
    SYNTAX INTEGER
        {
            none(0),
            psk(1),
            radius(2),
            wlanex(3)
        }
    MAX-ACCESS read-write
    STATUS current
    DESCRIPTION
        "Determines the security modes of the WLAN port.

        none  - The default value, no any security mode is set.

        psk  - Access to the port is denied until the port client is
        authorized (by 802.1X key negotiation).

        radius  - Access to the port is denied until the port
        client is authorized (by 802.1X).

        wlanex  - Access to the port is denied until the port client is
        authenticated by wlan cert."
    ::= { hpnicfDot11SrvPortSecurityEntry 6 }

-- *****************************************************************************
-- *  End of hpnicfDot11PortSecurityTable Definition
-- *****************************************************************************

-- *****************************************************************************
-- *  hpnicfDot11SrvPolicyExtendTable Definition
-- *****************************************************************************
hpnicfDot11SrvPolicyExtendTable OBJECT-TYPE
    SYNTAX      SEQUENCE OF HpnicfDot11SrvPolicyExtendEntry
    MAX-ACCESS  not-accessible
    STATUS      current
    DESCRIPTION
        "The table defines the parameters of each service policy."
    ::= { hpnicfDot11PolicyConfigGroup 6 }

hpnicfDot11SrvPolicyExtendEntry OBJECT-TYPE
    SYNTAX      HpnicfDot11SrvPolicyExtendEntry
    MAX-ACCESS  not-accessible
    STATUS      current
    DESCRIPTION
        "Each entry contains information of each service policy."
    INDEX
        {
            hpnicfDot11ServicePolicyID
        }
    ::= { hpnicfDot11SrvPolicyExtendTable 1 }

HpnicfDot11SrvPolicyExtendEntry ::= SEQUENCE
    {
        hpnicfDot11SPEnable              INTEGER
    }

hpnicfDot11SPEnable OBJECT-TYPE
    SYNTAX      INTEGER
    {
        enable(1),
        disable(2)
    }
    MAX-ACCESS  read-write
    STATUS      current
    DESCRIPTION
        "Represents whether the service policy is enabled."
    ::= { hpnicfDot11SrvPolicyExtendEntry 1 }

-- *****************************************************************************
-- *  End of hpnicfDot11ServicePolicyExtendTable Definition
-- *****************************************************************************

-- *****************************************************************************
-- *  hpnicfDot11APTemplateTable Definition
-- *****************************************************************************
hpnicfDot11APTemplateTable OBJECT-TYPE
    SYNTAX      SEQUENCE OF HpnicfDot11APTemplateEntry
    MAX-ACCESS  not-accessible
    STATUS      current
    DESCRIPTION
        "By AP template CLI, administrator will configure the parameters of AP
        by convenience.
        Before AP boot up and connect to AC by CAPWAP tunnel, administrator
        will create AP template for each AP. When AP connect to AC,
        AC will assign configuration to AP by hpnicfDot11APSerialID
        information in AP template."
    ::= { hpnicfDot11APConfigGroup 1 }

hpnicfDot11APTemplateEntry OBJECT-TYPE
    SYNTAX      HpnicfDot11APTemplateEntry
    MAX-ACCESS  not-accessible
    STATUS      current
    DESCRIPTION
        "Each entry contains configuration information for each AP."
    INDEX
        {
            hpnicfDot11APTemplateName
        }
    ::= { hpnicfDot11APTemplateTable 1 }

HpnicfDot11APTemplateEntry ::= SEQUENCE
    {
        hpnicfDot11APTemplateName             OCTET STRING,
        hpnicfDot11APSerialID                 OCTET STRING,
        hpnicfDot11TemplateAPModelAlias       OCTET STRING,
        hpnicfDot11Description                OCTET STRING,
        hpnicfDot11APWorkMode                 INTEGER,
        hpnicfDot11APTemplateRowStatus        RowStatus,
        hpnicfDot11APName                     OCTET STRING,
        hpnicfDot11StatisInterv               Integer32,
        hpnicfDot11APBroadcastProbeReply      TruthValue,
        hpnicfDot11StaIdleTimerInterv         Integer32,
        hpnicfDot11StaKeepAliveTimerInterv    Integer32,
        hpnicfDot11APCir                      Integer32,
        hpnicfDot11APCbs                      Integer32,
        hpnicfDot11APPriorityLevel            Integer32,
        hpnicfDot11APElementID                Integer32,
        hpnicfDot11APDevDetectEnable          TruthValue,
        hpnicfDot11APGetIPMethod              INTEGER,
        hpnicfDot11StatisIntervMode           INTEGER,
        hpnicfDot11ApTrapEnabled              TruthValue,
        hpnicfDot11ApFmwUpdState              INTEGER,
        hpnicfDot11StatisIntervModeCM         INTEGER,
        hpnicfDot11ApNasIDCM                  OCTET STRING
    }

hpnicfDot11APTemplateName OBJECT-TYPE
    SYNTAX      OCTET STRING(SIZE(0..127))
    MAX-ACCESS  not-accessible
    STATUS      current
    DESCRIPTION
        "Represents the name of AP template."
    ::= { hpnicfDot11APTemplateEntry 1 }

hpnicfDot11APSerialID OBJECT-TYPE
    SYNTAX      OCTET STRING
    MAX-ACCESS  read-create
    STATUS      current
    DESCRIPTION
        "Represents AP serial id."
    ::= { hpnicfDot11APTemplateEntry 2 }

hpnicfDot11TemplateAPModelAlias OBJECT-TYPE
    SYNTAX      OCTET STRING
    MAX-ACCESS  read-create
    STATUS      current
    DESCRIPTION
        "Represents the alias of AP model name."
    ::= { hpnicfDot11APTemplateEntry 3 }

hpnicfDot11Description OBJECT-TYPE
    SYNTAX      OCTET STRING
    MAX-ACCESS  read-create
    STATUS      current
    DESCRIPTION
        "This attribute will give more information about AP.
        Administrator could suggest the location, owner or
        other information for each AP.
        If the value is set to NULL, the description will be removed."
    ::= { hpnicfDot11APTemplateEntry 4 }

hpnicfDot11APWorkMode OBJECT-TYPE
    SYNTAX      INTEGER
        {
            normal(1),
            monitor(2),
            hybrid(3)
        }
    MAX-ACCESS  read-create
    STATUS      current
    DESCRIPTION
        "Represents what work mode for AP.
        The following values are supported:
        normal      - AP will supply WLAN service.
        monitor     - AP will be a monitor to find attack.
        hybrid      - AP will supply WLAN service and Device detection is
        enabled."
    DEFVAL      { normal }
    ::= { hpnicfDot11APTemplateEntry 5 }

hpnicfDot11APTemplateRowStatus OBJECT-TYPE
    SYNTAX      RowStatus
    MAX-ACCESS  read-create
    STATUS      current
    DESCRIPTION
        "The status of this table entry."
    ::= { hpnicfDot11APTemplateEntry 6 }

hpnicfDot11APName OBJECT-TYPE
    SYNTAX      OCTET STRING
    MAX-ACCESS  read-create
    STATUS      current
    DESCRIPTION
        "Represents the AP name."
    ::= { hpnicfDot11APTemplateEntry 7 }

hpnicfDot11StatisInterv OBJECT-TYPE
    SYNTAX      Integer32
    UNITS       "second"
    MAX-ACCESS  read-create
    STATUS      current
    DESCRIPTION
        "Represents the interval of radio statistic."
    ::= { hpnicfDot11APTemplateEntry 8 }

hpnicfDot11APBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { hpnicfDot11APTemplateEntry 9 }

hpnicfDot11StaIdleTimerInterv OBJECT-TYPE
    SYNTAX      Integer32
    UNITS       "second"
    MAX-ACCESS  read-create
    STATUS      current
    DESCRIPTION
        "Represents the interval for which the link between AP and STA
        ( power-save or awake ) can be idle."
    ::= { hpnicfDot11APTemplateEntry 10 }

hpnicfDot11StaKeepAliveTimerInterv OBJECT-TYPE
    SYNTAX      Integer32
    UNITS       "second"
    MAX-ACCESS  read-create
    STATUS      current
    DESCRIPTION
        "Represents the interval of the keep alive requests sent between
        AP and STA."
    ::= { hpnicfDot11APTemplateEntry 11 }

hpnicfDot11APCir OBJECT-TYPE
    SYNTAX      Integer32
    UNITS       "Kbps"
    MAX-ACCESS  read-create
    STATUS      current
    DESCRIPTION
        "Represents the committed information rate between AP and AC."
    ::= { hpnicfDot11APTemplateEntry 12 }

hpnicfDot11APCbs OBJECT-TYPE
    SYNTAX      Integer32
    UNITS       "Bytes"
    MAX-ACCESS  read-create
    STATUS      current
    DESCRIPTION
        "Represents the committed burst size between AP and AC."
    ::= { hpnicfDot11APTemplateEntry 13 }

hpnicfDot11APPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { hpnicfDot11APTemplateEntry 14 }

hpnicfDot11APElementID OBJECT-TYPE
    SYNTAX      Integer32
    MAX-ACCESS  read-only
    STATUS      current
    DESCRIPTION
        "This object represents the AP element ID."
    ::= { hpnicfDot11APTemplateEntry 15 }

hpnicfDot11APDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services. When an AP works
         in monitor mode, that is, the value of object hpnicfDot11APWorkMode is
         monitor, device detection can not be enabled with object
         hpnicfDot11APDevDetectEnable."
    DEFVAL      { false }
    ::= { hpnicfDot11APTemplateEntry 16 }

hpnicfDot11APGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { hpnicfDot11APTemplateEntry 17 }

hpnicfDot11StatisIntervMode OBJECT-TYPE
    SYNTAX      INTEGER
    {
        normal(1),
        realtime(2)
    }
    MAX-ACCESS  read-create
    STATUS      current
    DESCRIPTION
        "This object represents the mode of statics interval.
         normal    - statics interval value between 10s to 120s
         realtime  - statics interval value between 2s to 5s"
    DEFVAL      { normal }
    ::= { hpnicfDot11APTemplateEntry 18 }

hpnicfDot11ApTrapEnabled OBJECT-TYPE
    SYNTAX      TruthValue
    MAX-ACCESS  read-write
    STATUS      current
    DESCRIPTION
        "Represents whether the trap status is enabled or not.
        'true'  : Enable  the trap status;
        'false' : Disable the trap status."
    DEFVAL      { true }
    ::= { hpnicfDot11APTemplateEntry 19 }

hpnicfDot11ApFmwUpdState OBJECT-TYPE
    SYNTAX      INTEGER
    {
        enable(1),
        disable(2),
        inherit(3)
    }
    MAX-ACCESS  read-create
    STATUS      current
    DESCRIPTION
        "Represents the status of version auto-update for an AP.
        The following values are supported:
        enable   - AP version will be updated automatically.
        disable  - AP version will not be updated automatically.
        inherit  - The status will inherit value from apgroup-view or system-view."
    DEFVAL      { inherit }
    ::= { hpnicfDot11APTemplateEntry 20 }

hpnicfDot11StatisIntervModeCM OBJECT-TYPE
    SYNTAX      INTEGER
    {
        off(0),
        on(1)
    }
    MAX-ACCESS  read-create
    STATUS      current
    DESCRIPTION
        "This object represents the mode of statistic interval.
        off    - statistic interval value between 10s to 120s
        on     - statistic interval value between 2s to 5s"
    DEFVAL      { off }
    ::= { hpnicfDot11APTemplateEntry 21 }

hpnicfDot11ApNasIDCM OBJECT-TYPE
    SYNTAX      OCTET STRING
    MAX-ACCESS  read-create
    STATUS      current
    DESCRIPTION
        "Represents the NAS-ID of current service policy for each
        specific radio of AP."
    ::= { hpnicfDot11APTemplateEntry 22 }

-- *****************************************************************************
-- *  End of  hpnicfDot11APTemplateTable Definition
-- *****************************************************************************

-- *****************************************************************************
-- *  hpnicfDot11RadioToConfigTable Definition
-- *****************************************************************************
hpnicfDot11RadioToConfigTable OBJECT-TYPE
    SYNTAX      SEQUENCE OF HpnicfDot11RadioToConfigEntry
    MAX-ACCESS  not-accessible
    STATUS      current
    DESCRIPTION
        "Before AP connects to AC, administrator will configure radio
        parameter to each radio."
    ::= { hpnicfDot11APConfigGroup 2 }

hpnicfDot11RadioToConfigEntry OBJECT-TYPE
    SYNTAX      HpnicfDot11RadioToConfigEntry
    MAX-ACCESS  not-accessible
    STATUS      current
    DESCRIPTION
        "Each entry contains configuration information for each radio."
    INDEX
        {
            hpnicfDot11APTemplateNameCfg,
            hpnicfDot11CfgRadioID
        }
    ::= { hpnicfDot11RadioToConfigTable 1 }

HpnicfDot11RadioToConfigEntry ::= SEQUENCE
    {
        hpnicfDot11APTemplateNameCfg     OCTET STRING,
        hpnicfDot11CfgRadioID            HpnicfDot11RadioScopeType,
        hpnicfDot11CfgRadioPolicyName    OCTET STRING,
        hpnicfDot11CfgRadioType          HpnicfDot11RadioType,
        hpnicfDot11CfgChannel            HpnicfDot11ChannelScopeType,
        hpnicfDot11CfgMaxTxPowerLevel    HpnicfDot11TxPwrLevelScopeType,
        hpnicfDot11PreambleLen           HpnicfDot11PreambleType,
        hpnicfDot11CfgRadioStatus        TruthValue,
        hpnicfDot11CfgRdElementID        Unsigned32,
        hpnicfDot11CfgWorkMode           HpnicfDot11WorkMode,
        hpnicfDot11CfgPwrAttValue        Integer32,
        hpnicfDot11RadioTxArithmetic     INTEGER,
        hpnicfDot11CfgChannelLockStat    INTEGER,
        hpnicfDot11CfgPowerLockStat      INTEGER,
        hpnicfDot11CfgLBRdGroupId        Unsigned32,
        hpnicfDot11CfgRRMSDRdGroupId     Unsigned32,
        hpnicfDot11CfgRadioType2         HpnicfDot11RadioType2,
        hpnicfDot11CfgIDSEnable          TruthValue,
        hpnicfDot11CfgSaEnable           TruthValue,
        hpnicfDot11CfgSaCltRtFFTData     TruthValue,
        hpnicfDot11CfgSaBand             INTEGER
    }

hpnicfDot11APTemplateNameCfg OBJECT-TYPE
    SYNTAX      OCTET STRING(SIZE(0..127))
    MAX-ACCESS  not-accessible
    STATUS      current
    DESCRIPTION
        "Represents the name of AP template."
    ::= { hpnicfDot11RadioToConfigEntry 1 }

hpnicfDot11CfgRadioID OBJECT-TYPE
    SYNTAX      HpnicfDot11RadioScopeType
    MAX-ACCESS  not-accessible
    STATUS      current
    DESCRIPTION
        "Represents each radio."
    ::= { hpnicfDot11RadioToConfigEntry 2 }

hpnicfDot11CfgRadioPolicyName OBJECT-TYPE
    SYNTAX      OCTET STRING
    MAX-ACCESS  read-write
    STATUS      current
    DESCRIPTION
        "Represents the name of radio policy."
    ::= { hpnicfDot11RadioToConfigEntry 3 }

hpnicfDot11CfgRadioType OBJECT-TYPE
    SYNTAX      HpnicfDot11RadioType
    MAX-ACCESS  read-write
    STATUS      current
    DESCRIPTION
        "Represents the radio will work with which 802.11 radio type."
    ::= { hpnicfDot11RadioToConfigEntry 4 }

hpnicfDot11CfgChannel OBJECT-TYPE
    SYNTAX      HpnicfDot11ChannelScopeType
    MAX-ACCESS  read-write
    STATUS      current
    DESCRIPTION
        "Represents the channel allocation of radio."
    ::= { hpnicfDot11RadioToConfigEntry 5 }

hpnicfDot11CfgMaxTxPowerLevel OBJECT-TYPE
    SYNTAX      HpnicfDot11TxPwrLevelScopeType
    UNITS       "dbm"
    MAX-ACCESS  read-write
    STATUS      current
    DESCRIPTION
        "Represents the maximal transmit power scope for AP."
    ::= { hpnicfDot11RadioToConfigEntry 6 }

hpnicfDot11PreambleLen OBJECT-TYPE
    SYNTAX      HpnicfDot11PreambleType
    MAX-ACCESS  read-write
    STATUS      current
    DESCRIPTION
        "Represents whether use long or short preamble for 802.11 MAC
        frame.
        When hpnicfDot11CfgRadioType is either dot11b or dot11g,
        then value for hpnicfDot11PreambleLen will be valid.
        Otherwise, the value for it will be invalid."
    DEFVAL      { short }
    ::= { hpnicfDot11RadioToConfigEntry 7 }

hpnicfDot11CfgRadioStatus OBJECT-TYPE
    SYNTAX      TruthValue
    MAX-ACCESS  read-write
    STATUS      current
    DESCRIPTION
        "Represents the radio admin status whether is enabled
        or disabled."
    ::= { hpnicfDot11RadioToConfigEntry 8 }

hpnicfDot11CfgRdElementID OBJECT-TYPE
    SYNTAX      Unsigned32
    MAX-ACCESS  read-only
    STATUS      current
    DESCRIPTION
        "Represents the element ID of this radio. It comprises two parts.
        The highest 24 bits are AP element ID and the lowest 8 bits are
        radio ID."
    ::= { hpnicfDot11RadioToConfigEntry 9 }

hpnicfDot11CfgWorkMode OBJECT-TYPE
    SYNTAX      HpnicfDot11WorkMode
    MAX-ACCESS  read-write
    STATUS      current
    DESCRIPTION
        "Represents work mode of the radio."
    ::= { hpnicfDot11RadioToConfigEntry 10 }

hpnicfDot11CfgPwrAttValue OBJECT-TYPE
    SYNTAX      Integer32
    MAX-ACCESS  read-write
    STATUS      current
    DESCRIPTION
        "Represents the value of power attenuation."
    ::= { hpnicfDot11RadioToConfigEntry 11 }

hpnicfDot11RadioTxArithmetic OBJECT-TYPE
    SYNTAX      INTEGER
        {
            quality(1),
            bandwidth(2)
        }
    MAX-ACCESS  read-write
    STATUS      current
    DESCRIPTION
        "Represents the transmission arithmetic of the radio.
        The following values are supported:
        quality   - Consider the quality first during the transmission.
        bandwidth - Consider the bandwidth first during the transmission."
    DEFVAL      { quality }
    ::= { hpnicfDot11RadioToConfigEntry 12 }

hpnicfDot11CfgChannelLockStat OBJECT-TYPE
    SYNTAX      INTEGER
        {
            unlocked(1),
            locked(2)
        }
    MAX-ACCESS  read-write
    STATUS      current
    DESCRIPTION
        "Represents locked status of channel on the radio."
    DEFVAL      { unlocked }
    ::= { hpnicfDot11RadioToConfigEntry 13 }

hpnicfDot11CfgPowerLockStat OBJECT-TYPE
    SYNTAX      INTEGER
        {
            unlocked(1),
            locked(2)
        }
    MAX-ACCESS  read-write
    STATUS      current
    DESCRIPTION
        "Represents locked status of power on the radio."
    DEFVAL      { unlocked }
    ::= { hpnicfDot11RadioToConfigEntry 14 }

hpnicfDot11CfgLBRdGroupId OBJECT-TYPE
    SYNTAX      Unsigned32
    MAX-ACCESS  read-write
    STATUS      current
    DESCRIPTION
        "Represents the load balance group ID allocated for the radio."
    ::= { hpnicfDot11RadioToConfigEntry 15 }

hpnicfDot11CfgRRMSDRdGroupId OBJECT-TYPE
    SYNTAX      Unsigned32
    MAX-ACCESS  read-write
    STATUS      current
    DESCRIPTION
        "Represents the RRM self-decisive group ID allocated for the radio."
    ::= { hpnicfDot11RadioToConfigEntry 16 }

hpnicfDot11CfgRadioType2 OBJECT-TYPE
    SYNTAX      HpnicfDot11RadioType2
    MAX-ACCESS  read-write
    STATUS      current
    DESCRIPTION
        "Represents the radio will work with which 802.11 radio type."
    ::= { hpnicfDot11RadioToConfigEntry 17 }

hpnicfDot11CfgIDSEnable OBJECT-TYPE
    SYNTAX      TruthValue
    MAX-ACCESS  read-write
    STATUS      current
    DESCRIPTION
        "Represents whether intrusion detection is enabled for this radio."
    ::= { hpnicfDot11RadioToConfigEntry 18 }

hpnicfDot11CfgSaEnable OBJECT-TYPE
    SYNTAX      TruthValue
    MAX-ACCESS  read-write
    STATUS      current
    DESCRIPTION
        "Represents whether spectrum analysis is enabled."
    ::= { hpnicfDot11RadioToConfigEntry 19 }

hpnicfDot11CfgSaCltRtFFTData OBJECT-TYPE
    SYNTAX      TruthValue
    MAX-ACCESS  read-write
    STATUS      current
    DESCRIPTION
        "Represents whether to collect real-time FFT data for this radio."
    ::= { hpnicfDot11RadioToConfigEntry 20 }

hpnicfDot11CfgSaBand OBJECT-TYPE
    SYNTAX      INTEGER{
       dot11g(1),
       dot11aLower(2),
       dot11aMiddle(3),
       dot11aUpper(4)
    }
    MAX-ACCESS  read-write
    STATUS      current
    DESCRIPTION
        "Represents which band of channels will be monitored when collection
        real-time FFT data is enabled for this radio. Detection of
        interference devices and air quality will also be affected. Each band
        responds to the following channels.
         dot11g (Channels 1-14)
         dot11aLower (channels 36-64)
         dot11aMiddle (channels 100-140)
         dot11aUpper (channels 149-165)."
    ::= { hpnicfDot11RadioToConfigEntry 21 }

-- *****************************************************************************
-- *  End of  hpnicfDot11RadioToConfigTable Definition
-- *****************************************************************************

-- *****************************************************************************
-- *  hpnicfDot11APServiceSetTable Definition
-- *****************************************************************************
hpnicfDot11APServiceSetTable OBJECT-TYPE
    SYNTAX      SEQUENCE OF HpnicfDot11APServiceSetEntry
    MAX-ACCESS  not-accessible
    STATUS      current
    DESCRIPTION
        "For each radio, it could configure multiple service policies.
        The table describes the relationship between radio and
        service policies."
    ::= { hpnicfDot11APConfigGroup 3 }

hpnicfDot11APServiceSetEntry OBJECT-TYPE
    SYNTAX      HpnicfDot11APServiceSetEntry
    MAX-ACCESS  not-accessible
    STATUS      current
    DESCRIPTION
        "Each entry contains service policy information for each
        specific radio of AP."
    INDEX
        {
            hpnicfDot11APTemplateNameCfg,
            hpnicfDot11CfgRadioID,
            hpnicfDot11CfgServicePolicyID
        }
    ::= { hpnicfDot11APServiceSetTable 1 }

HpnicfDot11APServiceSetEntry ::= SEQUENCE
    {
        hpnicfDot11CfgServicePolicyID    HpnicfDot11ServicePolicyIDType,
        hpnicfDot11SrvSetRowStatus       RowStatus,
        hpnicfDot11ServiceSetVlanId      Integer32
    }

hpnicfDot11CfgServicePolicyID OBJECT-TYPE
    SYNTAX      HpnicfDot11ServicePolicyIDType
    MAX-ACCESS  not-accessible
    STATUS      current
    DESCRIPTION
        "Represents the ID of each service policy used by the AP."
    ::= { hpnicfDot11APServiceSetEntry 1 }

hpnicfDot11SrvSetRowStatus OBJECT-TYPE
    SYNTAX      RowStatus
    MAX-ACCESS  read-create
    STATUS      current
    DESCRIPTION
        "The status of this table entry."
    ::= { hpnicfDot11APServiceSetEntry 2 }

hpnicfDot11ServiceSetVlanId OBJECT-TYPE
    SYNTAX      Integer32(0..4094)
    MAX-ACCESS  read-create
    STATUS      current
    DESCRIPTION
        "Represents the Vlan ID of BSS which is generated when service policy
        is binded with the Radio."
    ::= { hpnicfDot11APServiceSetEntry 3 }
-- *****************************************************************************
-- * End of hpnicfDot11APServiceSetTable Definition
-- *****************************************************************************

-- *****************************************************************************
-- *  hpnicfDot11APSTVlanTable Definition
-- *****************************************************************************
hpnicfDot11APSTVlanTable OBJECT-TYPE
    SYNTAX      SEQUENCE OF HpnicfDot11APSTVlanEntry
    MAX-ACCESS  not-accessible
    STATUS      current
    DESCRIPTION
        "For each service policy, it could be bind to several VLANs.
        The table describes the relationship between VLAN and
        service policies."
    ::= { hpnicfDot11APConfigGroup 11 }

hpnicfDot11APSTVlanEntry OBJECT-TYPE
    SYNTAX      HpnicfDot11APSTVlanEntry
    MAX-ACCESS  not-accessible
    STATUS      current
    DESCRIPTION
        "Each entry contains VLAN and service policy information for each
        specific radio of AP."
    INDEX
        {
            hpnicfDot11SIDAPSerialID,
            hpnicfDot11CfgRadioID,
            hpnicfDot11CfgServicePolicyID
        }
    ::= { hpnicfDot11APSTVlanTable 1 }

HpnicfDot11APSTVlanEntry ::= SEQUENCE
    {
        hpnicfDot11CfgSTVLANID           Integer32,
        hpnicfDot11CfgSTNASPortID        OCTET STRING,
        hpnicfDot11CfgServiceSetRowStatus    RowStatus,
        hpnicfDot11CfgSTNASID            OCTET STRING
    }

hpnicfDot11CfgSTVLANID OBJECT-TYPE
    SYNTAX      Integer32(0..4094)
    MAX-ACCESS  read-create
    STATUS      current
    DESCRIPTION
        "Represents the VLAN that current Service Policy have bind to."
    ::= { hpnicfDot11APSTVlanEntry 1 }

hpnicfDot11CfgSTNASPortID OBJECT-TYPE
    SYNTAX      OCTET STRING(SIZE(0..127))
    MAX-ACCESS  read-only
    STATUS      current
    DESCRIPTION
        "Represents the NAS Port ID of current Service Policy for each
        specific radio of AP."
    ::= { hpnicfDot11APSTVlanEntry 2 }

hpnicfDot11CfgServiceSetRowStatus OBJECT-TYPE
    SYNTAX      RowStatus
    MAX-ACCESS  read-create
    STATUS      current
    DESCRIPTION
        "The status of this table entry."
    ::= { hpnicfDot11APSTVlanEntry 3 }

hpnicfDot11CfgSTNASID OBJECT-TYPE
    SYNTAX      OCTET STRING(SIZE(0..127))
    MAX-ACCESS  read-only
    STATUS      current
    DESCRIPTION
        "Represents the NAS ID of current Service Policy for each
        specific radio of AP."
    ::= { hpnicfDot11APSTVlanEntry 4 }
-- *****************************************************************************
-- * End of hpnicfDot11APSTVlanTable Definition
-- *****************************************************************************

-- *****************************************************************************
-- *  hpnicfDot11APSysInfoSetTable Definition
-- *****************************************************************************
hpnicfDot11APSysInfoSetTable OBJECT-TYPE
    SYNTAX      SEQUENCE OF HpnicfDot11APSysInfoSetEntry
    MAX-ACCESS  not-accessible
    STATUS      current
    DESCRIPTION
        "The table of the system information for each AP."
    ::= { hpnicfDot11APConfigGroup 4 }

hpnicfDot11APSysInfoSetEntry OBJECT-TYPE
    SYNTAX      HpnicfDot11APSysInfoSetEntry
    MAX-ACCESS  not-accessible
    STATUS      current
    DESCRIPTION
        "The system information configuration for each AP."
    INDEX
        {
            hpnicfDot11SIDAPSerialID
        }
    ::= { hpnicfDot11APSysInfoSetTable 1 }

HpnicfDot11APSysInfoSetEntry ::= SEQUENCE
    {
        hpnicfDot11APSysNetID            OCTET STRING,
        hpnicfDot11APCpuUsageThreshold   Integer32,
        hpnicfDot11APMemUsageThreshold   Integer32
    }

hpnicfDot11APSysNetID OBJECT-TYPE
    SYNTAX      OCTET STRING(SIZE(0..127))
    MAX-ACCESS  read-write
    STATUS      current
    DESCRIPTION
        "Represents the system Net ID for AP."
    ::= { hpnicfDot11APSysInfoSetEntry 1 }

hpnicfDot11APCpuUsageThreshold OBJECT-TYPE
    SYNTAX      Integer32(0..100)
    UNITS       "onepercent"
    MAX-ACCESS  read-write
    STATUS      current
    DESCRIPTION
        "The CPU usage threshold for AP."
    ::= { hpnicfDot11APSysInfoSetEntry 2 }

hpnicfDot11APMemUsageThreshold OBJECT-TYPE
    SYNTAX      Integer32(0..100)
    UNITS       "onepercent"
    MAX-ACCESS  read-write
    STATUS      current
    DESCRIPTION
        "The memory usage threshold for AP."
    ::= { hpnicfDot11APSysInfoSetEntry 3 }

-- *****************************************************************************
-- * End of hpnicfDot11APSysInfoSetTable Definition
-- *****************************************************************************

-- *****************************************************************************
-- *  hpnicfDot11APLimitTable Definition
-- *****************************************************************************
hpnicfDot11APLimitTable OBJECT-TYPE
    SYNTAX      SEQUENCE OF HpnicfDot11APLimitEntry
    MAX-ACCESS  not-accessible
    STATUS      current
    DESCRIPTION
        "For each connected APs, administrator could configure a series of
        limits. This table describes the limit information for AP(s)."
    ::= { hpnicfDot11APConfigGroup 5 }

hpnicfDot11APLimitEntry OBJECT-TYPE
    SYNTAX      HpnicfDot11APLimitEntry
    MAX-ACCESS  not-accessible
    STATUS      current
    DESCRIPTION
        "Each entry contains the limit information for each AP."
    INDEX
        {
            hpnicfDot11APElementIndex
        }
    ::= { hpnicfDot11APLimitTable 1 }

HpnicfDot11APLimitEntry ::= SEQUENCE
    {
        hpnicfDot11APSsidNumLimit     Integer32,
        hpnicfDot11APUserCntLimit     Integer32,
        hpnicfDot11APUserThreshold    Integer32
    }

hpnicfDot11APSsidNumLimit OBJECT-TYPE
    SYNTAX      Integer32(0..65535)
    MAX-ACCESS  read-write
    STATUS      current
    DESCRIPTION
        "Represents the upper limit of service template binded
        with this AP. All radios of AP share this limit.
        Default value 0 : There is no upper limit of service template
        binded with this AP."
    DEFVAL      { 0 }
    ::= { hpnicfDot11APLimitEntry 1 }

hpnicfDot11APUserCntLimit OBJECT-TYPE
    SYNTAX      Integer32(0..65535)
    MAX-ACCESS  read-write
    STATUS      current
    DESCRIPTION
        "Represents the upper limit of user which has access to this AP.
        All BSSs binded with AP share this limit.
        Default value 0 : There is no upper limit of user which has access
        to this AP."
    DEFVAL      { 0 }
    ::= { hpnicfDot11APLimitEntry 2 }

hpnicfDot11APUserThreshold OBJECT-TYPE
    SYNTAX      Integer32(0..65535)
    MAX-ACCESS  read-write
    STATUS      current
    DESCRIPTION
        "Represents the threshold of user which has access to this
        AP. All BSSs binded with AP share this limit. If the user counter
        is overflow, the trap will be sent.
        Default value 0 : There is no threshold of user which has access
        to this AP."
    DEFVAL      { 0 }
    ::= { hpnicfDot11APLimitEntry 3 }
-- *****************************************************************************
-- * End of hpnicfDot11APLimitTable Definition
-- *****************************************************************************

-- *****************************************************************************
-- * hpnicfDot11APIfSetTable Definition
-- *****************************************************************************
hpnicfDot11APIfSetTable OBJECT-TYPE
    SYNTAX      SEQUENCE OF HpnicfDot11APIfSetEntry
    MAX-ACCESS  not-accessible
    STATUS      current
    DESCRIPTION
        "The table of the interface information for each AP."
    ::= { hpnicfDot11APConfigGroup 6 }

hpnicfDot11APIfSetEntry OBJECT-TYPE
    SYNTAX      HpnicfDot11APIfSetEntry
    MAX-ACCESS  not-accessible
    STATUS      current
    DESCRIPTION
        "The interface information configuration for each AP."
    INDEX
        {
            hpnicfDot11APElementIndex,
            hpnicfDot11APSetIfIndex
        }
    ::= { hpnicfDot11APIfSetTable 1 }

HpnicfDot11APIfSetEntry ::= SEQUENCE
    {
        hpnicfDot11APSetIfIndex      Integer32,
        hpnicfDot11APIfAlias         DisplayString
    }

hpnicfDot11APSetIfIndex OBJECT-TYPE
    SYNTAX      Integer32
    MAX-ACCESS  not-accessible
    STATUS      current
    DESCRIPTION
        "Represents the index for a interface."
    ::= { hpnicfDot11APIfSetEntry 1 }

hpnicfDot11APIfAlias OBJECT-TYPE
    SYNTAX      DisplayString
    MAX-ACCESS  read-write
    STATUS      current
    DESCRIPTION
        "This object is an 'alias' name for the interface as specified
        by a network manager for AP."
    ::= { hpnicfDot11APIfSetEntry 2 }

-- *****************************************************************************
-- * End of hpnicfDot11APIfSetTable Definition
-- *****************************************************************************

-- *****************************************************************************
-- *  hpnicfDot11APServiceVlanTable Definition
-- *****************************************************************************
hpnicfDot11APServiceVlanTable OBJECT-TYPE
    SYNTAX      SEQUENCE OF HpnicfDot11APServiceVlanEntry
    MAX-ACCESS  not-accessible
    STATUS      current
    DESCRIPTION
        "For all the radios on the AP, it could configure multiple service policies.
        The table describes the relationship between AP and
        service policies."
    ::= { hpnicfDot11APConfigGroup 7 }

hpnicfDot11APServiceVlanEntry OBJECT-TYPE
    SYNTAX      HpnicfDot11APServiceVlanEntry
    MAX-ACCESS  not-accessible
    STATUS      current
    DESCRIPTION
        "Each entry contains service policy information for each AP."
    INDEX
        {
            hpnicfDot11APServiceVlanSerialID,
            hpnicfDot11APServiceVlanSPID
        }
    ::= { hpnicfDot11APServiceVlanTable 1 }

HpnicfDot11APServiceVlanEntry ::= SEQUENCE
    {
        hpnicfDot11APServiceVlanSerialID          OCTET STRING,
        hpnicfDot11APServiceVlanSPID              HpnicfDot11ServicePolicyIDType,
        hpnicfDot11APServiceVlanId                Integer32,
        hpnicfDot11APServiceVlanRowStatus         RowStatus

    }

hpnicfDot11APServiceVlanSerialID OBJECT-TYPE
    SYNTAX      OCTET STRING
    MAX-ACCESS  not-accessible
    STATUS      current
    DESCRIPTION
        "This object represents AP serial id."
    ::= { hpnicfDot11APServiceVlanEntry 1 }

hpnicfDot11APServiceVlanSPID OBJECT-TYPE
    SYNTAX      HpnicfDot11ServicePolicyIDType
    MAX-ACCESS  not-accessible
    STATUS      current
    DESCRIPTION
        "This object represents the ID of each service policy used by the AP."
    ::= { hpnicfDot11APServiceVlanEntry 2 }

hpnicfDot11APServiceVlanId OBJECT-TYPE
    SYNTAX      Integer32(0..4094)
    MAX-ACCESS  read-create
    STATUS      current
    DESCRIPTION
        "This object represents the VLAN ID of BSS which is generated when the
         service policy is bound to the radio."
    ::= { hpnicfDot11APServiceVlanEntry 3 }

hpnicfDot11APServiceVlanRowStatus OBJECT-TYPE
    SYNTAX      RowStatus
    MAX-ACCESS  read-create
    STATUS      current
    DESCRIPTION
        "This object represents the status of this table entry."
    ::= { hpnicfDot11APServiceVlanEntry 4 }

-- *****************************************************************************
-- * End of hpnicfDot11APServiceSetTable Definition
-- *****************************************************************************

-- *****************************************************************************
-- *  hpnicfDot11RadioConfigTable Definition
-- *****************************************************************************
hpnicfDot11RadioConfigTable OBJECT-TYPE
    SYNTAX      SEQUENCE OF HpnicfDot11RadioConfigEntry
    MAX-ACCESS  not-accessible
    STATUS      current
    DESCRIPTION
        "Before AP connects to AC, administrator will configure radio
        parameter to each radio."
    ::= { hpnicfDot11APConfigGroup 8 }

hpnicfDot11RadioConfigEntry OBJECT-TYPE
    SYNTAX      HpnicfDot11RadioConfigEntry
    MAX-ACCESS  not-accessible
    STATUS      current
    DESCRIPTION
        "Each entry contains configuration information for each radio."
    INDEX
        {
            hpnicfDot11RCAPSerialID,
            hpnicfDot11RCRadioID
        }
    ::= { hpnicfDot11RadioConfigTable 1 }

HpnicfDot11RadioConfigEntry ::= SEQUENCE
    {
        hpnicfDot11RCAPSerialID               OCTET STRING,
        hpnicfDot11RCRadioID                  HpnicfDot11RadioScopeType,
        hpnicfDot11RCRadioType                HpnicfDot11RadioType,
        hpnicfDot11RCChannel                  HpnicfDot11ChannelScopeType,
        hpnicfDot11RCPreambleLen              HpnicfDot11PreambleType,
        hpnicfDot11RCPwrAttValue              Integer32,
        hpnicfDot11RCApPowerLevel             HpnicfDot11TxPwrLevelScopeType,
        hpnicfDot11RCDynamicChlState          TruthValue,
        hpnicfDot11RCDynamicPowerState        TruthValue,
        hpnicfDot11RCRadioStatus              TruthValue,
        hpnicfDot11RCRadioRate                OCTET STRING,
        hpnicfDot11RCPwrAdjustStepLength      Integer32,
        hpnicfDot11RCRadioType2               HpnicfDot11RadioType2,
        hpnicfDot11RCPreambleLenCM            INTEGER,
        hpnicfDot11RCDynamicChlStateCM        INTEGER,
        hpnicfDot11RCRadioStatusCM            INTEGER,
        hpnicfDot11RCRadioRateCM              OCTET STRING,
        hpnicfDot11RCDynamicPowerStateCM      HpnicfDot11TruthValueCM
    }

hpnicfDot11RCAPSerialID OBJECT-TYPE
    SYNTAX      OCTET STRING(SIZE(0..127))
    MAX-ACCESS  not-accessible
    STATUS      current
    DESCRIPTION
        "This object represents the Serial ID of AP."
    ::= { hpnicfDot11RadioConfigEntry 1 }

hpnicfDot11RCRadioID OBJECT-TYPE
    SYNTAX      HpnicfDot11RadioScopeType
    MAX-ACCESS  not-accessible
    STATUS      current
    DESCRIPTION
        "This object represents each radio."
    ::= { hpnicfDot11RadioConfigEntry 2 }

hpnicfDot11RCRadioType OBJECT-TYPE
    SYNTAX      HpnicfDot11RadioType
    MAX-ACCESS  read-write
    STATUS      current
    DESCRIPTION
        "This object represents the radio will work with which 802.11 radio
         type."
    ::= { hpnicfDot11RadioConfigEntry 3 }

hpnicfDot11RCChannel OBJECT-TYPE
    SYNTAX      HpnicfDot11ChannelScopeType
    MAX-ACCESS  read-write
    STATUS      current
    DESCRIPTION
        "This object represents the channel allocation of radio."
    ::= { hpnicfDot11RadioConfigEntry 4 }

hpnicfDot11RCPreambleLen OBJECT-TYPE
    SYNTAX      HpnicfDot11PreambleType
    MAX-ACCESS  read-write
    STATUS      current
    DESCRIPTION
        "This object represents whether use long or short preamble for 802.11
         MAC frame.
        When hpnicfDot11CfgRadioType is either dot11b or dot11g,
        then value for hpnicfDot11PreambleLen will be valid.
        Otherwise, the value for it will be invalid."
    DEFVAL      { short }
    ::= { hpnicfDot11RadioConfigEntry 5 }

hpnicfDot11RCPwrAttValue OBJECT-TYPE
    SYNTAX      Integer32
    MAX-ACCESS  read-write
    STATUS      current
    DESCRIPTION
        "This object represents the value of power attenuation."
    ::= { hpnicfDot11RadioConfigEntry 6 }

hpnicfDot11RCApPowerLevel OBJECT-TYPE
    SYNTAX      HpnicfDot11TxPwrLevelScopeType
    UNITS       "dbm"
    MAX-ACCESS  read-write
    STATUS      current
    DESCRIPTION
        "Represents the maximal transmit power scope for AP."
    ::= { hpnicfDot11RadioConfigEntry 7 }

hpnicfDot11RCDynamicChlState OBJECT-TYPE
    SYNTAX      TruthValue
    MAX-ACCESS  read-write
    STATUS      current
    DESCRIPTION
        "Enable/Disable dynamic channel selection."
    ::= { hpnicfDot11RadioConfigEntry 8 }

hpnicfDot11RCDynamicPowerState OBJECT-TYPE
    SYNTAX      TruthValue
    MAX-ACCESS  read-write
    STATUS      current
    DESCRIPTION
        "Enable/Disable dynamic power selection for the band."
    ::= { hpnicfDot11RadioConfigEntry 9 }

hpnicfDot11RCRadioStatus OBJECT-TYPE
    SYNTAX      TruthValue
    MAX-ACCESS  read-write
    STATUS      current
    DESCRIPTION
        "Represents the radio admin status whether is enabled
        or disabled."
    ::= { hpnicfDot11RadioConfigEntry 10 }

hpnicfDot11RCRadioRate OBJECT-TYPE
    SYNTAX      OCTET STRING(SIZE(0..255))
    MAX-ACCESS  read-write
    STATUS      current
    DESCRIPTION
        "Set data transmit rates for the radio, in the format of 1,2,5.5...
        For 802.11n radios, the format can be MCS X. The data transmit rates
        between AP and STA must fall into the configured rates.
        (Note: For 802.11n radios, the first value will be treated as a mandatory rate,
        and the second value will be treated as a supported rate.
        If you configure more than two rates, the configuration cannot take effect.
        If you configure only one rate, it is considered as the mandatory rate by default.)"
    ::= { hpnicfDot11RadioConfigEntry 11 }

hpnicfDot11RCPwrAdjustStepLength OBJECT-TYPE
    SYNTAX      Integer32
    MAX-ACCESS  read-only
    STATUS      current
    DESCRIPTION
        "Power adjustment step-length in dBm."
    ::= { hpnicfDot11RadioConfigEntry 12 }

hpnicfDot11RCRadioType2 OBJECT-TYPE
    SYNTAX      HpnicfDot11RadioType2
    MAX-ACCESS  read-write
    STATUS      current
    DESCRIPTION
        "This object represents the radio will work with which 802.11 radio
         type."
    ::= { hpnicfDot11RadioConfigEntry 13 }

hpnicfDot11RCPreambleLenCM OBJECT-TYPE
    SYNTAX      INTEGER
        {
            long(0),
            short(1)
        }
    MAX-ACCESS  read-write
    STATUS      current
    DESCRIPTION
        "This object represents whether use long or short preamble for 802.11
         MAC frame.
        When hpnicfDot11CfgRadioType is either dot11b or dot11g,
        then value for hpnicfDot11PreambleLenCM will be valid.
        Otherwise, the value for it will be invalid."
    DEFVAL      { short }
    ::= { hpnicfDot11RadioConfigEntry 14 }

hpnicfDot11RCDynamicChlStateCM OBJECT-TYPE
    SYNTAX      INTEGER
        {
            off(0),
            on(1)
        }
    MAX-ACCESS  read-write
    STATUS      current
    DESCRIPTION
        "Enable/Disable dynamic channel selection."
    ::= { hpnicfDot11RadioConfigEntry 15 }

hpnicfDot11RCRadioStatusCM OBJECT-TYPE
    SYNTAX      INTEGER
        {
            up(1),
            down(2),
            testing(3)
        }
    MAX-ACCESS  read-write
    STATUS      current
    DESCRIPTION
        "Represents the radio admin status whether is enabled
        or disabled."
    ::= { hpnicfDot11RadioConfigEntry 16 }

hpnicfDot11RCRadioRateCM OBJECT-TYPE
    SYNTAX      OCTET STRING(SIZE(0..255))
    MAX-ACCESS  read-write
    STATUS      current
    DESCRIPTION
        "Set data transmit rates for the radio, in the format of 1,2,5.5...
        For 802.11n radios, the format of each value can be MCS X. The data transmit
        rates between AP and client should be one of the configured rates.
        (Note: For 802.11n radios, the first value is mandatory rate, and the second
        value is supported rate. If more than two rate values are configured, the
        configuration will not take effect. If only one rate value is configured,
        the mandatory rate will be set to the default value.)"
    ::= { hpnicfDot11RadioConfigEntry 17 }

hpnicfDot11RCDynamicPowerStateCM OBJECT-TYPE
    SYNTAX      HpnicfDot11TruthValueCM
    MAX-ACCESS  read-write
    STATUS      current
    DESCRIPTION
        "Enable/disable dynamic power selection for the band."
    ::= { hpnicfDot11RadioConfigEntry 18 }
-- *****************************************************************************
-- * End of hpnicfDot11RadioConfigTable Definition
-- *****************************************************************************

hpnicfDot11RadioSSIDCfgTable OBJECT-TYPE
    SYNTAX      SEQUENCE OF HpnicfDot11RadioSSIDCfgEntry
    MAX-ACCESS  not-accessible
    STATUS      current
    DESCRIPTION
        "For each radio, it could configure multiple service policies.
        The table describes the relationship between radio and
        service policies."
    ::= { hpnicfDot11APConfigGroup 9 }

hpnicfDot11RadioSSIDCfgEntry OBJECT-TYPE
    SYNTAX      HpnicfDot11RadioSSIDCfgEntry
    MAX-ACCESS  not-accessible
    STATUS      current
    DESCRIPTION
        "Each entry contains SSID configuration information for each radio."
    INDEX
        {
            hpnicfDot11RadioSSIDSerialID,
            hpnicfDot11RadioSSIDRadioID,
            hpnicfDot11RadioSSIDWLANID
        }
    ::= { hpnicfDot11RadioSSIDCfgTable 1 }

HpnicfDot11RadioSSIDCfgEntry ::= SEQUENCE
    {
        hpnicfDot11RadioSSIDSerialID    HpnicfDot11ObjectIDType,
        hpnicfDot11RadioSSIDRadioID     HpnicfDot11RadioScopeType,
        hpnicfDot11RadioSSIDWLANID      Integer32,
        hpnicfDot11RadioSSIDIndex       HpnicfDot11ServicePolicyIDType,
        hpnicfDot11RadioBSSID           MacAddress,
        hpnicfDot11RadioSSIDRowStatus   RowStatus
    }

hpnicfDot11RadioSSIDSerialID OBJECT-TYPE
    SYNTAX      HpnicfDot11ObjectIDType
    MAX-ACCESS  not-accessible
    STATUS      current
    DESCRIPTION
        "This object represents the serial ID of AP."
    ::= { hpnicfDot11RadioSSIDCfgEntry 1 }

hpnicfDot11RadioSSIDRadioID OBJECT-TYPE
    SYNTAX      HpnicfDot11RadioScopeType
    MAX-ACCESS  not-accessible
    STATUS      current
    DESCRIPTION
        "This object represents each radio."
    ::= { hpnicfDot11RadioSSIDCfgEntry 2 }

hpnicfDot11RadioSSIDWLANID OBJECT-TYPE
    SYNTAX      Integer32
    MAX-ACCESS  not-accessible
    STATUS      current
    DESCRIPTION
        "This object represents the WLAN ID of the BSSID."
    ::= { hpnicfDot11RadioSSIDCfgEntry 3 }

hpnicfDot11RadioSSIDIndex OBJECT-TYPE
    SYNTAX      HpnicfDot11ServicePolicyIDType
    MAX-ACCESS  read-create
    STATUS      current
    DESCRIPTION
        "This object represents the ID of each service policy used by the
         radio."
    ::= { hpnicfDot11RadioSSIDCfgEntry 4 }

hpnicfDot11RadioBSSID OBJECT-TYPE
    SYNTAX      MacAddress
    MAX-ACCESS  read-only
    STATUS      current
    DESCRIPTION
        "As MAC address format, it is used to identify BSS."
    ::= { hpnicfDot11RadioSSIDCfgEntry 5 }

hpnicfDot11RadioSSIDRowStatus OBJECT-TYPE
    SYNTAX      RowStatus
    MAX-ACCESS  read-create
    STATUS      current
    DESCRIPTION
        "RowStatus."
    ::= { hpnicfDot11RadioSSIDCfgEntry 6 }

-- *****************************************************************************
-- *  hpnicfDot11APSerialIDTable Definition
-- *****************************************************************************

hpnicfDot11APSerialIDTable OBJECT-TYPE
    SYNTAX      SEQUENCE OF HpnicfDot11APSerialIDEntry
    MAX-ACCESS  not-accessible
    STATUS      current
    DESCRIPTION
        "The table will provide the general information about APs."
    ::= { hpnicfDot11APConfigGroup 10 }

hpnicfDot11APSerialIDEntry OBJECT-TYPE
    SYNTAX      HpnicfDot11APSerialIDEntry
    MAX-ACCESS  not-accessible
    STATUS      current
    DESCRIPTION
        "Each entry contains the general information of an AP."
    INDEX
        {
            hpnicfDot11SIDAPSerialID
        }
    ::= { hpnicfDot11APSerialIDTable 1 }

HpnicfDot11APSerialIDEntry ::= SEQUENCE
    {
        hpnicfDot11SIDAPSerialID               OCTET STRING,
        hpnicfDot11SIDAPWorkMode               INTEGER,
        hpnicfDot11SIDAPGetIPMethod            INTEGER,
        hpnicfDot11SIDAPTemplateName           OCTET STRING,
        hpnicfDot11SIDModelAlias               OCTET STRING,
        hpnicfDot11SIDAPDescription            OCTET STRING,
        hpnicfDot11SIDRowStatus                RowStatus,
        hpnicfDot11SIDAPName                   OCTET STRING,
        hpnicfDot11SIDStatisInterv             Integer32,
        hpnicfDot11SIDAPBroadcastProbeReply    TruthValue,
        hpnicfDot11SIDAPStaIdleTimerInterv     Integer32,
        hpnicfDot11SIDStaKeepAliveTimerInterv  Integer32,
        hpnicfDot11SIDAPCir                    Integer32,
        hpnicfDot11SIDAPCbs                    Integer32,
        hpnicfDot11SIDAPPriorityLevel          Integer32,
        hpnicfDot11SIDAPElementID              Integer32,
        hpnicfDot11SIDAPDevDetectEnable        TruthValue,
        hpnicfDot11SIDAPStatisIntervMode       INTEGER,
        hpnicfDot11SIDAPWorkModeCM             INTEGER
    }

hpnicfDot11SIDAPSerialID OBJECT-TYPE
    SYNTAX      OCTET STRING
    MAX-ACCESS  not-accessible
    STATUS      current
    DESCRIPTION
        "Represents AP serial id."
    ::= { hpnicfDot11APSerialIDEntry 1 }

hpnicfDot11SIDAPWorkMode OBJECT-TYPE
    SYNTAX      INTEGER
        {
            normal(1),
            monitor(2),
            hybrid(3)
        }
    MAX-ACCESS  read-create
    STATUS      current
    DESCRIPTION
        "Represents what work mode for AP.
        The following values are supported:
        normal   - AP will supply WLAN service.
        monitor  - AP will be a monitor to find attack.
        hybrid   - AP will supply WLAN service and Device detection is
        enabled."
    DEFVAL      { normal }
    ::= { hpnicfDot11APSerialIDEntry 2 }

hpnicfDot11SIDAPGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { hpnicfDot11APSerialIDEntry 3 }
hpnicfDot11SIDAPTemplateName OBJECT-TYPE
    SYNTAX      OCTET STRING
    MAX-ACCESS  read-create
    STATUS      current
    DESCRIPTION
        "Represents the name of AP template."
    ::= { hpnicfDot11APSerialIDEntry 4 }
hpnicfDot11SIDModelAlias OBJECT-TYPE
    SYNTAX      OCTET STRING
    MAX-ACCESS  read-create
    STATUS      current
    DESCRIPTION
        "Represents the alias of AP model name."
    ::= { hpnicfDot11APSerialIDEntry 5 }

hpnicfDot11SIDAPDescription OBJECT-TYPE
    SYNTAX      OCTET STRING
    MAX-ACCESS  read-create
    STATUS      current
    DESCRIPTION
        "This attribute will give more information about AP.
        Administrator could suggest the location, owner or
        other information for each AP.
        If the value is set to NULL, the description will be removed."
    ::= { hpnicfDot11APSerialIDEntry 6 }

hpnicfDot11SIDRowStatus OBJECT-TYPE
    SYNTAX      RowStatus
    MAX-ACCESS  read-create
    STATUS      current
    DESCRIPTION
        "The status of this table entry."
    ::= { hpnicfDot11APSerialIDEntry 7 }

hpnicfDot11SIDAPName OBJECT-TYPE
    SYNTAX      OCTET STRING
    MAX-ACCESS  read-create
    STATUS      current
    DESCRIPTION
        "Represents the AP name."
    ::= { hpnicfDot11APSerialIDEntry 8 }

hpnicfDot11SIDStatisInterv OBJECT-TYPE
    SYNTAX      Integer32
    UNITS       "second"
    MAX-ACCESS  read-create
    STATUS      current
    DESCRIPTION
        "Represents the interval of radio statistic."
    ::= { hpnicfDot11APSerialIDEntry 9 }

hpnicfDot11SIDAPBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { hpnicfDot11APSerialIDEntry 10 }

hpnicfDot11SIDAPStaIdleTimerInterv OBJECT-TYPE
    SYNTAX      Integer32
    UNITS       "second"
    MAX-ACCESS  read-create
    STATUS      current
    DESCRIPTION
        "Represents the interval for which the link between AP and STA
        ( power-save or awake ) can be idle."
    ::= { hpnicfDot11APSerialIDEntry 11 }

hpnicfDot11SIDStaKeepAliveTimerInterv OBJECT-TYPE
    SYNTAX      Integer32
    UNITS       "second"
    MAX-ACCESS  read-create
    STATUS      current
    DESCRIPTION
        "Represents the interval of the keep alive requests sent between
        AP and STA."
    ::= { hpnicfDot11APSerialIDEntry 12 }

hpnicfDot11SIDAPCir OBJECT-TYPE
    SYNTAX      Integer32
    UNITS       "Kbps"
    MAX-ACCESS  read-create
    STATUS      current
    DESCRIPTION
        "Represents the committed information rate between AP and AC."
    ::= { hpnicfDot11APSerialIDEntry 13 }

hpnicfDot11SIDAPCbs OBJECT-TYPE
    SYNTAX      Integer32
    UNITS       "Bytes"
    MAX-ACCESS  read-create
    STATUS      current
    DESCRIPTION
        "Represents the committed burst size between AP and AC."
    ::= { hpnicfDot11APSerialIDEntry 14 }

hpnicfDot11SIDAPPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { hpnicfDot11APSerialIDEntry 15 }

hpnicfDot11SIDAPElementID OBJECT-TYPE
    SYNTAX      Integer32
    MAX-ACCESS  read-only
    STATUS      current
    DESCRIPTION
        "This object represents the AP element ID."
    ::= { hpnicfDot11APSerialIDEntry 16 }

hpnicfDot11SIDAPDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services. When an AP works
         in monitor mode, that is, the value of object hpnicfDot11APWorkMode is
         monitor, device detection can not be enabled with object
         hpnicfDot11SIDAPDevDetectEnable."
    DEFVAL      { false }
    ::= { hpnicfDot11APSerialIDEntry 17 }

hpnicfDot11SIDAPStatisIntervMode OBJECT-TYPE
    SYNTAX      INTEGER
    {
        normal(1),
        realtime(2)
    }
    MAX-ACCESS  read-create
    STATUS      current
    DESCRIPTION
        "This object represents the mode of statics interval.
         normal    - statics interval value between 10s to 120s
         realtime  - statics interval value between 2s to 5s"
    DEFVAL      { normal }
    ::= { hpnicfDot11APSerialIDEntry 18 }

hpnicfDot11SIDAPWorkModeCM OBJECT-TYPE
    SYNTAX      INTEGER
        {
            normal(0),
            monitor(1),
            semimonitor(2)
        }
    MAX-ACCESS  read-create
    STATUS      current
    DESCRIPTION
        "Represents what work mode for AP.
        The following values are supported:
        normal   - AP will supply WLAN service.
        monitor  - AP will be a monitor to find attack.
        SemiMonitor   - AP will supply WLAN service and Device detection is
        enabled."
    DEFVAL      { normal }
    ::= { hpnicfDot11APSerialIDEntry 19 }
-- *****************************************************************************
-- *  hpnicfDot11RadioIntfConfigTable Definition
-- *****************************************************************************
hpnicfDot11RadioIntfConfigTable OBJECT-TYPE
    SYNTAX      SEQUENCE OF HpnicfDot11RadioIntfConfigEntry
    MAX-ACCESS  not-accessible
    STATUS      current
    DESCRIPTION
        "The table defines the parameters for radio in AP, as per
        radio."
    ::= { hpnicfDot11RadioIntfConfigGroup 1 }

hpnicfDot11RadioIntfConfigEntry OBJECT-TYPE
    SYNTAX      HpnicfDot11RadioIntfConfigEntry
    MAX-ACCESS  not-accessible
    STATUS      current
    DESCRIPTION
        "Each entry contains information of each radio in AP."
    INDEX
        {
            hpnicfDot11RadioIfIdx
        }
    ::= { hpnicfDot11RadioIntfConfigTable 1 }

HpnicfDot11RadioIntfConfigEntry ::= SEQUENCE
    {
        hpnicfDot11RadioIfIdx               Integer32,
        hpnicfDot11RadioCfgBeaconIntvl      Integer32,
        hpnicfDot11RadioCfgDtimIntvl        Integer32,
        hpnicfDot11RadioCfgRtsThreshold     Integer32,
        hpnicfDot11RadioCfgFragThreshold    Integer32,
        hpnicfDot11RadioCfgShtRetryThld     Integer32,
        hpnicfDot11RadioCfglongRtrThld      Integer32,
        hpnicfDot11RadioCfgMaxRxLifetime    Unsigned32,
        hpnicfDot11RadioCfgType             HpnicfDot11RadioType,
        hpnicfDot11RadioCfgChannel          HpnicfDot11ChannelScopeType,
        hpnicfDot11RadioCfgMaxTxPwrLvl      HpnicfDot11TxPwrLevelScopeType,
        hpnicfDot11RadioCfgPreambleLen      HpnicfDot11PreambleType,
        hpnicfDot11RadioCfgWorkMode         HpnicfDot11WorkMode,
        hpnicfDot11RadioCfgOnly11gEnable    TruthValue,
        hpnicfDot11RadioCfgType2            HpnicfDot11RadioType2,
        hpnicfDot11RadioCfgRssithresholdCM  Integer32
    }

hpnicfDot11RadioIfIdx OBJECT-TYPE
    SYNTAX      Integer32
    MAX-ACCESS  not-accessible
    STATUS      current
    DESCRIPTION
        "Represents the Radio IfIndex of radio in AP."
    ::= { hpnicfDot11RadioIntfConfigEntry 1 }

hpnicfDot11RadioCfgBeaconIntvl OBJECT-TYPE
    SYNTAX      Integer32
    UNITS       "TU"
    MAX-ACCESS  read-write
    STATUS      current
    DESCRIPTION
        "Represents the interval for Beacon management frame."
    DEFVAL { 100 }
    ::= { hpnicfDot11RadioIntfConfigEntry 2 }

hpnicfDot11RadioCfgDtimIntvl OBJECT-TYPE
    SYNTAX      Integer32
    MAX-ACCESS  read-write
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL { 1 }
    ::= { hpnicfDot11RadioIntfConfigEntry 3 }

hpnicfDot11RadioCfgRtsThreshold OBJECT-TYPE
    SYNTAX      Integer32
    UNITS       "Byte"
    MAX-ACCESS  read-write
    STATUS      current
    DESCRIPTION
        "Represents the current minimum size,in octets,of the MAC
        protocol data unit (MPDU), below which a Request to send/Clear
        to send (RTS/CTS) handshake shall not be performed."
    DEFVAL { 2346 }
    ::= { hpnicfDot11RadioIntfConfigEntry 4 }

hpnicfDot11RadioCfgFragThreshold OBJECT-TYPE
    SYNTAX      Integer32
    UNITS       "Byte"
    MAX-ACCESS  read-write
    STATUS      current
    DESCRIPTION
        "Represents the current maximum size, in octets, of the MPDU that
        may be delivered to the PHY. A MSDU shall be broken into
        fragments if its size exceeds the value of this attribute after
        adding MAC headers and trailers."
    DEFVAL { 2346 }
    ::= { hpnicfDot11RadioIntfConfigEntry 5 }

hpnicfDot11RadioCfgShtRetryThld OBJECT-TYPE
    SYNTAX      Integer32
    MAX-ACCESS  read-write
    STATUS      current
    DESCRIPTION
        "Represents the maximum number of transmission attempts of a
        frame, the length of which is less than or equal to
        hpnicfDot11RadioRTSThreshold, that shall be made before a failure
        condition is indicated."
    DEFVAL { 5 }
    ::= { hpnicfDot11RadioIntfConfigEntry 6 }

hpnicfDot11RadioCfglongRtrThld OBJECT-TYPE
    SYNTAX      Integer32
    MAX-ACCESS  read-write
    STATUS      current
    DESCRIPTION
        "Represents the maximum number of transmission attempts of a
        frame, the length of which is longer than
        hpnicfDot11RadioRTSThreshold, that shall be made before a
        failure condition is indicated."
    DEFVAL { 5 }
    ::= { hpnicfDot11RadioIntfConfigEntry 7 }

hpnicfDot11RadioCfgMaxRxLifetime OBJECT-TYPE
    SYNTAX      Unsigned32
    UNITS       "millisecond"
    MAX-ACCESS  read-write
    STATUS      current
    DESCRIPTION
        "Represents the elapsed time. After the time specified by
        hpnicfDot11RadioCfgMaxRxLifetime, the further attempts to reassemble
        the MSDU shall be terminated."
    DEFVAL { 2000 }
    ::= { hpnicfDot11RadioIntfConfigEntry 8 }

hpnicfDot11RadioCfgType OBJECT-TYPE
    SYNTAX      HpnicfDot11RadioType
    MAX-ACCESS  read-write
    STATUS      current
    DESCRIPTION
        "Represents the radio will work with which 802.11 radio type."
    ::= { hpnicfDot11RadioIntfConfigEntry 9 }

hpnicfDot11RadioCfgChannel OBJECT-TYPE
    SYNTAX      HpnicfDot11ChannelScopeType
    MAX-ACCESS  read-write
    STATUS      current
    DESCRIPTION
        "Represents the channel allocation of radio."
    DEFVAL { 1 }
    ::= { hpnicfDot11RadioIntfConfigEntry 10 }

hpnicfDot11RadioCfgMaxTxPwrLvl OBJECT-TYPE
    SYNTAX      HpnicfDot11TxPwrLevelScopeType
    UNITS       "dbm"
    MAX-ACCESS  read-write
    STATUS      current
    DESCRIPTION
        "Represents the maximal transmit power scope for AP."
    ::= { hpnicfDot11RadioIntfConfigEntry 11 }

hpnicfDot11RadioCfgPreambleLen OBJECT-TYPE
    SYNTAX      HpnicfDot11PreambleType
    MAX-ACCESS  read-write
    STATUS      current
    DESCRIPTION
        "Represents whether use long or short preamble for 802.11 MAC
        frame."
    DEFVAL { short }
    ::= { hpnicfDot11RadioIntfConfigEntry 12 }

hpnicfDot11RadioCfgWorkMode OBJECT-TYPE
    SYNTAX      HpnicfDot11WorkMode
    MAX-ACCESS  read-write
    STATUS      current
    DESCRIPTION
        "Represents work mode of the radio."
    ::= { hpnicfDot11RadioIntfConfigEntry 13 }

hpnicfDot11RadioCfgOnly11gEnable OBJECT-TYPE
    SYNTAX      TruthValue
    MAX-ACCESS  read-write
    STATUS      current
    DESCRIPTION
        "Represents whether enable only 802.11g radio mode or not.
        'true' : Only 802.11g radio mode is enabled.
        'false': Only 802.11g radio mode is disabled."
    DEFVAL { false }
    ::= { hpnicfDot11RadioIntfConfigEntry 14 }

hpnicfDot11RadioCfgType2 OBJECT-TYPE
    SYNTAX      HpnicfDot11RadioType2
    MAX-ACCESS  read-write
    STATUS      current
    DESCRIPTION
        "Represents the radio will work with which 802.11 radio type."
    ::= { hpnicfDot11RadioIntfConfigEntry 15 }

hpnicfDot11RadioCfgRssithresholdCM OBJECT-TYPE
    SYNTAX      Integer32
    UNITS       "dBm"
    MAX-ACCESS  read-write
    STATUS      current
    DESCRIPTION
        "Represents the minimum value of the RSSI.
        The clients with RSSI below this value will be refused to associate."
    DEFVAL { 1 }
    ::= { hpnicfDot11RadioIntfConfigEntry 16 }

-- *****************************************************************************
-- *  End of hpnicfDot11RadioIntfConfigTable Definition
-- *****************************************************************************

-- *****************************************************************************
-- *  hpnicfDot11RadioIntfBindTable Definition
-- *****************************************************************************
hpnicfDot11RadioIntfBindTable OBJECT-TYPE
    SYNTAX      SEQUENCE OF HpnicfDot11RadioIntfBindEntry
    MAX-ACCESS  not-accessible
    STATUS      current
    DESCRIPTION
        "The table defines the binding information for each radio in AP.
        "
    ::= { hpnicfDot11RadioIntfConfigGroup 2 }

hpnicfDot11RadioIntfBindEntry OBJECT-TYPE
    SYNTAX      HpnicfDot11RadioIntfBindEntry
    MAX-ACCESS  not-accessible
    STATUS      current
    DESCRIPTION
        "Each entry contains the radio interface binding information
        in AP."
    INDEX
        {
            hpnicfDot11RadioIfIdx,
            hpnicfDot11RadioIntfBindSvcPlcyID
        }
    ::= { hpnicfDot11RadioIntfBindTable 1 }

HpnicfDot11RadioIntfBindEntry ::= SEQUENCE
    {
        hpnicfDot11RadioIntfBindSvcPlcyID    HpnicfDot11ServicePolicyIDType,
        hpnicfDot11RadioIntfBindIfIdx        Unsigned32,
        hpnicfDot11RadioIntfBindRowStatus    RowStatus
    }

hpnicfDot11RadioIntfBindSvcPlcyID OBJECT-TYPE
    SYNTAX      HpnicfDot11ServicePolicyIDType
    MAX-ACCESS  not-accessible
    STATUS      current
    DESCRIPTION
        "Represents the ID of each service policy."
    ::= { hpnicfDot11RadioIntfBindEntry 1 }

hpnicfDot11RadioIntfBindIfIdx OBJECT-TYPE
    SYNTAX      Unsigned32
    MAX-ACCESS  read-create
    STATUS      current
    DESCRIPTION
        "Represents the Ifindex of interface which is binded to
        the radio."
    ::= { hpnicfDot11RadioIntfBindEntry 2 }

hpnicfDot11RadioIntfBindRowStatus OBJECT-TYPE
    SYNTAX      RowStatus
    MAX-ACCESS  read-create
    STATUS      current
    DESCRIPTION
        "The status of this table entry."
    ::= { hpnicfDot11RadioIntfBindEntry 3 }
-- *****************************************************************************
-- *  End of hpnicfDot11RadioIntfBindTable Definition
-- *****************************************************************************

-- *****************************************************************************
-- *  hpnicfDot11DataRateConfigTable Definition
-- *****************************************************************************
hpnicfDot11DataRateConfigTable OBJECT-TYPE
    SYNTAX      SEQUENCE OF HpnicfDot11DataRateConfigEntry
    MAX-ACCESS  not-accessible
    STATUS      current
    DESCRIPTION
        "Table will provide data rate configuration for a specific radio type."
    ::= { hpnicfDot11DataRateConfigGroup 1 }

hpnicfDot11DataRateConfigEntry OBJECT-TYPE
    SYNTAX      HpnicfDot11DataRateConfigEntry
    MAX-ACCESS  not-accessible
    STATUS      current
    DESCRIPTION
        "Each entry of the table will provide data rate configuration for a
        specific radio type."
    INDEX
        {
            hpnicfDot11RadioTypeID
        }
    ::= { hpnicfDot11DataRateConfigTable 1 }

HpnicfDot11DataRateConfigEntry ::= SEQUENCE
    {
        hpnicfDot11RadioTypeID         HpnicfDot11RadioType,
        hpnicfDot11SupportedRateSet    OCTET STRING,
        hpnicfDot11MandatoryRateSet    OCTET STRING,
        hpnicfDot11DisabledRateSet     OCTET STRING,
        hpnicfDot11SmartRateSet        OCTET STRING
    }

hpnicfDot11RadioTypeID OBJECT-TYPE
    SYNTAX      HpnicfDot11RadioType
    MAX-ACCESS  not-accessible
    STATUS      current
    DESCRIPTION
        "Represents the radio type."
    ::= { hpnicfDot11DataRateConfigEntry 1 }

hpnicfDot11SupportedRateSet OBJECT-TYPE
    SYNTAX      OCTET STRING(SIZE(0..255))
    MAX-ACCESS  read-write
    STATUS      current
    DESCRIPTION
        "Represents the supported rate set of a particular radio type."
    ::= { hpnicfDot11DataRateConfigEntry 2 }

hpnicfDot11MandatoryRateSet OBJECT-TYPE
    SYNTAX      OCTET STRING(SIZE(0..255))
    MAX-ACCESS  read-write
    STATUS      current
    DESCRIPTION
        "Represents the mandatory rate set of a particular radio type."
    ::= { hpnicfDot11DataRateConfigEntry 3 }

hpnicfDot11DisabledRateSet OBJECT-TYPE
    SYNTAX      OCTET STRING(SIZE(0..255))
    MAX-ACCESS  read-write
    STATUS      current
    DESCRIPTION
        "Represents the disabled rate set of a particular radio type."
    ::= { hpnicfDot11DataRateConfigEntry 4 }

hpnicfDot11SmartRateSet OBJECT-TYPE
    SYNTAX      OCTET STRING(SIZE(0..255))
    MAX-ACCESS  read-write
    STATUS      current
    DESCRIPTION
        "Represents the rate set of a particular radio type."
    ::= { hpnicfDot11DataRateConfigEntry 5 }
-- *****************************************************************************
-- *  End of hpnicfDot11DataRateConfigTable Definition
-- *****************************************************************************

-- *****************************************************************************
-- *  hpnicfDot11WlanEssIfTable Definition
-- *************************************************************************

hpnicfDot11WlanEssIfTable OBJECT-TYPE
    SYNTAX      SEQUENCE OF HpnicfDot11WlanEssIfEntry
    MAX-ACCESS  not-accessible
    STATUS      current
    DESCRIPTION
        "This table is used to configure WLAN ESS interface."
    ::= { hpnicfDot11InterfaceConfigGroup 1 }

hpnicfDot11WlanEssIfEntry OBJECT-TYPE
    SYNTAX      HpnicfDot11WlanEssIfEntry
    MAX-ACCESS  not-accessible
    STATUS      current
    DESCRIPTION
        "Each entry contains the WLAN ESS interface configuration."
    INDEX
        {
            hpnicfDot11WlanEssIfNumber
        }
    ::= { hpnicfDot11WlanEssIfTable 1 }

HpnicfDot11WlanEssIfEntry ::= SEQUENCE
    {
        hpnicfDot11WlanEssIfNumber      Integer32,
        hpnicfDot11WlanEssIfIndex       Integer32,
        hpnicfDot11WlanEssRowStatus     RowStatus
    }

hpnicfDot11WlanEssIfNumber OBJECT-TYPE
    SYNTAX      Integer32
    MAX-ACCESS  not-accessible
    STATUS      current
    DESCRIPTION
        "This node represents the WLAN ESS interface number."
    ::= { hpnicfDot11WlanEssIfEntry 1 }

hpnicfDot11WlanEssIfIndex OBJECT-TYPE
    SYNTAX      Integer32
    MAX-ACCESS  read-only
    STATUS      current
    DESCRIPTION
        "This node represents the ifIndex of WLAN-ESS interface."
    ::= { hpnicfDot11WlanEssIfEntry 2 }

hpnicfDot11WlanEssRowStatus OBJECT-TYPE
    SYNTAX      RowStatus
    MAX-ACCESS  read-create
    STATUS      current
    DESCRIPTION
        "This node represents the WLAN ESS interface row status."
    ::= { hpnicfDot11WlanEssIfEntry 3 }

-- *****************************************************************************
-- *  End of hpnicfDot11WlanEssIfTable  Definition
-- *****************************************************************************
-- *****************************************************************************
-- *  hpnicfDot11WlanBssIfTable Definition
-- *************************************************************************

hpnicfDot11WlanBssIfTable OBJECT-TYPE
    SYNTAX      SEQUENCE OF HpnicfDot11WlanBssIfEntry
    MAX-ACCESS  not-accessible
    STATUS      current
    DESCRIPTION
        "This table is used to configure WLAN BSS interface."
    ::= { hpnicfDot11InterfaceConfigGroup 2 }

hpnicfDot11WlanBssIfEntry OBJECT-TYPE
    SYNTAX      HpnicfDot11WlanBssIfEntry
    MAX-ACCESS  not-accessible
    STATUS      current
    DESCRIPTION
        "Each entry contains the WLAN BSS interface configuration."
    INDEX
        {
            hpnicfDot11WlanBssIfNumber
        }
    ::= { hpnicfDot11WlanBssIfTable 1 }

HpnicfDot11WlanBssIfEntry ::= SEQUENCE
    {
        hpnicfDot11WlanBssIfNumber     Integer32,
        hpnicfDot11WlanBssIfIndex      Integer32,
        hpnicfDot11WlanBssRowStatus    RowStatus
    }

hpnicfDot11WlanBssIfNumber OBJECT-TYPE
    SYNTAX      Integer32
    MAX-ACCESS  not-accessible
    STATUS      current
    DESCRIPTION
        "This node represents the WLAN BSS interface number."
    ::= { hpnicfDot11WlanBssIfEntry 1 }

hpnicfDot11WlanBssIfIndex OBJECT-TYPE
    SYNTAX      Integer32
    MAX-ACCESS  read-only
    STATUS      current
    DESCRIPTION
        "This node represents the ifIndex of WLAN-BSS interface."
    ::= { hpnicfDot11WlanBssIfEntry 2 }

hpnicfDot11WlanBssRowStatus OBJECT-TYPE
    SYNTAX      RowStatus
    MAX-ACCESS  read-create
    STATUS      current
    DESCRIPTION
        "This node represents the WLAN BSS interface row status."
    ::= { hpnicfDot11WlanBssIfEntry 3 }

-- *****************************************************************************
-- *  End of hpnicfDot11WlanBssIfTable Definition
-- *****************************************************************************
-- *****************************************************************************
-- *  hpnicfDot11WLANEthernetIfTable Definition
-- *************************************************************************

hpnicfDot11WLANEthernetIfTable OBJECT-TYPE
    SYNTAX      SEQUENCE OF HpnicfDot11WLANEthernetIfEntry
    MAX-ACCESS  not-accessible
    STATUS      current
    DESCRIPTION
        "This table is used to configure WLAN Ethernet interface."
    ::= { hpnicfDot11InterfaceConfigGroup 3 }

hpnicfDot11WLANEthernetIfEntry OBJECT-TYPE
    SYNTAX      HpnicfDot11WLANEthernetIfEntry
    MAX-ACCESS  not-accessible
    STATUS      current
    DESCRIPTION
        "Each entry contains the WLAN Ethernet interface configuration."
    INDEX
        {
            hpnicfDot11WlanEthernetIfNumber
        }
    ::= { hpnicfDot11WLANEthernetIfTable 1 }

HpnicfDot11WLANEthernetIfEntry ::= SEQUENCE
    {
        hpnicfDot11WlanEthernetIfNumber     Integer32,
        hpnicfDot11WLANEthernetIfIndex      Integer32,
        hpnicfDot11WlanEthernetRowStatus    RowStatus
    }

hpnicfDot11WlanEthernetIfNumber OBJECT-TYPE
    SYNTAX      Integer32
    MAX-ACCESS  not-accessible
    STATUS      current
    DESCRIPTION
        "This node represents the WLAN Ethernet interface number."
    ::= { hpnicfDot11WLANEthernetIfEntry 1 }

hpnicfDot11WLANEthernetIfIndex OBJECT-TYPE
    SYNTAX      Integer32
    MAX-ACCESS  read-only
    STATUS      current
    DESCRIPTION
        "This node represents the ifIndex of WLAN-Ethernet interface."
    ::= { hpnicfDot11WLANEthernetIfEntry 2 }

hpnicfDot11WlanEthernetRowStatus OBJECT-TYPE
    SYNTAX      RowStatus
    MAX-ACCESS  read-create
    STATUS      current
    DESCRIPTION
        "This node represents the Wlan Ethernet interface row status."
    ::= { hpnicfDot11WLANEthernetIfEntry 3 }

-- *****************************************************************************
-- *  End of hpnicfDot11DataRateConfigTable Definition
-- *****************************************************************************
-- *****************************************************************************
-- *  hpnicfDot11PortSecurityTable Definition
-- *****************************************************************************
hpnicfDot11PortSecurityTable OBJECT-TYPE
    SYNTAX      SEQUENCE OF HpnicfDot11PortSecurityEntry
    MAX-ACCESS  not-accessible
    STATUS      current
    DESCRIPTION
        "This table defines the WLAN security status for ESS, BSS, mesh and
        WLAN-Ethernet interface which binding the crypto service-template.
        Otherwise, when binding the clear service-template,
        hpnicfPortSecurityTables should be used to configure port security."
    ::= { hpnicfDot11InterfaceConfigGroup 4 }

hpnicfDot11PortSecurityEntry OBJECT-TYPE
    SYNTAX      HpnicfDot11PortSecurityEntry
    MAX-ACCESS  not-accessible
    STATUS      current
    DESCRIPTION
        "There is a row in this table for each ESS, BSS and WLAN-Ethernet
        interface.It is indexed using the object ifIndex in RFC1213-MIB."
    INDEX
        {
            ifIndex
        }
    ::= { hpnicfDot11PortSecurityTable 1 }

HpnicfDot11PortSecurityEntry ::= SEQUENCE
    {
        hpnicfDot11PortSecurityMode                 INTEGER,
        hpnicfDot11SecurityUserLoginTxKeyType       INTEGER,
        hpnicfDot11SecurityPskKeyMode               INTEGER,
        hpnicfDot11SecurityPskKeyString             DisplayString
    }

hpnicfDot11PortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  - The default value,no any security mode is set.

        userLoginSecureExt  - Access to the port is denied until the port
        client is authorized (by 802.1X).

        psk  - Access to the port is denied until the port client is
        authorized (by 802.1X key negotiation).

        macAddressAndPsk  - The MAC address is first authenticated and only if
        this succeeds does the psk then attempt user authentication.

        userLoginSecureExtOrPsk  - This selects both the userLoginSecureExt and
        psk modes together such that either is allowed to authorized access.
        Which mode works for client depends on the client's choice.

        ext  - Access to the port is denied until the port client is
        authenticated (by ext).
        "
    ::= { hpnicfDot11PortSecurityEntry 1 }

hpnicfDot11SecurityUserLoginTxKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { hpnicfDot11PortSecurityEntry 2 }

hpnicfDot11SecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode. When input as pskKeyModePassPhrase,
        hpnicfDot11SecurePskKeyString must be 8 to 63 characters; when input as
        pskKeyModeRawKey, hpnicfDot11SecurePskKeyString must be 64 characters and
        each character must be '0'-'9', 'a'-'f' and 'A'-'F'."
    ::= { hpnicfDot11PortSecurityEntry 3 }

hpnicfDot11SecurityPskKeyString OBJECT-TYPE
    SYNTAX      DisplayString
    MAX-ACCESS  read-write
    STATUS      current
    DESCRIPTION
        "This is the password string used for psk authentication."
    ::= { hpnicfDot11PortSecurityEntry 4 }

-- *****************************************************************************
-- *  End of hpnicfDot11PortSecurityTable Definition
-- *****************************************************************************
-- *****************************************************************************
-- *  hpnicfDot11WlanMeshIfTable Definition
-- *************************************************************************

hpnicfDot11WlanMeshIfTable OBJECT-TYPE
    SYNTAX      SEQUENCE OF HpnicfDot11WlanMeshIfEntry
    MAX-ACCESS  not-accessible
    STATUS      current
    DESCRIPTION
        "This table is used to configure WLAN mesh interface."
    ::= { hpnicfDot11InterfaceConfigGroup 5 }

hpnicfDot11WlanMeshIfEntry OBJECT-TYPE
    SYNTAX      HpnicfDot11WlanMeshIfEntry
    MAX-ACCESS  not-accessible
    STATUS      current
    DESCRIPTION
        "Each entry contains the WLAN mesh interface configuration."
    INDEX
        {
            hpnicfDot11WlanMeshIfNumber
        }
    ::= { hpnicfDot11WlanMeshIfTable 1 }

HpnicfDot11WlanMeshIfEntry ::= SEQUENCE
    {
        hpnicfDot11WlanMeshIfNumber    Integer32,
        hpnicfDot11WlanMeshIfIndex     Integer32,
        hpnicfDot11WlanMeshRowStatus   RowStatus
    }

hpnicfDot11WlanMeshIfNumber OBJECT-TYPE
    SYNTAX      Integer32
    MAX-ACCESS  not-accessible
    STATUS      current
    DESCRIPTION
        "This node represents the WLAN mesh interface number."
    ::= { hpnicfDot11WlanMeshIfEntry 1 }

hpnicfDot11WlanMeshIfIndex OBJECT-TYPE
    SYNTAX      Integer32
    MAX-ACCESS  read-only
    STATUS      current
    DESCRIPTION
        "This node represents the index of WLAN mesh interface."
    ::= { hpnicfDot11WlanMeshIfEntry 2 }

hpnicfDot11WlanMeshRowStatus OBJECT-TYPE
    SYNTAX      RowStatus
    MAX-ACCESS  read-create
    STATUS      current
    DESCRIPTION
        "This node represents the WLAN mesh interface row status."
    ::= { hpnicfDot11WlanMeshIfEntry 3 }

-- *****************************************************************************
-- *  End of hpnicfDot11WlanMeshIfTable Definition
-- *****************************************************************************

-- *****************************************************************************
-- *  hpnicfDot11ACBackupGroup Definition
-- *****************************************************************************
hpnicfDot11BackupACAdrssIP OBJECT-TYPE
    SYNTAX      InetAddress
    MAX-ACCESS  read-write
    STATUS      current
    DESCRIPTION
        "This object represents the backup AC IP address.
        If the backup AC IP address is not configured,
        the object value is 0.0.0.0."
    ::= { hpnicfDot11ACBackupGroup 1 }

hpnicfDot11BackupACAdrssIPv6 OBJECT-TYPE
    SYNTAX      InetAddress
    MAX-ACCESS  read-write
    STATUS      current
    DESCRIPTION
        "This object represents the backup AC IPv6 address.
         If the backup AC IPv6 address is not configured,
         the object value is 0::0."
    ::= { hpnicfDot11ACBackupGroup 2 }

-- *****************************************************************************
-- *  End of hpnicfDot11ACBackupGroup Definition
-- *****************************************************************************

-- *****************************************************************************
-- *  hpnicfDot11RadioElementConfigGroup Definition
-- *****************************************************************************

hpnicfDot11nRadioCfgTable OBJECT-TYPE
    SYNTAX SEQUENCE OF HpnicfDot11nRadioCfgEntry
    MAX-ACCESS not-accessible
    STATUS current
    DESCRIPTION
        "This table is used to configure dot11n on the radio."
    ::= { hpnicfDot11RadioElementConfigGroup 1 }

hpnicfDot11nRadioCfgEntry OBJECT-TYPE
    SYNTAX HpnicfDot11nRadioCfgEntry
    MAX-ACCESS not-accessible
    STATUS current
    DESCRIPTION
        "This entry contains the dot11n configuration on the radio."
    INDEX { hpnicfDot11nRadioCfgIndex }
    ::= { hpnicfDot11nRadioCfgTable 1 }

HpnicfDot11nRadioCfgEntry ::= SEQUENCE
    {
        hpnicfDot11nRadioCfgIndex       HpnicfDot11RadioElementIndex,
        hpnicfDot11nAMpduEnable         TruthValue,
        hpnicfDot11nAMsduEnable         TruthValue,
        hpnicfDot11nClientDot11nOnly    TruthValue,
        hpnicfDot11nChanelBand          INTEGER,
        hpnicfDot11nShortGiEnable       TruthValue,
        hpnicfDot11nClientDot11acOnly   TruthValue
    }

hpnicfDot11nRadioCfgIndex OBJECT-TYPE
    SYNTAX HpnicfDot11RadioElementIndex
    MAX-ACCESS not-accessible
    STATUS current
    DESCRIPTION
        "Represents index of the radio."
    ::= { hpnicfDot11nRadioCfgEntry 1 }

hpnicfDot11nAMpduEnable OBJECT-TYPE
    SYNTAX TruthValue
    MAX-ACCESS read-write
    STATUS current
    DESCRIPTION
        "Enable the function of A-MPDU."
        DEFVAL { true }
    ::= { hpnicfDot11nRadioCfgEntry 2 }

hpnicfDot11nAMsduEnable OBJECT-TYPE
    SYNTAX TruthValue
    MAX-ACCESS read-write
    STATUS current
    DESCRIPTION
        "Enable the function of A-MSDU."
    DEFVAL { true }
    ::= { hpnicfDot11nRadioCfgEntry 3 }

hpnicfDot11nClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { hpnicfDot11nRadioCfgEntry 4 }

hpnicfDot11nChanelBand OBJECT-TYPE
    SYNTAX INTEGER
        {
        mode20(1),
        mode40(2),
        mode80(3)
        }
    MAX-ACCESS read-write
    STATUS current
    DESCRIPTION
        "Specify the bandwidth mode."
    DEFVAL { mode40 }
    ::= { hpnicfDot11nRadioCfgEntry 5 }

hpnicfDot11nShortGiEnable OBJECT-TYPE
    SYNTAX TruthValue
    MAX-ACCESS read-write
    STATUS current
    DESCRIPTION
        "The function of Short GI."
    DEFVAL { true }
    ::= { hpnicfDot11nRadioCfgEntry 6 }

hpnicfDot11nClientDot11acOnly OBJECT-TYPE
    SYNTAX TruthValue
    MAX-ACCESS read-write
    STATUS current
    DESCRIPTION
        "Only permit clients of 11ac mode."
    DEFVAL { false }
    ::= { hpnicfDot11nRadioCfgEntry 7 }

-- *****************************************************************************
-- *  End of hpnicfDot11RadioElementConfigGroup Definition
-- *****************************************************************************

-- *****************************************************************************
-- *  hpnicfDot11RadioWDSTable Definition
-- *****************************************************************************

hpnicfDot11RadioWDSTable OBJECT-TYPE
    SYNTAX      SEQUENCE OF HpnicfDot11RadioWDSEntry
    MAX-ACCESS  not-accessible
    STATUS      current
    DESCRIPTION
        "This table is used to configure WDS on the radio."
    ::= { hpnicfDot11RadioElementConfigGroup 2 }

hpnicfDot11RadioWDSEntry OBJECT-TYPE
    SYNTAX      HpnicfDot11RadioWDSEntry
    MAX-ACCESS  not-accessible
    STATUS      current
    DESCRIPTION
        "Each entry contains the WDS configuration on the radio."
    INDEX
        {
            hpnicfDot11RadioWDSIndex
        }
    ::= { hpnicfDot11RadioWDSTable 1 }

HpnicfDot11RadioWDSEntry ::= SEQUENCE
    {
        hpnicfDot11RadioWDSIndex            HpnicfDot11RadioElementIndex,
        hpnicfDot11RadioWDSMode             INTEGER,
        hpnicfDot11RadioWDSNetWorkID        OCTET STRING,
        hpnicfDot11WDSSecPskKeyMode         INTEGER,
        hpnicfDot11WDSSecPskKeyString       DisplayString
    }

hpnicfDot11RadioWDSIndex OBJECT-TYPE
    SYNTAX      HpnicfDot11RadioElementIndex
    MAX-ACCESS  not-accessible
    STATUS      current
    DESCRIPTION
        "Represents the element index of radio."
    ::= { hpnicfDot11RadioWDSEntry 1 }

hpnicfDot11RadioWDSMode OBJECT-TYPE
    SYNTAX      INTEGER
        {
            nowds(1),
            wds(2)
        }
    MAX-ACCESS  read-write
    STATUS      current
    DESCRIPTION
        "Represents enable the WDS mode or not.
        nowds: The WDS mode is disabled.
        wds  : The WDS mode is enabled"
    DEFVAL      { nowds }
    ::= { hpnicfDot11RadioWDSEntry 2 }

hpnicfDot11RadioWDSNetWorkID OBJECT-TYPE
    SYNTAX      OCTET STRING(SIZE(0..32))
    MAX-ACCESS  read-write
    STATUS      current
    DESCRIPTION
        "Represents the mesh ID of WDS."
    DEFVAL      { "" }
    ::= { hpnicfDot11RadioWDSEntry 3 }

hpnicfDot11WDSSecPskKeyMode OBJECT-TYPE
    SYNTAX      INTEGER
        {
          pskKeyModeNone(1),
          pskKeyModePassPhrase(2),
          pskKeyModeRawKey(3)
        }
    MAX-ACCESS  read-write
    STATUS      current
    DESCRIPTION
        "Represents the PSK mode of WDS."
    DEFVAL      { pskKeyModeNone }
    ::= { hpnicfDot11RadioWDSEntry 4 }

hpnicfDot11WDSSecPskKeyString OBJECT-TYPE
    SYNTAX      DisplayString
    MAX-ACCESS  read-write
    STATUS      current
    DESCRIPTION
        "Represents the PSK value of WDS."
    DEFVAL      { "" }
    ::= { hpnicfDot11RadioWDSEntry 5 }

-- *****************************************************************************
-- *  End of hpnicfDot11RadioWDSTable  Definition
-- *****************************************************************************

-- *****************************************************************************
-- *  hpnicfDot11nRadioCfg2Table Definition
-- *****************************************************************************

hpnicfDot11nRadioCfg2Table OBJECT-TYPE
    SYNTAX SEQUENCE OF HpnicfDot11nRadioCfg2Entry
    MAX-ACCESS not-accessible
    STATUS current
    DESCRIPTION
        "This table is used to configure dot11n on the radio."
    ::= { hpnicfDot11RadioElementConfigGroup 3 }

hpnicfDot11nRadioCfg2Entry OBJECT-TYPE
    SYNTAX HpnicfDot11nRadioCfg2Entry
    MAX-ACCESS not-accessible
    STATUS current
    DESCRIPTION
        "This entry contains the dot11n configuration on the radio."
    INDEX {
              hpnicfDot11nRadioCfg2APIDIndex,
              hpnicfDot11nRadioCfg2RadioIDIndex
          }
    ::= { hpnicfDot11nRadioCfg2Table 1 }

HpnicfDot11nRadioCfg2Entry ::= SEQUENCE
    {
        hpnicfDot11nRadioCfg2APIDIndex           HpnicfDot11ObjectIDType,
        hpnicfDot11nRadioCfg2RadioIDIndex        HpnicfDot11RadioScopeType,
        hpnicfDot11nRadioCfg2AMpduEnable         TruthValue,
        hpnicfDot11nRadioCfg2AMsduEnable         TruthValue,
        hpnicfDot11nRadioCfg2ClientDot11nOnly    TruthValue,
        hpnicfDot11nRadioCfg2ChannelBand          INTEGER,
        hpnicfDot11nRadioCfg2ShortGiEnable       TruthValue,
        hpnicfDot11nRadioCfg2AMpduEnableCM        INTEGER,
        hpnicfDot11nRadioCfg2ChannelBandCM        INTEGER,
        hpnicfDot11nRadioCfg2ShortGiEnableCM      INTEGER,
        hpnicfDot11nRadioCfg2ClientDot11acOnly   TruthValue,
        hpnicfDot11nRadioCfg2ClientDot11nOnlyCM   HpnicfDot11TruthValueCM
    }

hpnicfDot11nRadioCfg2APIDIndex OBJECT-TYPE
    SYNTAX HpnicfDot11ObjectIDType
    MAX-ACCESS not-accessible
    STATUS current
    DESCRIPTION
        "Represents index of the AP."
    ::= { hpnicfDot11nRadioCfg2Entry 1 }

hpnicfDot11nRadioCfg2RadioIDIndex OBJECT-TYPE
    SYNTAX HpnicfDot11RadioScopeType
    MAX-ACCESS not-accessible
    STATUS current
    DESCRIPTION
        "Represents index of the radio."
    ::= { hpnicfDot11nRadioCfg2Entry 2 }

hpnicfDot11nRadioCfg2AMpduEnable OBJECT-TYPE
    SYNTAX TruthValue
    MAX-ACCESS read-write
    STATUS current
    DESCRIPTION
        "Enable the function of A-MPDU."
        DEFVAL { true }
    ::= { hpnicfDot11nRadioCfg2Entry 3 }

hpnicfDot11nRadioCfg2AMsduEnable OBJECT-TYPE
    SYNTAX TruthValue
    MAX-ACCESS read-write
    STATUS current
    DESCRIPTION
        "Enable the function of A-MSDU."
    DEFVAL { true }
    ::= { hpnicfDot11nRadioCfg2Entry 4 }

hpnicfDot11nRadioCfg2ClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { hpnicfDot11nRadioCfg2Entry 5 }

hpnicfDot11nRadioCfg2ChannelBand OBJECT-TYPE
    SYNTAX INTEGER
        {
        mode20(1),
        mode40(2),
        mode80(3)
        }
    MAX-ACCESS read-write
    STATUS current
    DESCRIPTION
        "Specify the bandwidth mode."
    ::= { hpnicfDot11nRadioCfg2Entry 6 }

hpnicfDot11nRadioCfg2ShortGiEnable OBJECT-TYPE
    SYNTAX TruthValue
    MAX-ACCESS read-write
    STATUS current
    DESCRIPTION
        "Enable the function of Short GI."
    DEFVAL { true }
    ::= { hpnicfDot11nRadioCfg2Entry 7 }

hpnicfDot11nRadioCfg2AMpduEnableCM OBJECT-TYPE
    SYNTAX   INTEGER
        {
            off(0),
            on(1)
        }
    MAX-ACCESS read-write
    STATUS current
    DESCRIPTION
        "Enable the function of A-MPDU."
        DEFVAL { on }
    ::= { hpnicfDot11nRadioCfg2Entry 8 }

hpnicfDot11nRadioCfg2ChannelBandCM OBJECT-TYPE
    SYNTAX      INTEGER
        {
            mode40(1),
            mode20(2)
        }
    MAX-ACCESS read-write
    STATUS current
    DESCRIPTION
        "Specify the bandwidth mode."
    ::= { hpnicfDot11nRadioCfg2Entry 9 }

hpnicfDot11nRadioCfg2ShortGiEnableCM OBJECT-TYPE
    SYNTAX    INTEGER
        {
            off(0),
            on(1)
        }
    MAX-ACCESS read-write
    STATUS current
    DESCRIPTION
        "Enable the function of Short GI."
    DEFVAL { on }
    ::= { hpnicfDot11nRadioCfg2Entry 10 }

hpnicfDot11nRadioCfg2ClientDot11acOnly OBJECT-TYPE
    SYNTAX TruthValue
    MAX-ACCESS read-write
    STATUS current
    DESCRIPTION
        "Only permit clients of 11ac mode."
    DEFVAL { false }
    ::= { hpnicfDot11nRadioCfg2Entry 11 }

hpnicfDot11nRadioCfg2ClientDot11nOnlyCM OBJECT-TYPE
    SYNTAX HpnicfDot11TruthValueCM
    MAX-ACCESS read-write
    STATUS current
    DESCRIPTION
        "If radio type is 802.11an or 802.11gn, permit only clients of 11n mode.
        If radio type is 802.11ac, permit clients of both 11n and 11ac mode."
    DEFVAL { dot11false }
    ::= { hpnicfDot11nRadioCfg2Entry 12 }
-- *****************************************************************************
-- *  End of hpnicfDot11nRadioCfg2Table Definition
-- *****************************************************************************

-- *****************************************************************************
-- *  hpnicfDot11CfgNotifyGroup Definition
-- *****************************************************************************
hpnicfDot11CfgNotifications OBJECT IDENTIFIER ::= { hpnicfDot11CfgNotifyGroup 0 }

hpnicfDot11CfgCipherChange NOTIFICATION-TYPE
    OBJECTS
    {
        hpnicfDot11SSIDName,
        hpnicfDot11SecurityCiphers
    }
    STATUS      current
    DESCRIPTION
        "This notification is sent when cipher type of corresponding service
        template is changed."
    ::= { hpnicfDot11CfgNotifications 1 }

hpnicfDot11CfgPSKChange NOTIFICATION-TYPE
    OBJECTS
    {
        hpnicfDot11SSIDName
    }
    STATUS      current
    DESCRIPTION
        "This notification is sent when pre-shared key of corresponding
        service template is changed."
    ::= { hpnicfDot11CfgNotifications 2 }

hpnicfDot11SSIDWepIDConflictTrap NOTIFICATION-TYPE
    OBJECTS
    {
        hpnicfDot11PreConflictTemplateNum,
        hpnicfDot11CurrConflictTemplateNum,
        hpnicfDot11ConflictCipherIdx,
        hpnicfDot11ConfigureAPID,
        hpnicfDot11ConfigureRadioID,
        hpnicfDot11ConfigureAPMacAddress
    }
    STATUS      current
    DESCRIPTION
        "This notification will be sent when the same wep ID is configured
         on two service policies."
    ::= { hpnicfDot11CfgNotifications 3 }

-- CFG Notification variable object

hpnicfDot11CfgTrapVarObjects OBJECT IDENTIFIER
    ::= { hpnicfDot11CfgNotifyGroup 1 }

hpnicfDot11PreConflictTemplateNum OBJECT-TYPE
    SYNTAX      Integer32 (1..1024)
    MAX-ACCESS  accessible-for-notify
    STATUS      current
    DESCRIPTION
        "Represents previous service policy ID when radio bind service policy
         and current service policy conflict with previous service policy
         in cipher configuration."
    ::= { hpnicfDot11CfgTrapVarObjects 1 }

hpnicfDot11CurrConflictTemplateNum OBJECT-TYPE
    SYNTAX      Integer32 (1..1024)
    MAX-ACCESS  accessible-for-notify
    STATUS      current
    DESCRIPTION
        "Represents current service policy ID when radio bind service policy
         and current service policy conflict with previous service policy
         in cipher configuration."
    ::= { hpnicfDot11CfgTrapVarObjects 2 }

hpnicfDot11ConflictCipherIdx OBJECT-TYPE
    SYNTAX      Integer32 (1..4)
    MAX-ACCESS  accessible-for-notify
    STATUS      current
    DESCRIPTION
        "Represents wep ID that conflicted with."
    ::= { hpnicfDot11CfgTrapVarObjects 3 }

hpnicfDot11ConfigureAPID OBJECT-TYPE
    SYNTAX      HpnicfDot11ObjectIDType
    MAX-ACCESS  accessible-for-notify
    STATUS      current
    DESCRIPTION
        "Represents which AP is configured."
    ::= { hpnicfDot11CfgTrapVarObjects 4 }

hpnicfDot11ConfigureRadioID OBJECT-TYPE
    SYNTAX      HpnicfDot11RadioScopeType
    MAX-ACCESS  accessible-for-notify
    STATUS      current
    DESCRIPTION
        "Represents which radio in AP is configured."
    ::= { hpnicfDot11CfgTrapVarObjects 5 }

hpnicfDot11ConfigureAPMacAddress OBJECT-TYPE
    SYNTAX      MacAddress
    MAX-ACCESS  accessible-for-notify
    STATUS      current
    DESCRIPTION
        "Represents MAC Address of AP."
    ::= { hpnicfDot11CfgTrapVarObjects 6 }

-- *****************************************************************************
-- *  End of hpnicfDot11CfgNotifyGroup Definition
-- *****************************************************************************

END
