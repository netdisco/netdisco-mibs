HP-ICF-LAYER3VLAN-MIB DEFINITIONS ::= BEGIN

    IMPORTS
        OBJECT-TYPE, MODULE-IDENTITY
            FROM SNMPv2-SMI
        MODULE-COMPLIANCE, OBJECT-GROUP
            FROM SNMPv2-CONF
        ifIndex
            FROM IF-MIB
        hpSwitch
            FROM HP-ICF-OID;
        
    hpicfLayer3VlanConfigMIB MODULE-IDENTITY
        LAST-UPDATED "201003230000Z"  -- Mar 23, 2010
        ORGANIZATION "HP Networking"
        CONTACT-INFO "Hewlett Packard Company
                      8000 Foothills Blvd.
                      Roseville, CA 95747"
        DESCRIPTION  "This MIB module describes objects to enable/disable 
	              layer 3 interface on a VLAN for devices in the HP
                      Integrated Communication Facility product line."

        REVISION     "201003230000Z"  -- Mar 23, 2010
        DESCRIPTION  "Initial version."
        ::= { hpSwitch 70 }

-- **********************************************************************
-- LAYER3VLANCONFIG MIB Groups
-- **********************************************************************

    hpicfLayer3VlanConfig  OBJECT IDENTIFIER ::= {hpicfLayer3VlanConfigMIB 1}
    hpicfLayer3VlanConfigConformance OBJECT IDENTIFIER
                                             ::= { hpicfLayer3VlanConfigMIB 2 }

-- **********************************************************************
-- Start of MIB objects
-- **********************************************************************

    hpicfLayer3VlanConfigTable OBJECT-TYPE
        SYNTAX      SEQUENCE OF HpicfLayer3VlanConfigEntry
        MAX-ACCESS  not-accessible
        STATUS      current
        DESCRIPTION "This table contains layer 3 adminStatus
                    configuration information for each VLAN interface."
        ::= { hpicfLayer3VlanConfig 1 }

    hpicfLayer3VlanConfigEntry OBJECT-TYPE
        SYNTAX      HpicfLayer3VlanConfigEntry
        MAX-ACCESS  not-accessible
        STATUS      current
        DESCRIPTION "An entry in the hpicfLayer3VlanConfigEntry contains objects
                    for configuring layer 3 adminStatus for a VLAN interface."
        INDEX    { ifIndex }
        ::= { hpicfLayer3VlanConfigTable 1 }

    HpicfLayer3VlanConfigEntry ::=
        SEQUENCE {
            hpicfLayer3VlanStatus  INTEGER
        }


    hpicfLayer3VlanStatus OBJECT-TYPE
        SYNTAX      INTEGER  {
                       enable(1),
                       disable(2)
                    }                   
        MAX-ACCESS  read-write
        STATUS      current
        DESCRIPTION "The object contains the desired adminStatus of layer 3 on 
                     a VLAN. If set to 'enable' then layer 3(IPv4/IPv6) is 
                     enabled on that VLAN. If set to 'disable' then layer 3 is
                     disabled on that VLAN."
        DEFVAL { enable }
        ::= { hpicfLayer3VlanConfigEntry 1 }

-- **********************************************************************
-- Conformance Information
-- **********************************************************************

    hpicfL3VlanConfigMIBCompliances  OBJECT IDENTIFIER
                                      ::= { hpicfLayer3VlanConfigConformance 1 }
    hpicfLayer3VlanConfigMIBGroups       OBJECT IDENTIFIER 
                                      ::= { hpicfLayer3VlanConfigConformance 2 }

-- ......................................................................
-- Compliance statements
-- ......................................................................

    hpicfL3VlanConfigMIBCompliance MODULE-COMPLIANCE
        STATUS      current
        DESCRIPTION "The compliance statement for HP routers having layer 3
                     enable/disable of All VLANs feature and implementing the 
                     HP-ICF-LAYER3VLAN-MIB."
        MODULE  -- this module
            MANDATORY-GROUPS { hpicfLayer3VlanConfigGroup }

            GROUP       hpicfLayer3VlanConfigGroup
            DESCRIPTION "Support for this group is required for HP routers
                         that run layer 3 enable/disable on All VLANs feature"
        ::= { hpicfL3VlanConfigMIBCompliances 1 }

-- ......................................................................
-- Conformance Groups
-- ......................................................................

    hpicfLayer3VlanConfigGroup OBJECT-GROUP
        OBJECTS     { hpicfLayer3VlanStatus }
        STATUS      current
        DESCRIPTION "A collection of HP proprietary objects to support
                    enabling/disabling layer 3 on VLANs on HP routers."
        ::= { hpicfLayer3VlanConfigMIBGroups 1 }

END
