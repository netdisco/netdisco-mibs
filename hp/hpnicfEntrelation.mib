-- =================================================================
-- Copyright (c) 2010-2013 Hewlett-Packard Development Company, L.P.
--
-- Description: ENTITY RELATION MIB
-- Version: V1.2
-- History:
--   V1.0(Initial version) 19th Aug 2004
--   V1.1 2004-09-10 Exchange MIB objects' sequence, including hpnicfEntRelationType
--                   and hpnicfEntityIndex.
--                   Change subidentifier of hpnicfEntRelationConformance from 3 to 2.
--   V1.2 2004-10-12 updated by gaolong
--        Remove hpnicfEntityIndex, hpnicfEntRelationType from hpnicfEntRelationGroup
--        because they are not-accessible objects.
-- =================================================================
--

    HPN-ICF-ENTRELATION-MIB DEFINITIONS ::= BEGIN

        IMPORTS
            PhysicalIndex
                FROM ENTITY-MIB
            hpnicfCommon
                FROM HPN-ICF-OID-MIB
            OBJECT-GROUP, MODULE-COMPLIANCE
                FROM SNMPv2-CONF
            OBJECT-TYPE, MODULE-IDENTITY
                FROM SNMPv2-SMI
            TEXTUAL-CONVENTION
                FROM SNMPv2-TC;



        hpnicfEntityRelation MODULE-IDENTITY
            LAST-UPDATED "200408190000Z"
            ORGANIZATION
                ""
            CONTACT-INFO
                ""
            DESCRIPTION
                "The private MIB file includes the general relation information
                information of entities.
                Entity MIB is used to express the physical location of the physical
                entities. Other relations, such as stack port pair and combo port
                pair, are not suitable to be implemented in Entity MIB. So this MIB is
                used to  express these relations. "
            ::= { hpnicfCommon 15 }



--  Textual conventions
--
        HpnicfEntRelationType ::= TEXTUAL-CONVENTION
            STATUS current
            DESCRIPTION
                "entRelationType describe the relation type of the two entities
                (indicated by entityIndex and relatedEntityIndex) .
                stackport: this port is a stack port.
                entityIndex is the default uplinkport index,
                and relatedEntityIndex is the default downlinkport index.
                comboport: this port is a combo port.
                entityIndex is the default active port index,
                and relatedEntityIndex is the default inactive port index."
            SYNTAX INTEGER
                {
                stackport(1),
                comboport(2)
                }




--  Node definitions
--
        hpnicfEntRelationObjects OBJECT IDENTIFIER ::= { hpnicfEntityRelation 1 }

--    MIB contains four groups
        hpnicfEntRelation OBJECT IDENTIFIER ::= { hpnicfEntRelationObjects 1 }

        hpnicfEntRelationTable OBJECT-TYPE
            SYNTAX SEQUENCE OF HpnicfEntRelationEntry
            MAX-ACCESS not-accessible
            STATUS current
            DESCRIPTION
                "Entity MIB is used to express the physical location of
                the physical entities. Other relations, such as stack
                port pair and combo port pair, are not suitable to be
                implemented in Entity MIB. This MIB is used to express
                these relations. "
            ::= { hpnicfEntRelation 1 }

        hpnicfEntRelationEntry OBJECT-TYPE
            SYNTAX HpnicfEntRelationEntry
            MAX-ACCESS not-accessible
            STATUS current
            DESCRIPTION
                "The information about a particular physical entity."
            INDEX { hpnicfEntRelationType, hpnicfEntityIndex, hpnicfRelatedEntityIndex }
            ::= { hpnicfEntRelationTable 1 }

        HpnicfEntRelationEntry ::=
            SEQUENCE {
                hpnicfEntRelationType
                    HpnicfEntRelationType,
                hpnicfEntityIndex
                    PhysicalIndex,
                hpnicfRelatedEntityIndex
                    PhysicalIndex
             }

        hpnicfEntRelationType OBJECT-TYPE
            SYNTAX HpnicfEntRelationType
            MAX-ACCESS not-accessible
            STATUS current
            DESCRIPTION
                "The index of hpnicfEntRelationTable.
                entRelationType describe the relation type of the two
                entities(indicated by entityIndex and relatedEntityIndex) "
            ::= { hpnicfEntRelationEntry 1 }

        hpnicfEntityIndex OBJECT-TYPE
            SYNTAX PhysicalIndex
            MAX-ACCESS not-accessible
            STATUS current
            DESCRIPTION
                "The index of hpnicfEntRelationTable.
                entityIndex is the index of the entity.
                This index is identical to entPhysicalIndex in ENTITY-MIB"
            ::= { hpnicfEntRelationEntry 2 }

        hpnicfRelatedEntityIndex OBJECT-TYPE
            SYNTAX PhysicalIndex
            MAX-ACCESS read-only
            STATUS current
            DESCRIPTION
                "The index of hpnicfEntRelationTable.
                relatedEntityIndex is the entity index that entityIndex related to,
                This index is identical to entPhysicalIndex in ENTITY-MIB"
            ::= { hpnicfEntRelationEntry 3 }

--    Conformance and Compliance
        hpnicfEntRelationConformance OBJECT IDENTIFIER ::= { hpnicfEntityRelation 2 }

        hpnicfEntRelationCompliances OBJECT IDENTIFIER ::= { hpnicfEntRelationConformance 1 }


-- this module
        hpnicfEntRelationCompliance MODULE-COMPLIANCE
            STATUS current
            DESCRIPTION
                "The compliance statement for systems supporting this MIB."
            MODULE -- this module
                MANDATORY-GROUPS { hpnicfEntRelationGroup }
            ::= { hpnicfEntRelationCompliances 1 }

        hpnicfEntRelationGroups OBJECT IDENTIFIER ::= { hpnicfEntRelationConformance 2 }

        hpnicfEntRelationGroup OBJECT-GROUP
            OBJECTS { hpnicfRelatedEntityIndex }
            STATUS current
            DESCRIPTION
                "Standard Entity Relation group."
            ::= { hpnicfEntRelationGroups 1 }


    END
