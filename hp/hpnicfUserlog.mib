-- =================================================================
-- Copyright (c) 2010-2013 Hewlett-Packard Development Company, L.P.
--
-- Description:This MIB file is used for management of userlog
--             information.
-- Reference:
-- Version: V1.1
-- History:
--   V1.0
--   31st Mar 2003
--   tianli, initial version
--   V1.1 2005-07-05
--     Modify value range of hpnicfUserlogNatAclNumber and hpnicfUserlogFlowAclNumber
--     by tanbo02122.
--     Update file format by gaolong.
-- =================================================================
HPN-ICF-USERLOG-MIB DEFINITIONS ::= BEGIN

    IMPORTS
            hpnicfRhw
                    FROM HPN-ICF-OID-MIB
            OBJECT-GROUP, MODULE-COMPLIANCE
                    FROM SNMPv2-CONF
            IpAddress, Integer32, Counter32, OBJECT-TYPE,
            MODULE-IDENTITY
                    FROM SNMPv2-SMI;


    hpnicfUserLogMIB MODULE-IDENTITY
            LAST-UPDATED "200304100000Z"          -- April 10, 2003 at 00:00 GMT
            ORGANIZATION
                ""
            CONTACT-INFO
                ""
            DESCRIPTION
                    "The HPN-ICF-USERLOG-MIB contains objects to
                    Manage configuration and Monitor running state
                    for userlog feature."
            ::= { hpnicfRhw 18 }


    hpnicfUserlogObjects OBJECT IDENTIFIER ::= { hpnicfUserLogMIB 1 }


    hpnicfUserlogNatObjects OBJECT IDENTIFIER ::= { hpnicfUserlogObjects 1 }


    hpnicfUserlogNatVersion OBJECT-TYPE
            SYNTAX Integer32
            MAX-ACCESS read-only
            STATUS current
            DESCRIPTION
                    "NAT LOG version. Currently only version 1 is developed."
            ::= { hpnicfUserlogNatObjects 1 }


    hpnicfUserlogNatSyslog OBJECT-TYPE
            SYNTAX Integer32
            MAX-ACCESS read-write
            STATUS current
            DESCRIPTION
                    "
                    NAT LOG format.
                    If 1, LOG format is sysLog.
                    If 0, LOG format is UDP packet.
                    UDP packet is the default format, and is recommended.
                    "
            ::= { hpnicfUserlogNatObjects 2 }


    hpnicfUserlogNatSourceIP OBJECT-TYPE
            SYNTAX IpAddress
            MAX-ACCESS read-write
            STATUS current
            DESCRIPTION
                    "The Source IP address of NAT LOG UDP packet."
            ::= { hpnicfUserlogNatObjects 3 }


    hpnicfUserlogNatFlowBegin OBJECT-TYPE
            SYNTAX Integer32
            MAX-ACCESS read-write
            STATUS current
            DESCRIPTION
                    "
                    Log the NAT flow when it is created.
                    If 1, this function is enabled.
                    If 0, this function is disabled.
                    This function will be used when real-time monitor required.
                    "
            ::= { hpnicfUserlogNatObjects 4 }


    hpnicfUserlogNatActiveTime OBJECT-TYPE
            SYNTAX Integer32
            MAX-ACCESS read-write
            STATUS current
            DESCRIPTION
                    "
                    The active time for long-time existed NAT flow.
                    Unit: minute. Range: 10 minutes ~ 120 minutes.
                    When setting it, NAT flow can be logged after an interval of
                    active time.
                    This function will be used when real-time monitor required.
                    The default value 0 means real-time monitor function is disabled.
                    "
            ::= { hpnicfUserlogNatObjects 5 }


    hpnicfUserlogNatSlotCfgInfoTable OBJECT-TYPE
            SYNTAX SEQUENCE OF HpnicfUserlogNatSlotCfgInfoEntry
            MAX-ACCESS not-accessible
            STATUS current
            DESCRIPTION
                    "A table of NAT LOG configuration information for the
                    specified slot."
            ::= { hpnicfUserlogNatObjects 6 }


    hpnicfUserlogNatSlotCfgInfoEntry OBJECT-TYPE
            SYNTAX HpnicfUserlogNatSlotCfgInfoEntry
            MAX-ACCESS not-accessible
            STATUS current
            DESCRIPTION
                    "NAT LOG Configuration Information Entry for a slot."
            INDEX { hpnicfUserlogNatCfgSlotNumber }
            ::= { hpnicfUserlogNatSlotCfgInfoTable 1 }


    HpnicfUserlogNatSlotCfgInfoEntry ::=
            SEQUENCE {
                    hpnicfUserlogNatCfgSlotNumber
                            Integer32,
                    hpnicfUserlogNatEnable
                            Integer32,
                    hpnicfUserlogNatAclNumber
                            Integer32,
                    hpnicfUserlogNatHostAddress
                            IpAddress,
                    hpnicfUserlogNatUdpPort
                            Integer32
             }

    hpnicfUserlogNatCfgSlotNumber OBJECT-TYPE
            SYNTAX Integer32 (0..15)
            MAX-ACCESS read-only
            STATUS current
            DESCRIPTION
                    "Slot number. Specify which slot is configured with NAT LOG. "
            ::= { hpnicfUserlogNatSlotCfgInfoEntry 1 }


    hpnicfUserlogNatEnable OBJECT-TYPE
            SYNTAX Integer32
            MAX-ACCESS read-write
            STATUS current
            DESCRIPTION
                    "
                    The NAT LOG feature Enable status.
                    If 1, NAT LOG is enbled.
                    If 0, NAT LOG is disabled.
                    "
            ::= { hpnicfUserlogNatSlotCfgInfoEntry 2 }


    hpnicfUserlogNatAclNumber OBJECT-TYPE
            SYNTAX Integer32
            MAX-ACCESS read-write
            STATUS current
            DESCRIPTION
                    "
                    Access-list number.
                    The value 0 means no ACL is specified.
                    Only when NAT LOG is enabled, can ACL be configured.
                    Only NAT flow which match the ACL will be logged.
                    "
            ::= { hpnicfUserlogNatSlotCfgInfoEntry 3 }


    hpnicfUserlogNatHostAddress OBJECT-TYPE
            SYNTAX IpAddress
            MAX-ACCESS read-write
            STATUS current
            DESCRIPTION
                    "The IP address of NAT LOG server. "
            ::= { hpnicfUserlogNatSlotCfgInfoEntry 4 }


    hpnicfUserlogNatUdpPort OBJECT-TYPE
            SYNTAX Integer32 (0..65535)
            MAX-ACCESS read-write
            STATUS current
            DESCRIPTION
                    "The UDP Port Number of NAT LOG UDP packet."
            ::= { hpnicfUserlogNatSlotCfgInfoEntry 5 }


    hpnicfUserlogNatSlotRunInfoTable OBJECT-TYPE
            SYNTAX SEQUENCE OF HpnicfUserlogNatSlotRunInfoEntry
            MAX-ACCESS not-accessible
            STATUS current
            DESCRIPTION
                    "A table of NAT LOG running information for the specified slot."
            ::= { hpnicfUserlogNatObjects 7 }


    hpnicfUserlogNatSlotRunInfoEntry OBJECT-TYPE
            SYNTAX HpnicfUserlogNatSlotRunInfoEntry
            MAX-ACCESS not-accessible
            STATUS current
            DESCRIPTION
                    "NAT LOG Running Information Entry for a slot."
            INDEX { hpnicfUserlogNatRunSlotNumber }
            ::= { hpnicfUserlogNatSlotRunInfoTable 1 }


    HpnicfUserlogNatSlotRunInfoEntry ::=
            SEQUENCE {
                    hpnicfUserlogNatRunSlotNumber
                            Integer32,
                    hpnicfUserlogNatTotalEntries
                            Counter32,
                    hpnicfUserlogNatTotalPackets
                            Counter32,
                    hpnicfUserlogNatFailedEntries
                            Counter32,
                    hpnicfUserlogNatFailedPackets
                            Counter32,
                    hpnicfUserlogNatClearRunStat
                            Integer32
             }

    hpnicfUserlogNatRunSlotNumber OBJECT-TYPE
            SYNTAX Integer32 (0..15)
            MAX-ACCESS read-only
            STATUS current
            DESCRIPTION
                    "Slot number. Specify on which slot the NAT LOG statistics
                    displayed."
            ::= { hpnicfUserlogNatSlotRunInfoEntry 1 }


    hpnicfUserlogNatTotalEntries OBJECT-TYPE
            SYNTAX Counter32
            MAX-ACCESS read-only
            STATUS current
            DESCRIPTION
                    "The total number of NAT flow entries which are logged."
            ::= { hpnicfUserlogNatSlotRunInfoEntry 2 }


    hpnicfUserlogNatTotalPackets OBJECT-TYPE
            SYNTAX Counter32
            MAX-ACCESS read-only
            STATUS current
            DESCRIPTION
                    "The total number of NAT LOG UDP packets generated by the router."
            ::= { hpnicfUserlogNatSlotRunInfoEntry 3 }


    hpnicfUserlogNatFailedEntries OBJECT-TYPE
            SYNTAX Counter32
            MAX-ACCESS read-only
            STATUS current
            DESCRIPTION
                    "The total number of NAT flow entries failed in outputting."
            ::= { hpnicfUserlogNatSlotRunInfoEntry 4 }


    hpnicfUserlogNatFailedPackets OBJECT-TYPE
            SYNTAX Counter32
            MAX-ACCESS read-only
            STATUS current
            DESCRIPTION
                    "The total number of NAT LOG UDP packets failed in outputting."
            ::= { hpnicfUserlogNatSlotRunInfoEntry 5 }


    hpnicfUserlogNatClearRunStat OBJECT-TYPE
            SYNTAX Integer32
            MAX-ACCESS read-write
            STATUS current
            DESCRIPTION
                    "
                    Clear the running statistics for NAT LOG. Write-only.
                    If 1, the running statistics for NAT LOG is resetted.
                    Other value is invalid.
                    "
            ::= { hpnicfUserlogNatSlotRunInfoEntry 6 }


    hpnicfUserlogFlowObjects OBJECT IDENTIFIER ::= { hpnicfUserlogObjects 2 }


    hpnicfUserlogFlowVersion OBJECT-TYPE
            SYNTAX Integer32
            MAX-ACCESS read-only
            STATUS current
            DESCRIPTION
                    "BAS FLOW LOG version. Currently only version 1 is developed."
            ::= { hpnicfUserlogFlowObjects 1 }


    hpnicfUserlogFlowSyslog OBJECT-TYPE
            SYNTAX Integer32
            MAX-ACCESS read-write
            STATUS current
            DESCRIPTION
                    "
                    BAS FLOW LOG format.
                    If 1, LOG format is sysLog.
                    If 0, LOG format is UDP packet.
                    UDP packet is the default format, and is recommended.
                    "
            ::= { hpnicfUserlogFlowObjects 2 }


    hpnicfUserlogFlowSourceIP OBJECT-TYPE
            SYNTAX IpAddress
            MAX-ACCESS read-write
            STATUS current
            DESCRIPTION
                    "The Source IP address of BAS FLOW LOG UDP packet."
            ::= { hpnicfUserlogFlowObjects 3 }


    hpnicfUserlogFlowFlowBegin OBJECT-TYPE
            SYNTAX Integer32
            MAX-ACCESS read-write
            STATUS current
            DESCRIPTION
                    "
                    Log the BAS flow when it is created.
                    If 1, this function is enabled.
                    If 0, this function is disabled.
                    This function will be used when real-time monitor required.
                    "
            ::= { hpnicfUserlogFlowObjects 4 }


    hpnicfUserlogFlowActiveTime OBJECT-TYPE
            SYNTAX Integer32
            MAX-ACCESS read-write
            STATUS current
            DESCRIPTION
                    "
                    The active time for long-time existed BAS flow.
                    Unit: minute. Range: 10 minutes ~ 120 minutes.
                    When setting it, BAS flow can be logged after an internal of
                    active time.
                    This function will be used when real-time monitor required.
                    The default value 0 means real-time monitor function is disabled.
                    "
            ::= { hpnicfUserlogFlowObjects 5 }


    hpnicfUserlogFlowSlotCfgInfoTable OBJECT-TYPE
            SYNTAX SEQUENCE OF HpnicfUserlogFlowSlotCfgInfoEntry
            MAX-ACCESS not-accessible
            STATUS current
            DESCRIPTION
                    "A table of BAS FLOW LOG configuration information for the
                    specified slot."
            ::= { hpnicfUserlogFlowObjects 6 }


    hpnicfUserlogFlowSlotCfgInfoEntry OBJECT-TYPE
            SYNTAX HpnicfUserlogFlowSlotCfgInfoEntry
            MAX-ACCESS not-accessible
            STATUS current
            DESCRIPTION
                    "BAS FLOW LOG Configuration Information Entry for a slot."
            INDEX { hpnicfUserlogFlowCfgSlotNumber }
            ::= { hpnicfUserlogFlowSlotCfgInfoTable 1 }


    HpnicfUserlogFlowSlotCfgInfoEntry ::=
            SEQUENCE {
                    hpnicfUserlogFlowCfgSlotNumber
                            Integer32,
                    hpnicfUserlogFlowEnable
                            Integer32,
                    hpnicfUserlogFlowAclNumber
                            Integer32,
                    hpnicfUserlogFlowHostAddress
                            IpAddress,
                    hpnicfUserlogFlowUdpPort
                            Integer32
             }

    hpnicfUserlogFlowCfgSlotNumber OBJECT-TYPE
            SYNTAX Integer32 (0..15)
            MAX-ACCESS read-only
            STATUS current
            DESCRIPTION
                    "Slot number. Specify which slot is configured with BAS FLOW LOG."
            ::= { hpnicfUserlogFlowSlotCfgInfoEntry 1 }


    hpnicfUserlogFlowEnable OBJECT-TYPE
            SYNTAX Integer32
            MAX-ACCESS read-write
            STATUS current
            DESCRIPTION
                    "
                    The BAS FLOW LOG feature Enable status.
                    If 1, BAS FLOW LOG is enbled.
                    If 0, BAS FLOW LOG is disabled.
                    "
            ::= { hpnicfUserlogFlowSlotCfgInfoEntry 2 }


    hpnicfUserlogFlowAclNumber OBJECT-TYPE
            SYNTAX Integer32
            MAX-ACCESS read-write
            STATUS current
            DESCRIPTION
                    "
                    Access-list number.
                    The value 0 means no ACL is specified.
                    Only when BAS FLOW LOG is enabled, can ACL be configured.
                    Only BAS flow which match the ACL will be logged.
                    "
            ::= { hpnicfUserlogFlowSlotCfgInfoEntry 3 }


    hpnicfUserlogFlowHostAddress OBJECT-TYPE
            SYNTAX IpAddress
            MAX-ACCESS read-write
            STATUS current
            DESCRIPTION
                    "The IP address of BAS FLOW LOG server. "
            ::= { hpnicfUserlogFlowSlotCfgInfoEntry 4 }


    hpnicfUserlogFlowUdpPort OBJECT-TYPE
            SYNTAX Integer32 (0..65535)
            MAX-ACCESS read-write
            STATUS current
            DESCRIPTION
                    "The UDP Port Number of BAS FLOW LOG UDP packet."
            ::= { hpnicfUserlogFlowSlotCfgInfoEntry 5 }


    hpnicfUserlogFlowSlotRunInfoTable OBJECT-TYPE
            SYNTAX SEQUENCE OF HpnicfUserlogFlowSlotRunInfoEntry
            MAX-ACCESS not-accessible
            STATUS current
            DESCRIPTION
                    "A table of BAS FLOW LOG running information for the specified slot."
            ::= { hpnicfUserlogFlowObjects 7 }


    hpnicfUserlogFlowSlotRunInfoEntry OBJECT-TYPE
            SYNTAX HpnicfUserlogFlowSlotRunInfoEntry
            MAX-ACCESS not-accessible
            STATUS current
            DESCRIPTION
                    "Running Information Entry for a slot."
            INDEX { hpnicfUserlogFlowRunSlotNumber }
            ::= { hpnicfUserlogFlowSlotRunInfoTable 1 }


    HpnicfUserlogFlowSlotRunInfoEntry ::=
            SEQUENCE {
                    hpnicfUserlogFlowRunSlotNumber
                            Integer32,
                    hpnicfUserlogFlowTotalEntries
                            Counter32,
                    hpnicfUserlogFlowTotalPackets
                            Counter32,
                    hpnicfUserlogFlowFailedEntries
                            Counter32,
                    hpnicfUserlogFlowFailedPackets
                            Counter32,
                    hpnicfUserlogFlowClearRunStat
                            Integer32
             }

    hpnicfUserlogFlowRunSlotNumber OBJECT-TYPE
            SYNTAX Integer32 (0..15)
            MAX-ACCESS read-only
            STATUS current
            DESCRIPTION
                    "Slot number. Specify on which slot the BAS FLOW LOG
                    statistics displayed."
            ::= { hpnicfUserlogFlowSlotRunInfoEntry 1 }


    hpnicfUserlogFlowTotalEntries OBJECT-TYPE
            SYNTAX Counter32
            MAX-ACCESS read-only
            STATUS current
            DESCRIPTION
                    "The total number of BAS FLOW Entries which are logged."
            ::= { hpnicfUserlogFlowSlotRunInfoEntry 2 }


    hpnicfUserlogFlowTotalPackets OBJECT-TYPE
            SYNTAX Counter32
            MAX-ACCESS read-only
            STATUS current
            DESCRIPTION
                    "The total number of FLOW LOG UDP packet generated by the router."
            ::= { hpnicfUserlogFlowSlotRunInfoEntry 3 }


    hpnicfUserlogFlowFailedEntries OBJECT-TYPE
            SYNTAX Counter32
            MAX-ACCESS read-only
            STATUS current
            DESCRIPTION
                    "The total number of BAS FLOW  entries failed in outputting. "
            ::= { hpnicfUserlogFlowSlotRunInfoEntry 4 }


    hpnicfUserlogFlowFailedPackets OBJECT-TYPE
            SYNTAX Counter32
            MAX-ACCESS read-only
            STATUS current
            DESCRIPTION
                    "The total number of BAS FLOW LOG UDP packet failed in outputting."
            ::= { hpnicfUserlogFlowSlotRunInfoEntry 5 }


    hpnicfUserlogFlowClearRunStat OBJECT-TYPE
            SYNTAX Integer32
            MAX-ACCESS read-write
            STATUS current
            DESCRIPTION
                    "
                    Clear the running statistics for FLOW LOG. Write-only.
                    If 1, the running statistics for FLOW LOG is resetted.
                    Other value is invalid.
                    "
            ::= { hpnicfUserlogFlowSlotRunInfoEntry 6 }


    hpnicfUserlogAccessObjects OBJECT IDENTIFIER ::= { hpnicfUserlogObjects 3 }


    hpnicfUserlogAccessVersion OBJECT-TYPE
            SYNTAX Integer32
            MAX-ACCESS read-only
            STATUS current
            DESCRIPTION
                    "BAS ACCESS LOG version. Currently only version 1 is developed."
            ::= { hpnicfUserlogAccessObjects 1 }


    hpnicfUserlogAccessSyslog OBJECT-TYPE
            SYNTAX Integer32
            MAX-ACCESS read-write
            STATUS current
            DESCRIPTION
                    "
                    BAS ACCESS LOG format.
                    If 1, LOG format is sysLog;
                    If 0, LOG format is UDP packet.
                    UDP packet is the default format, and is recommended.
                    "
            ::= { hpnicfUserlogAccessObjects 2 }


    hpnicfUserlogAccessSourceIP OBJECT-TYPE
            SYNTAX IpAddress
            MAX-ACCESS read-write
            STATUS current
            DESCRIPTION
                    "The Source IP address of BAS ACCESS LOG UDP packet."
            ::= { hpnicfUserlogAccessObjects 3 }


    hpnicfUserlogAccessSlotCfgInfoTable OBJECT-TYPE
            SYNTAX SEQUENCE OF HpnicfUserlogAccessSlotCfgInfoEntry
            MAX-ACCESS not-accessible
            STATUS current
            DESCRIPTION
                    "A table of BAS ACCESS LOG configuration information for the specified slot."
            ::= { hpnicfUserlogAccessObjects 4 }


    hpnicfUserlogAccessSlotCfgInfoEntry OBJECT-TYPE
            SYNTAX HpnicfUserlogAccessSlotCfgInfoEntry
            MAX-ACCESS not-accessible
            STATUS current
            DESCRIPTION
                    "BAS ACCESS LOG Configuration Information Entry for a slot."
            INDEX { hpnicfUserlogAccessCfgSlotNumber }
            ::= { hpnicfUserlogAccessSlotCfgInfoTable 1 }


    HpnicfUserlogAccessSlotCfgInfoEntry ::=
            SEQUENCE {
                    hpnicfUserlogAccessCfgSlotNumber
                            Integer32,
                    hpnicfUserlogAccessEnable
                            Integer32,
                    hpnicfUserlogAccessHostAddress
                            IpAddress,
                    hpnicfUserlogAccessUdpPort
                            Integer32
             }

    hpnicfUserlogAccessCfgSlotNumber OBJECT-TYPE
            SYNTAX Integer32 (0..15)
            MAX-ACCESS read-only
            STATUS current
            DESCRIPTION
                    "Slot number. Specify which slot is configured with BAS ACCESS LOG."
            ::= { hpnicfUserlogAccessSlotCfgInfoEntry 1 }


    hpnicfUserlogAccessEnable OBJECT-TYPE
            SYNTAX Integer32
            MAX-ACCESS read-write
            STATUS current
            DESCRIPTION
                    "
                    The BAS ACCESS LOG feature Enable status.
                    If 1, BAS ACCESS LOG is enbled.
                    If 0, BAS ACCESS LOG is disabled.
                    "
            ::= { hpnicfUserlogAccessSlotCfgInfoEntry 2 }


    hpnicfUserlogAccessHostAddress OBJECT-TYPE
            SYNTAX IpAddress
            MAX-ACCESS read-write
            STATUS current
            DESCRIPTION
                    "The IP address of BAS ACCESS LOG server."
            ::= { hpnicfUserlogAccessSlotCfgInfoEntry 3 }


    hpnicfUserlogAccessUdpPort OBJECT-TYPE
            SYNTAX Integer32 (0..65535)
            MAX-ACCESS read-write
            STATUS current
            DESCRIPTION
                    "The UDP Port Number of BAS ACCESS LOG UDP packet."
            ::= { hpnicfUserlogAccessSlotCfgInfoEntry 4 }


    hpnicfUserlogAccessSlotRunInfoTable OBJECT-TYPE
            SYNTAX SEQUENCE OF HpnicfUserlogAccessSlotRunInfoEntry
            MAX-ACCESS not-accessible
            STATUS current
            DESCRIPTION
                    "A table of BAS ACCESS LOG running information for the specified slot."
            ::= { hpnicfUserlogAccessObjects 5 }


    hpnicfUserlogAccessSlotRunInfoEntry OBJECT-TYPE
            SYNTAX HpnicfUserlogAccessSlotRunInfoEntry
            MAX-ACCESS not-accessible
            STATUS current
            DESCRIPTION
                    "Running Information Entry for a slot."
            INDEX { hpnicfUserlogAccessRunSlotNumber }
            ::= { hpnicfUserlogAccessSlotRunInfoTable 1 }


    HpnicfUserlogAccessSlotRunInfoEntry ::=
            SEQUENCE {
                    hpnicfUserlogAccessRunSlotNumber
                            Integer32,
                    hpnicfUserlogAccessTotalEntries
                            Counter32,
                    hpnicfUserlogAccessTotalPackets
                            Counter32,
                    hpnicfUserlogAccessFailedEntries
                            Counter32,
                    hpnicfUserlogAccessFailedPackets
                            Counter32,
                    hpnicfUserlogAccessClearRunStat
                            Integer32
             }

    hpnicfUserlogAccessRunSlotNumber OBJECT-TYPE
            SYNTAX Integer32 (0..15)
            MAX-ACCESS read-only
            STATUS current
            DESCRIPTION
                    "Slot number. Specify on which slot the BAS ACCESS LOG statistics displayed."
            ::= { hpnicfUserlogAccessSlotRunInfoEntry 1 }


    hpnicfUserlogAccessTotalEntries OBJECT-TYPE
            SYNTAX Counter32
            MAX-ACCESS read-only
            STATUS current
            DESCRIPTION
                    "The total number of BAS ACCESS Records which are logged."
            ::= { hpnicfUserlogAccessSlotRunInfoEntry 2 }


    hpnicfUserlogAccessTotalPackets OBJECT-TYPE
            SYNTAX Counter32
            MAX-ACCESS read-only
            STATUS current
            DESCRIPTION
                    "The total number of ACCESS LOG UDP packet generated by the router."
            ::= { hpnicfUserlogAccessSlotRunInfoEntry 3 }


    hpnicfUserlogAccessFailedEntries OBJECT-TYPE
            SYNTAX Counter32
            MAX-ACCESS read-only
            STATUS current
            DESCRIPTION
                    "The total number of BAS ACCESS entries failed in outputting."
            ::= { hpnicfUserlogAccessSlotRunInfoEntry 4 }


    hpnicfUserlogAccessFailedPackets OBJECT-TYPE
            SYNTAX Counter32
            MAX-ACCESS read-only
            STATUS current
            DESCRIPTION
                    "The total number of BAS ACCESS LOG UDP packet failed in outputting."
            ::= { hpnicfUserlogAccessSlotRunInfoEntry 5 }


    hpnicfUserlogAccessClearRunStat OBJECT-TYPE
            SYNTAX Integer32
            MAX-ACCESS read-write
            STATUS current
            DESCRIPTION
                    "
                    Clear the running statistics for ACCESS LOG. Write-only.
                    If 1, the running statistics for ACCESS LOG is resetted.
                    Other value is invalid.
                    "
            ::= { hpnicfUserlogAccessSlotRunInfoEntry 6 }


    hpnicfUserlogNotifications OBJECT IDENTIFIER ::= { hpnicfUserLogMIB 2 }


    hpnicfUserlogConformance OBJECT IDENTIFIER ::= { hpnicfUserLogMIB 3 }


    hpnicfUserlogCompliances OBJECT IDENTIFIER ::= { hpnicfUserlogConformance 1 }


    hpnicfUserlogCompliance MODULE-COMPLIANCE
            STATUS current
            DESCRIPTION
                    "The compliance statement for entities which implement the
                    Userlog mib."
            MODULE -- this module
                    MANDATORY-GROUPS { hpnicfUserlogMandatoryGroup }
            ::= { hpnicfUserlogCompliances 1 }


    hpnicfUserlogGroups OBJECT IDENTIFIER ::= { hpnicfUserlogConformance 2 }


    hpnicfUserlogMandatoryGroup OBJECT-GROUP
            OBJECTS { hpnicfUserlogNatEnable, hpnicfUserlogNatHostAddress, hpnicfUserlogNatUdpPort,
                      hpnicfUserlogFlowEnable, hpnicfUserlogFlowHostAddress, hpnicfUserlogFlowUdpPort,
                      hpnicfUserlogAccessEnable, hpnicfUserlogAccessHostAddress, hpnicfUserlogAccessUdpPort
                    }
            STATUS current
            DESCRIPTION
                    "A collection of objects providing mandatory Userlog information."
            ::= { hpnicfUserlogGroups 1 }


    hpnicfUserlogConfigGroup OBJECT-GROUP
            OBJECTS { hpnicfUserlogNatVersion, hpnicfUserlogNatSyslog, hpnicfUserlogNatSourceIP,
                      hpnicfUserlogNatFlowBegin, hpnicfUserlogNatActiveTime, hpnicfUserlogNatCfgSlotNumber,
                      hpnicfUserlogNatEnable, hpnicfUserlogNatAclNumber, hpnicfUserlogNatHostAddress,
                      hpnicfUserlogNatUdpPort, hpnicfUserlogFlowVersion, hpnicfUserlogFlowSyslog,
                      hpnicfUserlogFlowSourceIP, hpnicfUserlogFlowFlowBegin, hpnicfUserlogFlowActiveTime,
                      hpnicfUserlogFlowCfgSlotNumber, hpnicfUserlogFlowEnable, hpnicfUserlogFlowAclNumber,
                      hpnicfUserlogFlowHostAddress, hpnicfUserlogFlowUdpPort, hpnicfUserlogAccessVersion,
                      hpnicfUserlogAccessSyslog, hpnicfUserlogAccessSourceIP, hpnicfUserlogAccessCfgSlotNumber,
                      hpnicfUserlogAccessEnable, hpnicfUserlogAccessHostAddress, hpnicfUserlogAccessUdpPort
                    }
            STATUS current
            DESCRIPTION
                    "All configurable parameters of Userlog feature."
            ::= { hpnicfUserlogGroups 2 }


    hpnicfUserlogInfoGroup OBJECT-GROUP
            OBJECTS { hpnicfUserlogNatTotalEntries, hpnicfUserlogNatTotalPackets,
                      hpnicfUserlogNatFailedEntries, hpnicfUserlogNatFailedPackets,
                      hpnicfUserlogFlowTotalEntries, hpnicfUserlogFlowTotalPackets,
                      hpnicfUserlogFlowFailedEntries, hpnicfUserlogFlowFailedPackets,
                      hpnicfUserlogAccessTotalEntries, hpnicfUserlogAccessTotalPackets,
                      hpnicfUserlogAccessFailedEntries, hpnicfUserlogAccessFailedPackets
                    }
            STATUS current
            DESCRIPTION
                    "All running information of Userlog feature."
            ::= { hpnicfUserlogGroups 3 }

END
