-- =============================================================================
-- Copyright (c) 2010-2014 Hewlett-Packard Development Company, L.P.
--
-- Description: Multiprotocol Label Switching Traffic Engineering MIB
-- Reference:
-- Version: V1.0
-- History:
--   V1.0 2013-06-13 Initial version Created by Neng Yan
-- =============================================================================
HPN-ICF-MPLSTE-MIB DEFINITIONS ::= BEGIN
IMPORTS
    MODULE-IDENTITY, OBJECT-TYPE, Unsigned32
        FROM SNMPv2-SMI
    RowStatus, TruthValue
        FROM SNMPv2-TC
    hpnicfCommon
        FROM HPN-ICF-OID-MIB
    ;

-- =============================================================================
-- module identity part
-- =============================================================================
hpnicfMplsTe MODULE-IDENTITY
    LAST-UPDATED
        "201306131800Z"        -- Jan 13, 2013 at 18:00 GMT
    ORGANIZATION
        ""
    CONTACT-INFO
        ""
    DESCRIPTION
        "Multiprotocol Label Switching Traffic Engineering MIB"
    REVISION
        "201306131800Z"   -- Jan 13, 2013 at 18:00 GMT
    DESCRIPTION
        "Initial version of this MIB."
    ::= { hpnicfCommon 143 }

-- =============================================================================
-- object definition begin
-- =============================================================================
hpnicfMplsTeObjects      OBJECT IDENTIFIER ::= { hpnicfMplsTe 1 }

hpnicfMplsTeScalarGroup  OBJECT IDENTIFIER ::= { hpnicfMplsTeObjects 1 }

hpnicfMplsTeStatus    OBJECT-TYPE
    SYNTAX      TruthValue
    MAX-ACCESS  read-write
    STATUS      current
    DESCRIPTION
        "The global configuration of MPLS(Multiprotocol Label Switching)
        TE(Traffic Engineering)."
    ::= { hpnicfMplsTeScalarGroup 1 }

hpnicfMplsTeRsvpStatus    OBJECT-TYPE
    SYNTAX      TruthValue
    MAX-ACCESS  read-write
    STATUS      current
    DESCRIPTION
        "The global configuration of RSVP(Resource Reservation Protocol)."
    ::= { hpnicfMplsTeScalarGroup 2 }

-- =============================================================================
-- hpnicfMplsTeTable Definition
-- =============================================================================
hpnicfMplsTeTable     OBJECT-TYPE
    SYNTAX      SEQUENCE OF HpnicfMplsTeEntry
    MAX-ACCESS  not-accessible
    STATUS      current
    DESCRIPTION
        "A table for configuring MPLS TE parameters."
    ::= { hpnicfMplsTeObjects 2 }

hpnicfMplsTeEntry     OBJECT-TYPE
    SYNTAX      HpnicfMplsTeEntry
    MAX-ACCESS  not-accessible
    STATUS      current
    DESCRIPTION
        "An entry for configuring MPLS TE parameters."
    INDEX
    {
        hpnicfMplsTeIndex
    }
    ::= { hpnicfMplsTeTable 1 }

HpnicfMplsTeEntry ::=
    SEQUENCE
    {
        hpnicfMplsTeIndex                 Unsigned32,
        hpnicfMplsTeCapability            TruthValue,
        hpnicfMplsTeRowStatus             RowStatus
    }

hpnicfMplsTeIndex     OBJECT-TYPE
    SYNTAX      Unsigned32(1..4294967295)
    MAX-ACCESS  not-accessible
    STATUS      current
    DESCRIPTION
        "Index of TE interface."
    ::= { hpnicfMplsTeEntry 1 }

hpnicfMplsTeCapability    OBJECT-TYPE
    SYNTAX      TruthValue
    MAX-ACCESS  read-create
    STATUS      current
    DESCRIPTION
        "The TE capability of an interface."
    DEFVAL { false }
    ::= { hpnicfMplsTeEntry 2 }

hpnicfMplsTeRowStatus     OBJECT-TYPE
    SYNTAX      RowStatus
    MAX-ACCESS  read-create
    STATUS      current
    DESCRIPTION
        "Operation status of this table entry.  A row entry cannot
        be modified when the value of this object is 'active'."
    ::= { hpnicfMplsTeEntry 3 }
-- =============================================================================
-- End of hpnicfMplsTeTable Definition
-- =============================================================================

-- =============================================================================
-- hpnicfMplsTeRsvpTable Definition
-- =============================================================================
hpnicfMplsTeRsvpTable     OBJECT-TYPE
    SYNTAX      SEQUENCE OF HpnicfMplsTeRsvpEntry
    MAX-ACCESS  not-accessible
    STATUS      current
    DESCRIPTION
        "A table for configuring RSVP(Resource Reservation Protocol)
        TE parameters."
    ::= { hpnicfMplsTeObjects 3 }

hpnicfMplsTeRsvpEntry     OBJECT-TYPE
    SYNTAX      HpnicfMplsTeRsvpEntry
    MAX-ACCESS  not-accessible
    STATUS      current
    DESCRIPTION
        "An entry for configuring RSVP TE parameters."
    INDEX
    {
        hpnicfMplsTeRsvpIndex
    }
    ::= { hpnicfMplsTeRsvpTable 1 }

HpnicfMplsTeRsvpEntry ::=
    SEQUENCE
    {
        hpnicfMplsTeRsvpIndex                 Unsigned32,
        hpnicfMplsTeRsvpCapability            TruthValue,
        hpnicfMplsTeRsvpRowStatus             RowStatus
    }

hpnicfMplsTeRsvpIndex     OBJECT-TYPE
    SYNTAX      Unsigned32(1..4294967295)
    MAX-ACCESS  not-accessible
    STATUS      current
    DESCRIPTION
        "Index of RSVP interface."
    ::= { hpnicfMplsTeRsvpEntry 1 }

hpnicfMplsTeRsvpCapability    OBJECT-TYPE
    SYNTAX      TruthValue
    MAX-ACCESS  read-create
    STATUS      current
    DESCRIPTION
        "The RSVP capability of an interface."
    DEFVAL { false }
    ::= { hpnicfMplsTeRsvpEntry 2 }

hpnicfMplsTeRsvpRowStatus     OBJECT-TYPE
    SYNTAX      RowStatus
    MAX-ACCESS  read-create
    STATUS      current
    DESCRIPTION
        "Operation status of this table entry.  A row entry cannot
        be modified when the value of this object is 'active'."
    ::= { hpnicfMplsTeRsvpEntry 3 }
-- =============================================================================
-- End of hpnicfMplsTeRsvpTable Definition
-- =============================================================================

END
