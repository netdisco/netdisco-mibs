-- =================================================================
-- Copyright (c) 2010-2014 Hewlett-Packard Development Company, L.P.
--
-- Description:  Extended MIB File(extended from DISMAN-PING-MIB RFC2925)
-- Reference:
-- Version: V2.5
-- History:
-- V1.0  Lv zhenfeng, 2003.08, Initial Version
-- V1.1 2004-10-12 updated by gaolong
--      Import OBJECT-IDENTITY, Integer32, Counter32, Gauge32.
-- V1.2 Add new column objects
--      hpnicfNqaResultsMaxDelaySD
--      hpnicfNqaResultsMaxDelayDS
--      hpnicfNqaResultsLostPacketRatio
--      under hpnicfNqaResultsTable table by zhaoyujin, 20041101
--  Add new column objects
--      hpnicfNqaJitterStatsAvePositivesSD
--      hpnicfNqaJitterStatsAveNegativesSD
--      hpnicfNqaJitterStatsAvePositivesDS
--      hpnicfNqaJitterStatsAveNegativesDS
--      hpnicfNqaJitterStatsPktLossUnknown
--  under hpnicfNqaJitterStatsTable table by zhaoyujin, 20041101
--      revise words errors
-- V1.3 2004-12-25 updated by zhaoyujin and weixinzhe
--      Objects description updated
-- V1.4 2005-12-22 Modified by qiuchunxia and liqian
--      add hpnicfNqaCtlHistoryKeptTime
--      add hpnicfNqaCtlHistoryEnable
--      add hpnicfNqaStatisticsResultsTable
--      add hpnicfNqaGroupStatsJitterTable
--      add hpnicfNqaStatisticsCtlTable
--      add hpnicfNqaStatsMaxGroupNumber
--      remove definition of InetAddress, and import from INET-ADDRESS-MIB
-- V1.5 2006-03-03 Modified by jinyi and wangqingfeng
--      modified the description of hpnicfNqaStatResRttSequenceErrors
--      modified the description of hpnicfNqaResultsRttSequenceErrors
--      modified UNITS of some objects by jinyi
--      add hpnicfNqaCtlICPIFAdvFactor, hpnicfNqaCtlCodecType in hpnicfNqaCtlTable
--      add hpnicfNqaResultsPacketLateArrival in hpnicfNqaResultsTable
--      add hpnicfNqaJitterStatsOperOfICPIF and hpnicfNqaJitterStatsOperOfMOS
--      in hpnicfNqaJitterStatsTable
--      add hpnicfNqaStatResPacketLateArrival in hpnicfNqaStatisticsResultsTable
--      add hpnicfNqaStatJitterMaxOfICPIF, hpnicfNqaStatJitterMinOfICPIF
--      hpnicfNqaStatJitterMaxOfMOS and hpnicfNqaStatJitterMinOfMOS
--      in hpnicfNqaGroupStatsJitterTable
--      rename subidentifier 5 of hpnicfNqaStatisticsCtlEntry to
--      hpnicfNqaCtlLifeTime by wangqingfeng
--      rename subidentifier 11 of hpnicfNqaStatisticsResultsEntry to
--      hpnicfNqaStatResInterval by wangqingfeng
-- V1.6 2006-05-12
--      rewrite this MIB with prefix "hpnicfNqa".
-- V2.0 2006-08-14 Modified by zhangjun
--      change the name of root from "hpnicfDismanPing" to "hpnicfNqa"
--      modify some mistakes
-- V2.1 2006-08-22 Modified by qiuchunxia, dupengfei and shenjuanjuan
--      add hpnicfNqaReactionTable and add hpnicfNqaNotifications
-- V2.2 2007-03-08 Modified by zhouwenming
--      add hpnicfNqaResultsRttSum, hpnicfNqaResultsNumOfDelaySD, hpnicfNqaResultsMinDelaySD,
--       hpnicfNqaResultsSumDelaySD, hpnicfNqaResultsSum2DelaySD, hpnicfNqaResultsNumOfDelayDS,
--       hpnicfNqaResultsMinDelayDS, hpnicfNqaResultsSumDelayDS, hpnicfNqaResultsSum2DelayDS
--       in hpnicfNqaResultsTable
--      add hpnicfNqaStatResRttSum, hpnicfNqaStatResNumOfDelaySD, hpnicfNqaStatResMinDelaySD,
--       hpnicfNqaStatResSumDelaySD, hpnicfNqaStatResSum2DelaySD, hpnicfNqaStatResNumOfDelayDS,
--       hpnicfNqaStatResMinDelayDS, hpnicfNqaStatResSumDelayDS, hpnicfNqaStatResSum2DelayDS,
--       hpnicfNqaStatResMaxDelaySD, hpnicfNqaStatResMaxDelayDS
--       in hpnicfNqaStatisticsResultsTable
--      add jitterOwdSD, jitterOwdDS to hpnicfNqaReactCheckedElement
--       in hpnicfNqaReactionTable.
--      add hpnicfNqaReactCheckedNum, hpnicfNqaReactThresholdNum in hpnicfNqaReactionTable
--      add hpnicfNqaStatisticsReactionTable
-- V2.3 2007-04-25 Modified by zhouxingyue and zhouhaifeng
--      add icmpTimestamp in hpnicfNqaCtlCodecType
--      remove size limit and DEFVAL in definition of hpnicfNqaCtlStatisticsInterval.
--      modify type of below from  Unsigned32 to Gauge32:
--       hpnicfNqaStatResMinRtt, hpnicfNqaStatResMaxRtt,hpnicfNqaStatResAverageRtt,
--       hpnicfNqaStatResInterval, hpnicfNqaStatResLostPacketRatio, hpnicfNqaStatResMinDelaySD,
--       hpnicfNqaStatResMaxDelaySD,hpnicfNqaStatResMinDelayDS, hpnicfNqaStatResMaxDelayDS.
--      modify type of below from  Unsigned32 to Counter32:
--       hpnicfNqaStatResProbeResponses, hpnicfNqaStatResSentProbes, hpnicfNqaStatResRttSumOfSquares,
--       hpnicfNqaStatResRttNumDisconnects, hpnicfNqaStatResRttTimeouts, hpnicfNqaStatResRttBusies,
--       hpnicfNqaStatResRttNoConnections, hpnicfNqaStatResRttDrops, hpnicfNqaStatResRttSequenceErrors,
--       hpnicfNqaStatResRttErrors, hpnicfNqaStatResPacketLateArrival, hpnicfNqaStatResRttSum,
--       hpnicfNqaStatResNumOfDelaySD, hpnicfNqaStatResSumDelaySD, hpnicfNqaStatResSum2DelaySD,
--       hpnicfNqaStatResNumOfDelayDS, hpnicfNqaStatResSumDelayDS, hpnicfNqaStatResSum2DelayDS,
--       hpnicfNqaStatReactCheckedNum, hpnicfNqaStatReactThresholdNum.
--      modify type of below from  Gauge32 to Counter32:
--       hpnicfNqaStatJitterNumOfPosSD, hpnicfNqaStatJitterSumOfPosSD, hpnicfNqaStatJitterSumOfSquarePosSD,
--       hpnicfNqaStatJitterNumOfNegSD, hpnicfNqaStatJitterSumOfNegSD, hpnicfNqaStatJitterSumOfSquareNegSD,
--       hpnicfNqaStatJitterNumOfPosDS, hpnicfNqaStatJitterSumOfPosDS, hpnicfNqaStatJitterSumOfSquarePosDS,
--       hpnicfNqaStatJitterNumOfNegDS, hpnicfNqaStatJitterSumOfNegDS, hpnicfNqaStatJitterSumOfSquareNegDS,
--       hpnicfNqaStatJitterPacketLossSD, hpnicfNqaStatJitterPacketLossDS, hpnicfNqaStatJitterPktLossUnknown.
-- V2.4 2012-04-20 Modified by sunbiliang and wanghaidong
--      add raw in hpnicfNqaCtlHttpOperationType
--      modifiy the range of hpnicfNqaCtlHttpOperationString
-- V2.5 2013-12-17 Modified by wangbo
--      modify the descriptions of hpnicfNqaCtlICPIFAdvFactor, hpnicfNqaStatJitterNumOfNegSD,
--       hpnicfNqaStatJitterNumOfPosSD, hpnicfNqaStatJitterNumOfPosDS, hpnicfNqaStatJitterNumOfNegDS,
--       hpnicfNqaReactCurrentStatus
-- =================================================================
HPN-ICF-NQA-MIB DEFINITIONS ::= BEGIN

        IMPORTS
            MODULE-IDENTITY, OBJECT-TYPE, Unsigned32,
            OBJECT-IDENTITY, NOTIFICATION-TYPE, Integer32, Counter32, Gauge32
                FROM SNMPv2-SMI
            DateAndTime, DisplayString, RowStatus
                FROM SNMPv2-TC
            InetAddressType, InetAddress
                FROM INET-ADDRESS-MIB
            hpnicfRhw
                FROM HPN-ICF-OID-MIB
            pingCtlEntry, pingCtlOwnerIndex, pingCtlTestName, pingCtlType,
            pingCtlTargetAddress, pingCtlTargetAddressType, pingCtlDescr
                FROM DISMAN-PING-MIB
            SnmpAdminString
                FROM SNMP-FRAMEWORK-MIB;          -- RFC2571

    hpnicfNqa MODULE-IDENTITY
        LAST-UPDATED "200608140000Z"
        ORGANIZATION
            ""
        CONTACT-INFO
            ""
            DESCRIPTION
                "The private MIB file includes the test information of the
                device. It is supplementary for rfc2925.txt."
        ::= { hpnicfRhw 3 }

    hpnicfNqaObjects OBJECT IDENTIFIER ::= { hpnicfNqa 1 }

 -- The registration node (point) for remote NQA(Network Quality Analysis) test
 -- implementation types

hpnicfNqaImplementationTypeDomains  OBJECT IDENTIFIER ::= { hpnicfNqa 2 }

hpnicfNqaUdpEcho OBJECT-IDENTITY
    STATUS      current
    DESCRIPTION
        "Indicates that an implementation is using the UDP based echo server.
        Notes: The hpnicfNqaCtlTargetPort and hpnicfNqaCtlSourcePort need to be set,
        while in the pingUdpEcho Node, hpnicfNqaCtlTargetPort must be set to the
        default value."
    ::= { hpnicfNqaImplementationTypeDomains 1 }

hpnicfNqaTcpconnect OBJECT-IDENTITY
    STATUS      current
    DESCRIPTION
        "Indicates that an implementation is attempting to
        connect to a TCP port in order to calculate a round
        trip time.
        Notes: The hpnicfNqaCtlTargetPort and hpnicfNqaCtlSourcePort need to be set,
        while in the pingTcpConnectionAttempt Node, hpnicfNqaCtlTargetPort must
        be set to the default value."
    ::= { hpnicfNqaImplementationTypeDomains 2 }

hpnicfNqajitter OBJECT-IDENTITY
    STATUS      current
    DESCRIPTION
        "Indicates that an implementation is using udp for packet transfers.
        'jitter' will cause the NQA(Network Quality Analysis) application
        to perform delay variance analysis."
    ::= { hpnicfNqaImplementationTypeDomains 3 }

hpnicfNqaHttp OBJECT-IDENTITY
    STATUS      current
    DESCRIPTION
        "Indicates that an implementation is using udp for name resolution,
        tcp connect and tcp data transfer mechanisms for HTTP data download
        from a particular HTTP Server.
        It causes the NQA application to perform a download of the object
        specified in the URL."
    ::= { hpnicfNqaImplementationTypeDomains 4 }


hpnicfNqadlsw OBJECT-IDENTITY
    STATUS      current
    DESCRIPTION
        "Indicates that an implementation is using tcp for sending keepalives.
        'dlsw' will cause the NQA application to perform a keepalive operation
        to measure the response time of a DLSw peer."
    ::= { hpnicfNqaImplementationTypeDomains 5 }

hpnicfNqadhcp OBJECT-IDENTITY
    STATUS      current
    DESCRIPTION
        "Indicates that an implementation is using udp for sending dhcp
        requests. 'dhcp' will cause the NQA application
        to perform an IP Address lease request/teardown operation."
    ::= { hpnicfNqaImplementationTypeDomains 6 }

hpnicfNqaftp OBJECT-IDENTITY
    STATUS      current
    DESCRIPTION
        "Indicates that an implementation is using tcp packet for ftp connect
         and data transfer."
    ::= { hpnicfNqaImplementationTypeDomains 7 }


-- MIB contains 3 groups

hpnicfNqaMIBVersion OBJECT-TYPE
    SYNTAX      DisplayString
    MAX-ACCESS  read-only
    STATUS      current
    DESCRIPTION
        "Version string of this MIB.
        The format will be: 'Version.Release.Patch: Description'
        An instance likes: '1.0.0: Initial NQA MIB'
        "
    ::= { hpnicfNqaObjects 1 }

hpnicfNqaCtlTable OBJECT-TYPE
    SYNTAX      SEQUENCE OF HpnicfNqaCtlEntry
    MAX-ACCESS  not-accessible
    STATUS      current
    DESCRIPTION
        "Defines the NQA Control Extend Table for providing, via SNMP,
        the capability of performing network analysis operations at a
        remote host."
   ::= { hpnicfNqaObjects 2 }

hpnicfNqaCtlEntry OBJECT-TYPE
    SYNTAX      HpnicfNqaCtlEntry
    MAX-ACCESS  not-accessible
    STATUS      current
    DESCRIPTION
        "Defines an entry in the hpnicfNqaCtlTable. The operation of this
        table is same as that of pingResultsTable."
    AUGMENTS    { pingCtlEntry }
    ::= { hpnicfNqaCtlTable 1 }

HpnicfNqaCtlEntry ::=
    SEQUENCE {
    hpnicfNqaCtlTargetPort               Integer32,
    hpnicfNqaCtlSourcePort               Integer32,
    hpnicfNqaCtlTTL                      Integer32,
    hpnicfNqaCtlJitterAdminInterval      Integer32,
    hpnicfNqaCtlJitterAdminNumPackets    Integer32,
    hpnicfNqaCtlHttpOperationType        INTEGER,
    hpnicfNqaCtlHttpOperationString      DisplayString,
    hpnicfNqaCtlFtpOperationType         INTEGER,
    hpnicfNqaCtlFtpUsername              DisplayString,
    hpnicfNqaCtlFtpPassword              DisplayString,
    hpnicfNqaCtlFtpOperationString       DisplayString,
    hpnicfNqaCtlVPNInstance              DisplayString,
    hpnicfNqaCtlHistoryKeptTime          Integer32,
    hpnicfNqaCtlHistoryEnable            INTEGER,
    hpnicfNqaCtlICPIFAdvFactor           Integer32,
    hpnicfNqaCtlCodecType                INTEGER
    }

hpnicfNqaCtlTargetPort          OBJECT-TYPE
    SYNTAX      Integer32 (0..65536)
    MAX-ACCESS  read-create
    STATUS      current
    DESCRIPTION
        "The destination port that may be used by udpEcho,
        tcpConnect and jitter probes."
    DEFVAL      { 0 }
    ::= { hpnicfNqaCtlEntry 1 }

hpnicfNqaCtlSourcePort          OBJECT-TYPE
    SYNTAX      Integer32 (0..65536)
    MAX-ACCESS  read-create
    STATUS      current
    DESCRIPTION
        "The source port that may be used by all tests except
        for dns and dlsw.
        If no source port is specified, system will create
        a random port as source port."
    DEFVAL      { 0 }
    ::= { hpnicfNqaCtlEntry 2 }

hpnicfNqaCtlTTL OBJECT-TYPE
    SYNTAX      Integer32
    MAX-ACCESS  read-create
    STATUS      current
    DESCRIPTION
        "Specifies the value to store in the TTL Field in the IP packet used to
        encapsulate the NQA probe."
    DEFVAL      { 20 }
    ::= { hpnicfNqaCtlEntry 3 }

hpnicfNqaCtlJitterAdminInterval OBJECT-TYPE
    SYNTAX      Integer32 (0..60000)
    UNITS       "milliseconds"
    MAX-ACCESS  read-create
    STATUS      current
    DESCRIPTION
        "Time value in milliseconds that is an interval between two continuous
        probes in jitter test.

        This object is only used by jitter test."
    DEFVAL      { 20 }
    ::= { hpnicfNqaCtlEntry 4 }

hpnicfNqaCtlJitterAdminNumPackets OBJECT-TYPE
    SYNTAX      Integer32
    MAX-ACCESS  read-create
    STATUS      current
    DESCRIPTION
        "Packet number that specifys how many packets will be sent in
        one jitter test.

        This object is only used by jitter test."
    DEFVAL      { 10 }
    ::= { hpnicfNqaCtlEntry 5 }

hpnicfNqaCtlHttpOperationType OBJECT-TYPE
    SYNTAX      INTEGER{
                get(1),
                post(2),
                raw(3)
                }
    MAX-ACCESS  read-create
    STATUS      current
    DESCRIPTION
        "Http operation type: get, post or raw."
    DEFVAL      { get }
    ::= { hpnicfNqaCtlEntry 6 }

hpnicfNqaCtlHttpOperationString OBJECT-TYPE
    SYNTAX      DisplayString(SIZE(0..1023))
    MAX-ACCESS  read-create
    STATUS      current
    DESCRIPTION
        "Http operation string. For example, if the http operation type is get,
        the string will be url, home page and http version."
    DEFVAL      { "" }
    ::= { hpnicfNqaCtlEntry 7 }

hpnicfNqaCtlFtpOperationType OBJECT-TYPE
    SYNTAX      INTEGER{
                get(1),
                put(2)
                }
    MAX-ACCESS  read-create
    STATUS      current
    DESCRIPTION
        "Ftp operation type."
    DEFVAL      { get }
    ::= {hpnicfNqaCtlEntry 8 }

hpnicfNqaCtlFtpUsername OBJECT-TYPE
    SYNTAX      DisplayString(SIZE(0..32))
    MAX-ACCESS  read-create
    STATUS      current
    DESCRIPTION
        "Ftp username."
    DEFVAL      { "" }
    ::= { hpnicfNqaCtlEntry 9 }

hpnicfNqaCtlFtpPassword OBJECT-TYPE
    SYNTAX      DisplayString(SIZE(0..32))
    MAX-ACCESS  read-create
    STATUS      current
    DESCRIPTION
        "Ftp password."
    DEFVAL      { "" }
    ::= { hpnicfNqaCtlEntry 10 }

hpnicfNqaCtlFtpOperationString OBJECT-TYPE
    SYNTAX      DisplayString(SIZE(0..255))
    MAX-ACCESS  read-create
    STATUS      current
    DESCRIPTION
        "Ftp operation string. If the ftp operation type is get,
        the string must be the file name which will be gotten from ftp server."
    DEFVAL      { "" }
    ::= { hpnicfNqaCtlEntry 11 }

hpnicfNqaCtlVPNInstance OBJECT-TYPE
    SYNTAX      DisplayString(SIZE(0..255))
    MAX-ACCESS  read-create
    STATUS      current
    DESCRIPTION
        "VPN name by which system finds route in the specified VPN
        to send NQA probe packets."
    DEFVAL      { "" }
    ::= { hpnicfNqaCtlEntry 12 }

hpnicfNqaCtlHistoryKeptTime OBJECT-TYPE
    SYNTAX     Integer32(1..1440)
    UNITS      "minutes"
    MAX-ACCESS read-create
    STATUS     current
    DESCRIPTION
        "To indicate how long the history records will be saved
        in the pingProbeHistoryTable table after the test stopped."
    DEFVAL     { 120 }
    ::= { hpnicfNqaCtlEntry 13 }

hpnicfNqaCtlHistoryEnable OBJECT-TYPE
    SYNTAX      INTEGER
        {
            enabled(1),  --history will be recorded
            disabled(2)  --history will not be recorded
        }
    MAX-ACCESS  read-create
    STATUS      current
    DESCRIPTION
        "To indicate whether the history should be recorded in the
        PingProbeHistoryTable or not.
            enabled(1)   --history will be recorded
            disabled(2)  --history will not be recorded."
    DEFVAL      { disabled }
    ::= {hpnicfNqaCtlEntry 14 }

hpnicfNqaCtlICPIFAdvFactor OBJECT-TYPE
    SYNTAX  Integer32
    MAX-ACCESS read-create
    STATUS  current
    DESCRIPTION
        "The advantage factor depends on the type of access and how the service
        is to be used. This object will be used while calculating the ICPIF
        (Calculated Planning Impairment Factor) values.  This is applicable
        only for the jitter probe.

        Suggestion values:

        |-----------------------------------|-------|
        |          Service                  |factor |
        |-----------------------------------|-------|
        |conventional wire-line             |  0    |
        |-----------------------------------|-------|
        |mobility within Building           |  5    |
        |-----------------------------------|-------|
        |mobility within geographical area  |  10   |
        |-----------------------------------|-------|
        |access to hard-to-reach location   |  20   |
        |-----------------------------------|-------|
        "
    DEFVAL  {0}
    ::= { hpnicfNqaCtlEntry 15 }

hpnicfNqaCtlCodecType OBJECT-TYPE
    SYNTAX     INTEGER
        {
            notDefined(1),     -- no codec type is defined or codec is unknown
            g711Alaw(2),       -- uses G.711 A-Law
            g711Ulaw(3),       -- uses G.711 muHmm-Law
            g729A(4),          -- uses G.729A
            icmpTimestamp(5)   -- uses icmp timestamp packet type
        }
    MAX-ACCESS read-create
    STATUS     current
    DESCRIPTION
        "To indicate the codec type to be used with jitter probe. This is
        applicable only for the jitter probe."
    DEFVAL     { notDefined }
    ::= { hpnicfNqaCtlEntry 16 }

-- NQA Test Results Table

hpnicfNqaResultsTable OBJECT-TYPE
    SYNTAX      SEQUENCE OF HpnicfNqaResultsEntry
    MAX-ACCESS  not-accessible
    STATUS      current
    DESCRIPTION
        "Defines the NQA Results Extend Table for providing
        the capability of performing NQA operations at a remote
        host. The results of these operations are stored in the
        hpnicfNqaResultsTable. The operation of this table is same
        as that of pingResultsTable."
   ::= { hpnicfNqaObjects 3 }

hpnicfNqaResultsEntry OBJECT-TYPE
    SYNTAX      HpnicfNqaResultsEntry
    MAX-ACCESS  not-accessible
    STATUS      current
    DESCRIPTION
        "The operation of this table is same as that of pingResultsTable."
    INDEX {
             pingCtlOwnerIndex,
             pingCtlTestName
          }
    ::= { hpnicfNqaResultsTable 1 }

HpnicfNqaResultsEntry ::=
    SEQUENCE {
        hpnicfNqaResultsRttNumDisconnects   Unsigned32,
        hpnicfNqaResultsRttTimeouts         Unsigned32,
        hpnicfNqaResultsRttBusies           Unsigned32,
        hpnicfNqaResultsRttNoConnections    Unsigned32,
        hpnicfNqaResultsRttDrops            Unsigned32,
        hpnicfNqaResultsRttSequenceErrors   Unsigned32,
        hpnicfNqaResultsRttStatsErrors      Unsigned32,
        hpnicfNqaResultsMaxDelaySD          Unsigned32,
        hpnicfNqaResultsMaxDelayDS          Unsigned32,
        hpnicfNqaResultsLostPacketRatio     Unsigned32,
        hpnicfNqaResultsPacketLateArrival   Unsigned32,
        hpnicfNqaResultsRttSum              Unsigned32,
        hpnicfNqaResultsNumOfDelaySD        Unsigned32,
        hpnicfNqaResultsMinDelaySD          Unsigned32,
        hpnicfNqaResultsSumDelaySD          Unsigned32,
        hpnicfNqaResultsSum2DelaySD         Unsigned32,
        hpnicfNqaResultsNumOfDelayDS        Unsigned32,
        hpnicfNqaResultsMinDelayDS          Unsigned32,
        hpnicfNqaResultsSumDelayDS          Unsigned32,
        hpnicfNqaResultsSum2DelayDS         Unsigned32
    }

hpnicfNqaResultsRttNumDisconnects OBJECT-TYPE
    SYNTAX      Unsigned32
    MAX-ACCESS  read-only
    STATUS      current
    DESCRIPTION
        "The number of times that a NQA probe failed because
        the destination became disconnected.

        For connectionless protocol pingCtlTypes, this number should be
        zero."
    ::= { hpnicfNqaResultsEntry 1 }


hpnicfNqaResultsRttTimeouts OBJECT-TYPE
    SYNTAX      Unsigned32
    MAX-ACCESS  read-only
    STATUS      current
    DESCRIPTION
        "The number of times that a NQA probe failed because the
        probe timed out."
    ::= { hpnicfNqaResultsEntry 2 }


hpnicfNqaResultsRttBusies OBJECT-TYPE
    SYNTAX      Unsigned32
    MAX-ACCESS  read-only
    STATUS      current
    DESCRIPTION
        "The number of times that a NQA probe failed because all
         NQA tasks have been running.

        If a new probe fails to start, the value of this object
        is incremented. The next test will not start until the
        next Frequency."
   ::= { hpnicfNqaResultsEntry 3 }


hpnicfNqaResultsRttNoConnections OBJECT-TYPE
    SYNTAX      Unsigned32
    MAX-ACCESS  read-only
    STATUS      current
    DESCRIPTION
        "The number of times that a NQA probe failed because the probe
        destination is unavailable.

        For connectionless protocol pingCtlTypes, this number should be
        zero."
    ::= { hpnicfNqaResultsEntry 4 }


hpnicfNqaResultsRttDrops OBJECT-TYPE
    SYNTAX      Unsigned32
    MAX-ACCESS  read-only
    STATUS      current
    DESCRIPTION
        "The number of times that a NQA operation failed to initiated
        for unavailibility of necessary internal resources."
    ::= { hpnicfNqaResultsEntry 5 }


hpnicfNqaResultsRttSequenceErrors OBJECT-TYPE
    SYNTAX      Unsigned32
    MAX-ACCESS  read-only
    STATUS      current
    DESCRIPTION
        "The number of packets arrived out of sequence."
   ::= { hpnicfNqaResultsEntry 6 }

hpnicfNqaResultsRttStatsErrors OBJECT-TYPE
    SYNTAX      Unsigned32
    MAX-ACCESS  read-only
    STATUS      current
    DESCRIPTION
        "The number of some other errors."
    ::= { hpnicfNqaResultsEntry 7 }

hpnicfNqaResultsMaxDelaySD OBJECT-TYPE
    SYNTAX      Unsigned32
    UNITS       "milliseconds"
    MAX-ACCESS  read-only
    STATUS      current
    DESCRIPTION
        "The maximal delay from source device to destination device.
         Currently this value is only used for jitter test, and this
         value must be 0 in other type test. In jitter test, if
         destination system time is not valid, the SD delay may be set 0."
    ::= { hpnicfNqaResultsEntry 8 }

hpnicfNqaResultsMaxDelayDS OBJECT-TYPE
    SYNTAX      Unsigned32
    UNITS       "milliseconds"
    MAX-ACCESS  read-only
    STATUS      current
    DESCRIPTION
        "The maximal delay from destination device to source device.
         Currently this value is only used for jitter test, and this
         value is 0 in other type test. In jitter test, if destination
         system time is not valid, the DS delay may be set 0."
    ::= { hpnicfNqaResultsEntry 9 }

hpnicfNqaResultsLostPacketRatio OBJECT-TYPE
    SYNTAX      Unsigned32
    UNITS       "milliseconds"
    MAX-ACCESS  read-only
    STATUS      current
    DESCRIPTION
        "The value of this object reflects the drop rate of NQA test.
         For example, this value is 30 that means source device only
         had received 70% packets of total sent packets."
    ::= { hpnicfNqaResultsEntry 10 }

hpnicfNqaResultsPacketLateArrival OBJECT-TYPE
    SYNTAX      Unsigned32
    MAX-ACCESS  read-only
    STATUS      current
    DESCRIPTION
        "The value of this object indicates the number of the packets that
        arrived after the timeout."
    ::= { hpnicfNqaResultsEntry 11 }

hpnicfNqaResultsRttSum OBJECT-TYPE
    SYNTAX      Unsigned32
    MAX-ACCESS  read-only
    STATUS      current
    DESCRIPTION
        "The sum of round trip time."
    ::= { hpnicfNqaResultsEntry 12 }

hpnicfNqaResultsNumOfDelaySD OBJECT-TYPE
    SYNTAX      Unsigned32
    MAX-ACCESS  read-only
    STATUS      current
    DESCRIPTION
        "The number of delay from source to destination that are
        successfully measured."
    ::= { hpnicfNqaResultsEntry 13 }

hpnicfNqaResultsMinDelaySD OBJECT-TYPE
    SYNTAX      Unsigned32
    MAX-ACCESS  read-only
    STATUS      current
    DESCRIPTION
        "The minimum of all one way times from source to destination."
    ::= { hpnicfNqaResultsEntry 14 }

hpnicfNqaResultsSumDelaySD OBJECT-TYPE
    SYNTAX      Unsigned32
    MAX-ACCESS  read-only
    STATUS      current
    DESCRIPTION
        "The sum of one way times from source to destination."
    ::= { hpnicfNqaResultsEntry 15 }

hpnicfNqaResultsSum2DelaySD OBJECT-TYPE
    SYNTAX      Unsigned32
    MAX-ACCESS  read-only
    STATUS      current
    DESCRIPTION
        "The sum of squares of one way times from source to  destination."
    ::= { hpnicfNqaResultsEntry 16 }

hpnicfNqaResultsNumOfDelayDS OBJECT-TYPE
    SYNTAX      Unsigned32
    MAX-ACCESS  read-only
    STATUS      current
    DESCRIPTION
        "The number of delay from destination to source that are
        successfully measured."
    ::= { hpnicfNqaResultsEntry 17 }

hpnicfNqaResultsMinDelayDS OBJECT-TYPE
    SYNTAX      Unsigned32
    MAX-ACCESS  read-only
    STATUS      current
    DESCRIPTION
        "The minimum of all one way times from destination to source."
    ::= { hpnicfNqaResultsEntry 18 }

hpnicfNqaResultsSumDelayDS OBJECT-TYPE
    SYNTAX      Unsigned32
    MAX-ACCESS  read-only
    STATUS      current
    DESCRIPTION
        "The sum of one way times from destination to source."
    ::= { hpnicfNqaResultsEntry 19 }

hpnicfNqaResultsSum2DelayDS OBJECT-TYPE
    SYNTAX      Unsigned32
    MAX-ACCESS  read-only
    STATUS      current
    DESCRIPTION
        "The sum of squares of one way times from destination to source."
    ::= { hpnicfNqaResultsEntry 20 }

-- =================================================================
--    Jitter Statistics Table
-- =================================================================


hpnicfNqaJitterStatsTable OBJECT-TYPE
    SYNTAX SEQUENCE OF HpnicfNqaJitterStatsEntry
    MAX-ACCESS  not-accessible
    STATUS      current
    DESCRIPTION
        "Statistics table for latest jitter activity."
    ::= { hpnicfNqaObjects 4 }

hpnicfNqaJitterStatsEntry OBJECT-TYPE
    SYNTAX      HpnicfNqaJitterStatsEntry
    MAX-ACCESS  not-accessible
    STATUS      current
    DESCRIPTION
        "An entry contains the statistics for the latest jitter activity.
        This entry is created only if the pingCtlType is hpnicfNqajitter."
    INDEX {
            pingCtlOwnerIndex,
            pingCtlTestName
          }
    ::= { hpnicfNqaJitterStatsTable 1 }

HpnicfNqaJitterStatsEntry  ::= SEQUENCE
{
    hpnicfNqaJitterStatsNumOfRTT                Counter32,
    hpnicfNqaJitterStatsMinOfPositivesSD        Gauge32,
    hpnicfNqaJitterStatsMaxOfPositivesSD        Gauge32,
    hpnicfNqaJitterStatsNumOfPositivesSD        Gauge32,
    hpnicfNqaJitterStatsSumOfPositivesSD        Gauge32,
    hpnicfNqaJitterStatsSum2PositivesSD         Gauge32,
    hpnicfNqaJitterStatsMinOfNegativesSD        Gauge32,
    hpnicfNqaJitterStatsMaxOfNegativesSD        Gauge32,
    hpnicfNqaJitterStatsNumOfNegativesSD        Gauge32,
    hpnicfNqaJitterStatsSumOfNegativesSD        Gauge32,
    hpnicfNqaJitterStatsSum2NegativesSD         Gauge32,
    hpnicfNqaJitterStatsMinOfPositivesDS        Gauge32,
    hpnicfNqaJitterStatsMaxOfPositivesDS        Gauge32,
    hpnicfNqaJitterStatsNumOfPositivesDS        Gauge32,
    hpnicfNqaJitterStatsSumOfPositivesDS        Gauge32,
    hpnicfNqaJitterStatsSum2PositivesDS         Gauge32,
    hpnicfNqaJitterStatsMinOfNegativesDS        Gauge32,
    hpnicfNqaJitterStatsMaxOfNegativesDS        Gauge32,
    hpnicfNqaJitterStatsNumOfNegativesDS        Gauge32,
    hpnicfNqaJitterStatsSumOfNegativesDS        Gauge32,
    hpnicfNqaJitterStatsSum2NegativesDS         Gauge32,
    hpnicfNqaJitterStatsPacketLossSD            Gauge32,
    hpnicfNqaJitterStatsPacketLossDS            Gauge32,
    hpnicfNqaJitterStatsAvePositivesSD          Gauge32,
    hpnicfNqaJitterStatsAveNegativesSD          Gauge32,
    hpnicfNqaJitterStatsAvePositivesDS          Gauge32,
    hpnicfNqaJitterStatsAveNegativesDS          Gauge32,
    hpnicfNqaJitterStatsPktLossUnknown          Gauge32,
    hpnicfNqaJitterStatsOperOfICPIF             Gauge32,
    hpnicfNqaJitterStatsOperOfMOS               Gauge32
}

hpnicfNqaJitterStatsNumOfRTT OBJECT-TYPE
    SYNTAX      Counter32
    MAX-ACCESS  read-only
    STATUS      current
    DESCRIPTION
        "The number of received destination device responses with which
        jitter test can reach round-trip time."
    ::= { hpnicfNqaJitterStatsEntry 1 }


hpnicfNqaJitterStatsMinOfPositivesSD OBJECT-TYPE
    SYNTAX      Gauge32
    MAX-ACCESS  read-only
    STATUS      current
    DESCRIPTION
        "The value of time that records the minimal positive jitter value from
        source to destination in the jitter test."
    ::= { hpnicfNqaJitterStatsEntry 2 }

hpnicfNqaJitterStatsMaxOfPositivesSD OBJECT-TYPE
    SYNTAX      Gauge32
    MAX-ACCESS  read-only
    STATUS      current
    DESCRIPTION
        "The value of time that records the maximal positive jitter value from
        source to destination in the jitter test."
   ::= { hpnicfNqaJitterStatsEntry 3 }

hpnicfNqaJitterStatsNumOfPositivesSD OBJECT-TYPE
    SYNTAX      Gauge32
    MAX-ACCESS  read-only
    STATUS      current
    DESCRIPTION
        "The number that records positive jitter times from source to
        destination in the jitter test.
        The total number of the value of all positive jitters in packets
        sent from source to destination."
    ::= { hpnicfNqaJitterStatsEntry 4 }

hpnicfNqaJitterStatsSumOfPositivesSD OBJECT-TYPE
    SYNTAX      Gauge32
    MAX-ACCESS  read-only
    STATUS      current
    DESCRIPTION
        "The value of time that records the sum of positive jitter values from
        source to destination in the jitter test."
    ::= { hpnicfNqaJitterStatsEntry 5 }

hpnicfNqaJitterStatsSum2PositivesSD OBJECT-TYPE
    SYNTAX      Gauge32
    MAX-ACCESS  read-only
    STATUS      current
    DESCRIPTION
        "The value of time that records the sum of square of positive jitter
        values from source to destination in the jitter test."
    ::= { hpnicfNqaJitterStatsEntry 6 }

hpnicfNqaJitterStatsMinOfNegativesSD OBJECT-TYPE
    SYNTAX      Gauge32
    MAX-ACCESS  read-only
    STATUS      current
    DESCRIPTION
        "The value of time that records the minimal absolute values of
        negative jitter value from source to destination in the jitter test."
    ::= { hpnicfNqaJitterStatsEntry 7 }

hpnicfNqaJitterStatsMaxOfNegativesSD OBJECT-TYPE
    SYNTAX      Gauge32
    MAX-ACCESS  read-only
    STATUS      current
    DESCRIPTION
        "The value of time that records the maximal absolute values of negative
        jitter value from source to destination in the jitter test."
    ::= { hpnicfNqaJitterStatsEntry 8 }

hpnicfNqaJitterStatsNumOfNegativesSD OBJECT-TYPE
    SYNTAX      Gauge32
    MAX-ACCESS  read-only
    STATUS      current
    DESCRIPTION
        "The number that records negative jitter times from source to
        destination in the jitter test.
        The total number of all negative jitter values in packets
        sent from source to destination."
    ::= { hpnicfNqaJitterStatsEntry 9 }

hpnicfNqaJitterStatsSumOfNegativesSD OBJECT-TYPE
    SYNTAX      Gauge32
    MAX-ACCESS  read-only
    STATUS      current
    DESCRIPTION
        "The value of time that records the sum of negative jitter values from
        source to destination in the jitter test.
        The total number of the value of all negative jitters in packets
        sent from source to destination."
    ::= { hpnicfNqaJitterStatsEntry 10 }

hpnicfNqaJitterStatsSum2NegativesSD OBJECT-TYPE
    SYNTAX      Gauge32
    MAX-ACCESS  read-only
    STATUS      current
    DESCRIPTION
        "The value of time that records the sum of square of negative jitter
        values from source to destination in the jitter test."
    ::= { hpnicfNqaJitterStatsEntry 11 }

hpnicfNqaJitterStatsMinOfPositivesDS OBJECT-TYPE
    SYNTAX      Gauge32
    MAX-ACCESS  read-only
    STATUS      current
    DESCRIPTION
        "The value of time that records the minimal positive jitter value from
        destination to source in the jitter test."
    ::= { hpnicfNqaJitterStatsEntry 12 }

hpnicfNqaJitterStatsMaxOfPositivesDS OBJECT-TYPE
    SYNTAX      Gauge32
    MAX-ACCESS  read-only
    STATUS      current
    DESCRIPTION
        "The value of time that records the maximal positive jitter value from
        destination to source in the jitter test."
    ::= { hpnicfNqaJitterStatsEntry 13 }

hpnicfNqaJitterStatsNumOfPositivesDS OBJECT-TYPE
    SYNTAX      Gauge32
    MAX-ACCESS  read-only
    STATUS      current
    DESCRIPTION
        "The number that records positive jitter times from destination to
        source in the jitter test."
    ::= { hpnicfNqaJitterStatsEntry 14 }

hpnicfNqaJitterStatsSumOfPositivesDS OBJECT-TYPE
    SYNTAX      Gauge32
    MAX-ACCESS  read-only
    STATUS      current
    DESCRIPTION
        "The value of time that records the sum of positive jitter values from
        destination to source in the jitter test."
    ::= { hpnicfNqaJitterStatsEntry 15 }

hpnicfNqaJitterStatsSum2PositivesDS OBJECT-TYPE
    SYNTAX      Gauge32
    MAX-ACCESS  read-only
    STATUS      current
    DESCRIPTION
        "The value of time that records the sum of square of positive jitter
        values from destination to source in the jitter test."
    ::= { hpnicfNqaJitterStatsEntry 16 }

hpnicfNqaJitterStatsMinOfNegativesDS OBJECT-TYPE
    SYNTAX      Gauge32
    MAX-ACCESS  read-only
    STATUS      current
    DESCRIPTION
        "The value of time that records the minimal absolute values of negative
        jitter value from destination to source in the jitter test."
    ::= { hpnicfNqaJitterStatsEntry 17 }

hpnicfNqaJitterStatsMaxOfNegativesDS OBJECT-TYPE
    SYNTAX      Gauge32
    MAX-ACCESS  read-only
    STATUS      current
    DESCRIPTION
        "The value of time that records the maximal absolute values of negative
        jitter value from destination to source in the jitter test."
    ::= { hpnicfNqaJitterStatsEntry 18 }

hpnicfNqaJitterStatsNumOfNegativesDS OBJECT-TYPE
    SYNTAX      Gauge32
    MAX-ACCESS  read-only
    STATUS      current
    DESCRIPTION
        "The number that records negative jitter times from destination to source
        in the jitter test."
    ::= { hpnicfNqaJitterStatsEntry 19 }

hpnicfNqaJitterStatsSumOfNegativesDS OBJECT-TYPE
    SYNTAX      Gauge32
    MAX-ACCESS  read-only
    STATUS      current
    DESCRIPTION
        "The value of time that records the sum of negative jitter values from
        destination to source in the jitter test."
    ::= { hpnicfNqaJitterStatsEntry 20 }

hpnicfNqaJitterStatsSum2NegativesDS OBJECT-TYPE
    SYNTAX      Gauge32
    MAX-ACCESS  read-only
    STATUS      current
    DESCRIPTION
        "The value of time that records the sum of square of negative jitter
        values from destination to source in the jitter test."
    ::= { hpnicfNqaJitterStatsEntry 21 }

hpnicfNqaJitterStatsPacketLossSD OBJECT-TYPE
    SYNTAX      Gauge32
    MAX-ACCESS  read-only
    STATUS      current
    DESCRIPTION
        "The lost packets number sent from source to destination."
    ::= { hpnicfNqaJitterStatsEntry 22 }

hpnicfNqaJitterStatsPacketLossDS OBJECT-TYPE
    SYNTAX      Gauge32
    MAX-ACCESS  read-only
    STATUS      current
    DESCRIPTION
        "The lost packets number sent from destination to source."
    ::= { hpnicfNqaJitterStatsEntry 23 }

hpnicfNqaJitterStatsAvePositivesSD OBJECT-TYPE
    SYNTAX      Gauge32
    MAX-ACCESS  read-only
    STATUS      current
    DESCRIPTION
        "The value of time that records the average positive jitter value
        from source to destination."
    ::= { hpnicfNqaJitterStatsEntry 24 }

hpnicfNqaJitterStatsAveNegativesSD OBJECT-TYPE
    SYNTAX      Gauge32
    MAX-ACCESS  read-only
    STATUS      current
    DESCRIPTION
        "The value of time that records the average negative jitter value
        from source to destination."
    ::= { hpnicfNqaJitterStatsEntry 25 }

hpnicfNqaJitterStatsAvePositivesDS OBJECT-TYPE
    SYNTAX      Gauge32
    MAX-ACCESS  read-only
    STATUS      current
    DESCRIPTION
        "The value of time that records the average positive jitter value
        from destination to source."
    ::= { hpnicfNqaJitterStatsEntry 26 }

hpnicfNqaJitterStatsAveNegativesDS OBJECT-TYPE
    SYNTAX      Gauge32
    MAX-ACCESS  read-only
    STATUS      current
    DESCRIPTION
        "The value of time that records the average negative jitter value
        from destination to source."
    ::= { hpnicfNqaJitterStatsEntry 27 }

hpnicfNqaJitterStatsPktLossUnknown OBJECT-TYPE
    SYNTAX      Gauge32
    UNITS       "milliseconds"
    MAX-ACCESS  read-only
    STATUS      current
    DESCRIPTION
        "The number of packets which is lost with unknown reason."
    ::= { hpnicfNqaJitterStatsEntry 28 }

hpnicfNqaJitterStatsOperOfICPIF OBJECT-TYPE
    SYNTAX      Gauge32
    MAX-ACCESS  read-only
    STATUS      current
    DESCRIPTION
        "The ICPIF (Calculated Planning Impairment Factor) value for the latest
        jitter test."
    ::= { hpnicfNqaJitterStatsEntry 29 }

hpnicfNqaJitterStatsOperOfMOS OBJECT-TYPE
    SYNTAX      Gauge32
    MAX-ACCESS  read-only
    STATUS      current
    DESCRIPTION
        "The MOS (Mean Opinion Score) value for the latest jitter test."
    ::= { hpnicfNqaJitterStatsEntry 30 }

hpnicfNqaAgentEnable OBJECT-TYPE
    SYNTAX      INTEGER{
                enable(1),
                disable(2)
                }
    MAX-ACCESS  read-write
    STATUS      current
    DESCRIPTION
        "Enable NQA agent function."
    DEFVAL { disable }
    ::= { hpnicfNqaObjects 5 }

-- =================================================================
--   Tcp server configuration information Statistics Table
-- =================================================================


hpnicfNqaTcpServerTable OBJECT-TYPE
    SYNTAX SEQUENCE OF HpnicfNqaTcpServerEntry
    MAX-ACCESS  not-accessible
    STATUS      current
    DESCRIPTION
        "A table which contains the status of NQA tcp server
        configuration information."
    ::= { hpnicfNqaObjects 6 }

hpnicfNqaTcpServerEntry OBJECT-TYPE
    SYNTAX      HpnicfNqaTcpServerEntry
    MAX-ACCESS  not-accessible
    STATUS      current
    DESCRIPTION
        "A table which contains the status of NQA tcp server
        configuration information.

        This entry includes not only the tcp server ip address
        but also the tcp server port."
    INDEX {
            hpnicfNqaTcpServerIpAddress,
            hpnicfNqaTcpServerPort
          }
    ::= { hpnicfNqaTcpServerTable 1 }

HpnicfNqaTcpServerEntry  ::= SEQUENCE
{
    hpnicfNqaTcpServerIpAddress                InetAddress,
    hpnicfNqaTcpServerPort                     Integer32,
    hpnicfNqaTcpServerRowStatus                RowStatus
}

hpnicfNqaTcpServerIpAddress          OBJECT-TYPE
    SYNTAX      InetAddress
    MAX-ACCESS  not-accessible
    STATUS      current
    DESCRIPTION
        "Tcp server's ip address."
    DEFVAL { ''H }
    ::= { hpnicfNqaTcpServerEntry 1 }

hpnicfNqaTcpServerPort          OBJECT-TYPE
    SYNTAX      Integer32 (0..65536)
    MAX-ACCESS  not-accessible
    STATUS      current
    DESCRIPTION
        "Tcp server's port number."
    DEFVAL      { 0 }
    ::= { hpnicfNqaTcpServerEntry 2 }

hpnicfNqaTcpServerRowStatus OBJECT-TYPE
    SYNTAX      RowStatus
    MAX-ACCESS  read-create
    STATUS      current
    DESCRIPTION
        "hpnicfNqaTcpServerIpAddress and hpnicfNqaTcpServerPort
        must be set during a creation operation."
    REFERENCE
        "RFC 2579"
    ::= { hpnicfNqaTcpServerEntry 3 }

hpnicfNqaUdpServerTable OBJECT-TYPE
    SYNTAX SEQUENCE OF HpnicfNqaUdpServerEntry
    MAX-ACCESS  not-accessible
    STATUS      current
    DESCRIPTION
        "Status of NQA udp server configuration information."
    ::= { hpnicfNqaObjects 7 }

hpnicfNqaUdpServerEntry OBJECT-TYPE
    SYNTAX      HpnicfNqaUdpServerEntry
    MAX-ACCESS  not-accessible
    STATUS      current
    DESCRIPTION
        "This entry includes not only the udp server ip address
        but also the udp server udp port."
    INDEX {
            hpnicfNqaUdpServerIpAddress,
            hpnicfNqaUdpServerPort
          }
    ::= { hpnicfNqaUdpServerTable 1 }

HpnicfNqaUdpServerEntry  ::= SEQUENCE
{
    hpnicfNqaUdpServerIpAddress                InetAddress,
    hpnicfNqaUdpServerPort                     Integer32,
    hpnicfNqaUdpServerRowStatus                RowStatus
}

hpnicfNqaUdpServerIpAddress          OBJECT-TYPE
    SYNTAX      InetAddress
    MAX-ACCESS  not-accessible
    STATUS      current
    DESCRIPTION
        "Udp server's ip address."
    DEFVAL { ''H }
    ::= { hpnicfNqaUdpServerEntry 1 }

hpnicfNqaUdpServerPort          OBJECT-TYPE
    SYNTAX      Integer32 (0..65536)
    MAX-ACCESS  not-accessible
    STATUS      current
    DESCRIPTION
        "Udp server's port number."
    DEFVAL      { 0 }
    ::= { hpnicfNqaUdpServerEntry 2 }

hpnicfNqaUdpServerRowStatus OBJECT-TYPE
    SYNTAX      RowStatus
    MAX-ACCESS  read-create
    STATUS      current
    DESCRIPTION
        "hpnicfNqaUdpServerIpAddress and hpnicfNqaUdpServerPort
        must be set during a creation operation."
    REFERENCE
        "RFC 2579"
    ::= { hpnicfNqaUdpServerEntry 3 }

hpnicfNqaServerEnable OBJECT-TYPE
    SYNTAX      INTEGER{
                enable(1),
                disable(2)
                }
    MAX-ACCESS  read-write
    STATUS      current
    DESCRIPTION
        "Enable NQA server function."
    DEFVAL { disable }
    ::= { hpnicfNqaObjects 8 }

hpnicfNqaStatsMaxGroupNumber OBJECT-TYPE
    SYNTAX     Integer32
    MAX-ACCESS read-only
    STATUS     current
    DESCRIPTION
        "The maximum number saved per group. The maximum value of
        hpnicfNqaCtlStatisticsGroupNumber can not exceed the value of
        this object."
    ::= { hpnicfNqaObjects 9 }


hpnicfNqaStatisticsCtlTable OBJECT-TYPE
    SYNTAX      SEQUENCE OF HpnicfNqaStatisticsCtlEntry
    MAX-ACCESS  not-accessible
    STATUS      current
    DESCRIPTION
        "Defines the NQA statistics control table for providing, via SNMP,
        the capability of performing NQA operations at a remote host.
        The results of these operations are stored in the
        hpnicfNqaStatisticsResultsTable and the hpnicfNqaGroupStatsJitterTable."
    ::= { hpnicfNqaObjects 10 }

hpnicfNqaStatisticsCtlEntry OBJECT-TYPE
    SYNTAX      HpnicfNqaStatisticsCtlEntry
    MAX-ACCESS  not-accessible
    STATUS      current
    DESCRIPTION
        "Defines an entry in the hpnicfNqaStatisticsCtlTable.
        The hpnicfNqaStatisticsCtlTable has the same index as the
        pingCtlTable in order for a hpnicfNqaStatisticsCtlTable to
        correspond to the pingCtlEntry."
    AUGMENTS    { pingCtlEntry }
    ::= { hpnicfNqaStatisticsCtlTable 1 }

HpnicfNqaStatisticsCtlEntry ::=
    SEQUENCE
        {
            hpnicfNqaCtlStatisticsInterval       Unsigned32,
            hpnicfNqaCtlStatisticsGroupNumber    Unsigned32,
            hpnicfNqaCtlStatisticsKeptTime       Unsigned32,
            hpnicfNqaCtlBeginTime                DateAndTime,
            hpnicfNqaCtlLifeTime                 Unsigned32
        }

hpnicfNqaCtlStatisticsInterval OBJECT-TYPE
    SYNTAX     Unsigned32
    UNITS      "minutes"
    MAX-ACCESS read-create
    STATUS     current
    DESCRIPTION
        "Statistic information will be calculated after the time that is
        the value of hpnicfNqaCtlStatisticsInterval."
    ::= { hpnicfNqaStatisticsCtlEntry 1 }

hpnicfNqaCtlStatisticsGroupNumber OBJECT-TYPE
    SYNTAX     Unsigned32
    MAX-ACCESS read-create
    STATUS     current
    DESCRIPTION
        "The value of this object indicates the number of group saved.
        The length of this object is from 1 to hpnicfNqaStatsMaxGroupNumber."
    DEFVAL     { 2 }
    ::= { hpnicfNqaStatisticsCtlEntry 2 }

hpnicfNqaCtlStatisticsKeptTime OBJECT-TYPE
    SYNTAX     Unsigned32(1..1440)
    UNITS      "minutes"
    MAX-ACCESS read-create
    STATUS     current
    DESCRIPTION
        "To indicate how long the statistic information will be saved after
        the test stops."
    DEFVAL     { 120 }
    ::= { hpnicfNqaStatisticsCtlEntry 3 }

hpnicfNqaCtlBeginTime OBJECT-TYPE
    SYNTAX     DateAndTime
    MAX-ACCESS read-create
    STATUS     current
    DESCRIPTION
        "Time at which the type-specified test will start."
    ::= { hpnicfNqaStatisticsCtlEntry 4 }

hpnicfNqaCtlLifeTime OBJECT-TYPE
    SYNTAX     Unsigned32
    UNITS      "seconds"
    MAX-ACCESS read-create
    STATUS     current
    DESCRIPTION
        "To indicate how long the type-specified test will last."
    DEFVAL     { 0 }
    ::= { hpnicfNqaStatisticsCtlEntry 5 }

hpnicfNqaStatisticsResultsTable OBJECT-TYPE
    SYNTAX      SEQUENCE OF HpnicfNqaStatisticsResultsEntry
    MAX-ACCESS  not-accessible
    STATUS      current
    DESCRIPTION
        "Defines the NQA statistics results table for providing
        the capability of performing NQA operations at a remote
        host. The statistics results of these operations in a statistic cycle
        are stored in the hpnicfNqaStatisticsResultsTable. The statistic cycle is
        the value of hpnicfNqaCtlStatisticsInterval.
        The first two index identify the pingCtlEntry that the probe statistics
        result (HpnicfNqaStatisticsResultsEntry) belongs to."

    ::= { hpnicfNqaObjects 11 }


hpnicfNqaStatisticsResultsEntry OBJECT-TYPE
    SYNTAX       HpnicfNqaStatisticsResultsEntry
    MAX-ACCESS   not-accessible
    STATUS       current
    DESCRIPTION
        "Defines an entry in the hpnicfNqaStatisticsResultsTable. The
        hpnicfNqaStatisticsResultsTable has the same index as the
        pingCtlTable in order for a hpnicfNqaStatisticsResultsEntry to
        correspond to the pingCtlEntry that caused it to be created."
    INDEX
        {
            pingCtlOwnerIndex,
            pingCtlTestName,
            hpnicfNqaStatResIndex
        }
    ::= { hpnicfNqaStatisticsResultsTable 1 }

HpnicfNqaStatisticsResultsEntry ::=
    SEQUENCE
        {
            hpnicfNqaStatResIndex                  Unsigned32,
            hpnicfNqaStatResIpTargetAddressType    InetAddressType,
            hpnicfNqaStatResIpTargetAddress        InetAddress,
            hpnicfNqaStatResMinRtt                 Gauge32,
            hpnicfNqaStatResMaxRtt                 Gauge32,
            hpnicfNqaStatResAverageRtt             Gauge32,
            hpnicfNqaStatResProbeResponses         Counter32,
            hpnicfNqaStatResSentProbes             Counter32,
            hpnicfNqaStatResRttSumOfSquares        Counter32,
            hpnicfNqaStatResStartTime              DateAndTime,
            hpnicfNqaStatResInterval               Gauge32,
            hpnicfNqaStatResRttNumDisconnects      Counter32,
            hpnicfNqaStatResRttTimeouts            Counter32,
            hpnicfNqaStatResRttBusies              Counter32,
            hpnicfNqaStatResRttNoConnections       Counter32,
            hpnicfNqaStatResRttDrops               Counter32,
            hpnicfNqaStatResRttSequenceErrors      Counter32,
            hpnicfNqaStatResRttErrors              Counter32,
            hpnicfNqaStatResLostPacketRatio        Gauge32,
            hpnicfNqaStatResPacketLateArrival      Counter32,
            hpnicfNqaStatResRttSum                 Counter32,
            hpnicfNqaStatResNumOfDelaySD           Counter32,
            hpnicfNqaStatResMinDelaySD             Gauge32,
            hpnicfNqaStatResMaxDelaySD             Gauge32,
            hpnicfNqaStatResSumDelaySD             Counter32,
            hpnicfNqaStatResSum2DelaySD            Counter32,
            hpnicfNqaStatResNumOfDelayDS           Counter32,
            hpnicfNqaStatResMinDelayDS             Gauge32,
            hpnicfNqaStatResMaxDelayDS             Gauge32,
            hpnicfNqaStatResSumDelayDS             Counter32,
            hpnicfNqaStatResSum2DelayDS            Counter32
        }

hpnicfNqaStatResIndex OBJECT-TYPE
    SYNTAX      Unsigned32(1..'ffffffff'h)
    MAX-ACCESS  not-accessible
    STATUS      current
    DESCRIPTION
        "An entry in this table is created when the statistics
        result of a NQA probe is determined.

        An implementation MUST start assigning
        hpnicfNqaStatResIndex values at 1 and wrap after
        exceeding the maximum possible value as defined by
        the limit of this object ('ffffffff'h)."
    ::= { hpnicfNqaStatisticsResultsEntry 1 }

hpnicfNqaStatResIpTargetAddressType OBJECT-TYPE
    SYNTAX      InetAddressType
    MAX-ACCESS  read-only
    STATUS      current
    DESCRIPTION
        "This object indicates the type of address stored
        in the corresponding hpnicfNqaStatResIpTargetAddress
        object."
    DEFVAL { unknown }
    ::= { hpnicfNqaStatisticsResultsEntry 2 }

hpnicfNqaStatResIpTargetAddress OBJECT-TYPE
    SYNTAX      InetAddress
    MAX-ACCESS  read-only
    STATUS      current
    DESCRIPTION
        "This object represent the host address to be used at a remote host for
        performing a network analysis operation."
    DEFVAL { ''H }
    ::= { hpnicfNqaStatisticsResultsEntry 3 }

hpnicfNqaStatResMinRtt  OBJECT-TYPE
    SYNTAX      Gauge32
    UNITS       "milliseconds"
    MAX-ACCESS  read-only
    STATUS      current
    DESCRIPTION
        "The minimum NQA probe round-trip-time (RTT) received. The value
        of 0 for this object implies that no RTT has been received."
    ::= { hpnicfNqaStatisticsResultsEntry 4 }

hpnicfNqaStatResMaxRtt OBJECT-TYPE
    SYNTAX      Gauge32
    UNITS       "milliseconds"
    MAX-ACCESS  read-only
    STATUS      current
    DESCRIPTION
        "The maximum NQA probe round-trip-time (RTT) received. The value
        of 0 for this object implies that no RTT has been received."
    ::= { hpnicfNqaStatisticsResultsEntry 5 }

hpnicfNqaStatResAverageRtt OBJECT-TYPE
    SYNTAX      Gauge32
    UNITS       "milliseconds"
    MAX-ACCESS  read-only
    STATUS      current
    DESCRIPTION
        "The average NQA probe round-trip-time (RTT)."
    ::= { hpnicfNqaStatisticsResultsEntry 6 }

hpnicfNqaStatResProbeResponses OBJECT-TYPE
    SYNTAX      Counter32
    MAX-ACCESS  read-only
    STATUS      current
    DESCRIPTION
        "The number of responses received. The value of this object
        MUST be reported as 0 when no probe responses have been
        received."
    ::= { hpnicfNqaStatisticsResultsEntry 7 }

hpnicfNqaStatResSentProbes OBJECT-TYPE
    SYNTAX      Counter32
    UNITS       "probes"
    MAX-ACCESS  read-only
    STATUS      current
    DESCRIPTION
        "The value of this object reflects the number of probes sent.
        The value of this object MUST be reported as 0 when no probes
        have been sent."
    ::= { hpnicfNqaStatisticsResultsEntry 8 }

hpnicfNqaStatResRttSumOfSquares OBJECT-TYPE
    SYNTAX      Counter32
    UNITS       "milliseconds"
    MAX-ACCESS  read-only
    STATUS      current
    DESCRIPTION
        "This object contains the sum of the squares for all NQA
        responses received. The value of this object MUST
        be reported as 0 when no NQA responses have been
        received."
    ::= { hpnicfNqaStatisticsResultsEntry 9 }

hpnicfNqaStatResStartTime OBJECT-TYPE
    SYNTAX      DateAndTime
    MAX-ACCESS  read-only
    STATUS      current
    DESCRIPTION
        "This object contains the start time of the statistic."
    ::= { hpnicfNqaStatisticsResultsEntry 10 }

hpnicfNqaStatResInterval OBJECT-TYPE
    SYNTAX      Gauge32
    UNITS       "seconds"
    MAX-ACCESS  read-only
    STATUS      current
    DESCRIPTION
        "This object contains the interval between two times of statistic."
    ::= { hpnicfNqaStatisticsResultsEntry 11 }

hpnicfNqaStatResRttNumDisconnects OBJECT-TYPE
    SYNTAX      Counter32
    MAX-ACCESS  read-only
    STATUS      current
    DESCRIPTION
        "The number of times that a NQA probe failed because the destination
        became disconnected.
        For connectionless protocol pingCtlTypes, this number should be
        zero."
    ::= { hpnicfNqaStatisticsResultsEntry 12 }

hpnicfNqaStatResRttTimeouts OBJECT-TYPE
    SYNTAX      Counter32
    MAX-ACCESS  read-only
    STATUS      current
    DESCRIPTION
       "The number of times that a probe failed because the probe timed out."
    ::= { hpnicfNqaStatisticsResultsEntry 13 }

hpnicfNqaStatResRttBusies OBJECT-TYPE
    SYNTAX      Counter32
    MAX-ACCESS  read-only
    STATUS      current
    DESCRIPTION
        "The number of times that a NQA probe failed because
        errors related to sockets."
    ::= { hpnicfNqaStatisticsResultsEntry 14 }

hpnicfNqaStatResRttNoConnections OBJECT-TYPE
    SYNTAX      Counter32
    MAX-ACCESS  read-only
    STATUS      current
    DESCRIPTION
        "The number of times that a NQA probe failed because the
        probe destination is unavailable.
        For connectionless protocol pingCtlTypes, this number should be
        zero."
    ::= { hpnicfNqaStatisticsResultsEntry 15 }

hpnicfNqaStatResRttDrops OBJECT-TYPE
    SYNTAX      Counter32
    MAX-ACCESS  read-only
    STATUS      current
    DESCRIPTION
        "The number of times that a NQA operation failed to initiate
        for unavailibility of necessary internal resources."
    ::= { hpnicfNqaStatisticsResultsEntry 16 }

hpnicfNqaStatResRttSequenceErrors OBJECT-TYPE
    SYNTAX      Counter32
    MAX-ACCESS  read-only
    STATUS      current
    DESCRIPTION
        "The number of packets arrived out of sequence."
    ::= { hpnicfNqaStatisticsResultsEntry 17 }

hpnicfNqaStatResRttErrors OBJECT-TYPE
    SYNTAX      Counter32
    MAX-ACCESS  read-only
    STATUS      current
    DESCRIPTION
        "The number of other errors."
    ::= { hpnicfNqaStatisticsResultsEntry 18 }

hpnicfNqaStatResLostPacketRatio OBJECT-TYPE
    SYNTAX      Gauge32
    MAX-ACCESS  read-only
    STATUS      current
    DESCRIPTION
        "The value of this object reflects the drop rate of NQA
        test packet.
        For example, if the value is 30, that means source device
        only had received 70 percent packets of total sent packets."
    ::= { hpnicfNqaStatisticsResultsEntry 19 }

hpnicfNqaStatResPacketLateArrival OBJECT-TYPE
    SYNTAX      Counter32
    MAX-ACCESS  read-only
    STATUS      current
    DESCRIPTION
        "The value of this object reflects the number of the packets that
        arrived after the timeout."
    ::= { hpnicfNqaStatisticsResultsEntry 20 }

hpnicfNqaStatResRttSum OBJECT-TYPE
    SYNTAX      Counter32
    MAX-ACCESS  read-only
    STATUS      current
    DESCRIPTION
        "This object contains the sum of the squares for all NQA
        responses received during the test lifetime. The value of this object
        MUST be reported as 0 when no NQA responses have been received."
    ::= { hpnicfNqaStatisticsResultsEntry 21 }

hpnicfNqaStatResNumOfDelaySD OBJECT-TYPE
    SYNTAX      Counter32
    MAX-ACCESS  read-only
    STATUS      current
    DESCRIPTION
        "The number of one way times from source to destination that are
        successfully measured."
    ::= { hpnicfNqaStatisticsResultsEntry 22 }

hpnicfNqaStatResMinDelaySD OBJECT-TYPE
    SYNTAX      Gauge32
    MAX-ACCESS  read-only
    STATUS      current
    DESCRIPTION
        "The minimum one way times from source to destination."
    ::= { hpnicfNqaStatisticsResultsEntry 23 }

hpnicfNqaStatResMaxDelaySD OBJECT-TYPE
    SYNTAX      Gauge32
    MAX-ACCESS  read-only
    STATUS      current
    DESCRIPTION
        "The maximum one way times from source to destination."
    ::= { hpnicfNqaStatisticsResultsEntry 24 }

hpnicfNqaStatResSumDelaySD OBJECT-TYPE
    SYNTAX      Counter32
    MAX-ACCESS  read-only
    STATUS      current
    DESCRIPTION
        "The sum of one way times from source to destination."
    ::= { hpnicfNqaStatisticsResultsEntry 25 }

hpnicfNqaStatResSum2DelaySD OBJECT-TYPE
    SYNTAX      Counter32
    MAX-ACCESS  read-only
    STATUS      current
    DESCRIPTION
        "The sum of squares of one way times from source to destination."
    ::= { hpnicfNqaStatisticsResultsEntry 26 }

hpnicfNqaStatResNumOfDelayDS OBJECT-TYPE
    SYNTAX      Counter32
    MAX-ACCESS  read-only
    STATUS      current
    DESCRIPTION
        "The number of one way times from destination to source that are
        successfully measured."
    ::= { hpnicfNqaStatisticsResultsEntry 27 }

hpnicfNqaStatResMinDelayDS OBJECT-TYPE
    SYNTAX      Gauge32
    MAX-ACCESS  read-only
    STATUS      current
    DESCRIPTION
        "The minimum one way times from destination to source."
    ::= { hpnicfNqaStatisticsResultsEntry 28 }

hpnicfNqaStatResMaxDelayDS OBJECT-TYPE
    SYNTAX      Gauge32
    MAX-ACCESS  read-only
    STATUS      current
    DESCRIPTION
        "The maximum one way times from destination to source."
    ::= { hpnicfNqaStatisticsResultsEntry 29 }

hpnicfNqaStatResSumDelayDS OBJECT-TYPE
    SYNTAX      Counter32
    MAX-ACCESS  read-only
    STATUS      current
    DESCRIPTION
        "The sum of one way times from destination to source."
    ::= { hpnicfNqaStatisticsResultsEntry 30 }

hpnicfNqaStatResSum2DelayDS OBJECT-TYPE
    SYNTAX      Counter32
    MAX-ACCESS  read-only
    STATUS      current
    DESCRIPTION
        "The sum of squares of one way times from destination to source."
    ::= { hpnicfNqaStatisticsResultsEntry 31 }


-- =================================================================
--    hpnicfNqaGroupStatsJitterTable
-- =================================================================

hpnicfNqaGroupStatsJitterTable OBJECT-TYPE
    SYNTAX      SEQUENCE OF HpnicfNqaGroupStatsJitterEntry
    MAX-ACCESS  not-accessible
    STATUS      current
    DESCRIPTION
        "Test Group Statistic table for jitter activity in a statistic cycle.
        The statistic cycle is the value of hpnicfNqaCtlStatisticsInterval.
        The first two index identify the pingCtlEntry that a probe statistics
        result (HpnicfNqaStatisticsResultsEntry) belongs to."
    ::= { hpnicfNqaObjects 12 }

hpnicfNqaGroupStatsJitterEntry OBJECT-TYPE
    SYNTAX      HpnicfNqaGroupStatsJitterEntry
    MAX-ACCESS  not-accessible
    STATUS      current
    DESCRIPTION
        "An entry contains the group statistic information for jitter activity.
        This entry is created only if the pingCtlType is hpnicfNqajitter."
    INDEX
        {
            pingCtlOwnerIndex,
            pingCtlTestName,
            hpnicfNqaStatJitterIndex
        }
    ::= { hpnicfNqaGroupStatsJitterTable 1 }

HpnicfNqaGroupStatsJitterEntry ::=
    SEQUENCE
        {
            hpnicfNqaStatJitterIndex               Unsigned32,
            hpnicfNqaStatJitterMinOfPosSD          Gauge32,
            hpnicfNqaStatJitterMaxOfPosSD          Gauge32,
            hpnicfNqaStatJitterNumOfPosSD          Counter32,
            hpnicfNqaStatJitterSumOfPosSD          Counter32,
            hpnicfNqaStatJitterSumOfSquarePosSD    Counter32,
            hpnicfNqaStatJitterMinOfNegSD          Gauge32,
            hpnicfNqaStatJitterMaxOfNegSD          Gauge32,
            hpnicfNqaStatJitterNumOfNegSD          Counter32,
            hpnicfNqaStatJitterSumOfNegSD          Counter32,
            hpnicfNqaStatJitterSumOfSquareNegSD    Counter32,
            hpnicfNqaStatJitterMinOfPosDS          Gauge32,
            hpnicfNqaStatJitterMaxOfPosDS          Gauge32,
            hpnicfNqaStatJitterNumOfPosDS          Counter32,
            hpnicfNqaStatJitterSumOfPosDS          Counter32,
            hpnicfNqaStatJitterSumOfSquarePosDS    Counter32,
            hpnicfNqaStatJitterMinOfNegDS          Gauge32,
            hpnicfNqaStatJitterMaxOfNegDS          Gauge32,
            hpnicfNqaStatJitterNumOfNegDS          Counter32,
            hpnicfNqaStatJitterSumOfNegDS          Counter32,
            hpnicfNqaStatJitterSumOfSquareNegDS    Counter32,
            hpnicfNqaStatJitterPacketLossSD        Counter32,
            hpnicfNqaStatJitterPacketLossDS        Counter32,
            hpnicfNqaStatJitterAvePosSD            Gauge32,
            hpnicfNqaStatJitterAveNegSD            Gauge32,
            hpnicfNqaStatJitterAvePosDS            Gauge32,
            hpnicfNqaStatJitterAveNegDS            Gauge32,
            hpnicfNqaStatJitterPktLossUnknown      Counter32,
            hpnicfNqaStatJitterMaxOfICPIF          Gauge32,
            hpnicfNqaStatJitterMinOfICPIF          Gauge32,
            hpnicfNqaStatJitterMaxOfMOS            Gauge32,
            hpnicfNqaStatJitterMinOfMOS            Gauge32
        }

hpnicfNqaStatJitterIndex OBJECT-TYPE
    SYNTAX      Unsigned32(1..'ffffffff'h)
    MAX-ACCESS  not-accessible
    STATUS      current
    DESCRIPTION
        "An entry in this table is created when the statistic
        result of a NQA probe in a statistic cycle is determined.

        An implementation MUST start assigning hpnicfNqaStatJitterIndex
        values at 1 and wrap after exceeding the maximum possible
        value as defined by the limit of this object ('ffffffff'h)."
    ::= { hpnicfNqaGroupStatsJitterEntry 1 }

hpnicfNqaStatJitterMinOfPosSD OBJECT-TYPE
    SYNTAX      Gauge32
    UNITS       "milliseconds"
    MAX-ACCESS  read-only
    STATUS      current
    DESCRIPTION
        "The value of time that records the minimal positive jitter value
        from source to destination in jitter test."
    ::= { hpnicfNqaGroupStatsJitterEntry 2 }

hpnicfNqaStatJitterMaxOfPosSD OBJECT-TYPE
    SYNTAX      Gauge32
    UNITS       "milliseconds"
    MAX-ACCESS  read-only
    STATUS      current
    DESCRIPTION
        "The value of time that records the maximal positive jitter value
        from source to destination in the jitter test."
    ::= { hpnicfNqaGroupStatsJitterEntry 3 }

hpnicfNqaStatJitterNumOfPosSD OBJECT-TYPE
    SYNTAX      Counter32
    MAX-ACCESS  read-only
    STATUS      current
    DESCRIPTION
        "The total number of positive jitters from source to destination in the
        jitter test."
    ::= { hpnicfNqaGroupStatsJitterEntry 4 }

hpnicfNqaStatJitterSumOfPosSD OBJECT-TYPE
    SYNTAX      Counter32
    UNITS       "milliseconds"
    MAX-ACCESS  read-only
    STATUS      current
    DESCRIPTION
        "The value of time that records the sum of positive jitter values
        from source to destination in the jitter test."
    ::= { hpnicfNqaGroupStatsJitterEntry 5 }

hpnicfNqaStatJitterSumOfSquarePosSD OBJECT-TYPE
    SYNTAX      Counter32
    UNITS       "milliseconds"
    MAX-ACCESS  read-only
    STATUS      current
    DESCRIPTION
        "The value of time that records the sum of square of positive jitter
        values from source to destination in the jitter test."
    ::= { hpnicfNqaGroupStatsJitterEntry 6 }

hpnicfNqaStatJitterMinOfNegSD OBJECT-TYPE
    SYNTAX      Gauge32
    UNITS       "milliseconds"
    MAX-ACCESS  read-only
    STATUS      current
    DESCRIPTION
        "The value of time that records the minimal absolute values of
        negative jitter value from source to destination in the jitter test."
    ::= { hpnicfNqaGroupStatsJitterEntry 7 }

hpnicfNqaStatJitterMaxOfNegSD OBJECT-TYPE
    SYNTAX      Gauge32
    UNITS       "milliseconds"
    MAX-ACCESS  read-only
    STATUS      current
    DESCRIPTION
        "The value of time that records the maximal absolute values of negative
        jitter value from source to destination in the jitter test."
    ::= { hpnicfNqaGroupStatsJitterEntry 8 }

hpnicfNqaStatJitterNumOfNegSD OBJECT-TYPE
    SYNTAX      Counter32
    MAX-ACCESS  read-only
    STATUS      current
    DESCRIPTION
        "The total number of negative jitters from source to destination in the
        jitter test."
    ::= { hpnicfNqaGroupStatsJitterEntry 9 }

hpnicfNqaStatJitterSumOfNegSD OBJECT-TYPE
    SYNTAX      Counter32
    UNITS       "milliseconds"
    MAX-ACCESS  read-only
    STATUS      current
    DESCRIPTION
        "The value of time that records the sum of negative jitter values
        from source to destination in the jitter test."
    ::= { hpnicfNqaGroupStatsJitterEntry 10 }

hpnicfNqaStatJitterSumOfSquareNegSD OBJECT-TYPE
    SYNTAX      Counter32
    UNITS       "milliseconds"
    MAX-ACCESS  read-only
    STATUS      current
    DESCRIPTION
        "The value of time that records the sum of square of negative jitter
        values from source to destination in the jitter test."
    ::= { hpnicfNqaGroupStatsJitterEntry 11 }

hpnicfNqaStatJitterMinOfPosDS OBJECT-TYPE
    SYNTAX      Gauge32
    UNITS       "milliseconds"
    MAX-ACCESS  read-only
    STATUS      current
    DESCRIPTION
        "The value of time that records the minimal positive jitter value
        from destination to source in the jitter test."
    ::= { hpnicfNqaGroupStatsJitterEntry 12 }

hpnicfNqaStatJitterMaxOfPosDS OBJECT-TYPE
    SYNTAX      Gauge32
    UNITS       "milliseconds"
    MAX-ACCESS  read-only
    STATUS      current
    DESCRIPTION
        "The value of time that records the maximal positive jitter value
        from destination to source in the jitter test."
    ::= { hpnicfNqaGroupStatsJitterEntry 13 }

hpnicfNqaStatJitterNumOfPosDS OBJECT-TYPE
    SYNTAX      Counter32
    MAX-ACCESS  read-only
    STATUS      current
    DESCRIPTION
        "The total number of positive jitters from destination to source in the
        jitter test."
    ::= { hpnicfNqaGroupStatsJitterEntry 14 }

hpnicfNqaStatJitterSumOfPosDS OBJECT-TYPE
    SYNTAX      Counter32
    UNITS       "milliseconds"
    MAX-ACCESS  read-only
    STATUS      current
    DESCRIPTION
        "The value of time that records the sum of positive jitter values
        from destination to source in the jitter test."
    ::= { hpnicfNqaGroupStatsJitterEntry 15 }

hpnicfNqaStatJitterSumOfSquarePosDS OBJECT-TYPE
    SYNTAX      Counter32
    UNITS       "milliseconds"
    MAX-ACCESS  read-only
    STATUS      current
    DESCRIPTION
        "The value of time that records the sum of square of positive jitter
        values destination to source in the jitter test."
    ::= { hpnicfNqaGroupStatsJitterEntry 16 }

hpnicfNqaStatJitterMinOfNegDS OBJECT-TYPE
    SYNTAX      Gauge32
    UNITS       "milliseconds"
    MAX-ACCESS  read-only
    STATUS      current
    DESCRIPTION
        "The value of time that records the minimal absolute values of negative
        jitter value from destination to source in the jitter test."
    ::= { hpnicfNqaGroupStatsJitterEntry 17 }

hpnicfNqaStatJitterMaxOfNegDS OBJECT-TYPE
    SYNTAX      Gauge32
    UNITS       "milliseconds"
    MAX-ACCESS  read-only
    STATUS      current
    DESCRIPTION
        "The value of time that records the maximal absolute values of negative
        jitter value from destination to source in the jitter test."
    ::= { hpnicfNqaGroupStatsJitterEntry 18 }

hpnicfNqaStatJitterNumOfNegDS OBJECT-TYPE
    SYNTAX      Counter32
    MAX-ACCESS  read-only
    STATUS      current
    DESCRIPTION
        "The total number of negative jitters from destination to source in the
        jitter test."
    ::= { hpnicfNqaGroupStatsJitterEntry 19 }

hpnicfNqaStatJitterSumOfNegDS OBJECT-TYPE
    SYNTAX      Counter32
    UNITS       "milliseconds"
    MAX-ACCESS  read-only
    STATUS      current
    DESCRIPTION
        "The value of time that records the sum of negative jitter values
        from destination to source in the jitter test."
    ::= { hpnicfNqaGroupStatsJitterEntry 20 }

hpnicfNqaStatJitterSumOfSquareNegDS OBJECT-TYPE
    SYNTAX      Counter32
    UNITS       "milliseconds"
    MAX-ACCESS  read-only
    STATUS      current
    DESCRIPTION
        "The value of time that records the sum of square of negative jitter
        values from destination to source in the jitter test."
    ::= { hpnicfNqaGroupStatsJitterEntry 21 }

hpnicfNqaStatJitterPacketLossSD OBJECT-TYPE
    SYNTAX      Counter32
    MAX-ACCESS  read-only
    STATUS      current
    DESCRIPTION
        "The lost packets number sent from source to destination."
    ::= { hpnicfNqaGroupStatsJitterEntry 22 }

hpnicfNqaStatJitterPacketLossDS OBJECT-TYPE
    SYNTAX      Counter32
    MAX-ACCESS  read-only
    STATUS      current
    DESCRIPTION
        "The lost packets number sent from destination to source."
    ::= { hpnicfNqaGroupStatsJitterEntry 23 }

hpnicfNqaStatJitterAvePosSD OBJECT-TYPE
    SYNTAX      Gauge32
    UNITS       "milliseconds"
    MAX-ACCESS  read-only
    STATUS      current
    DESCRIPTION
        "The value of time that records the average positive jitter value
        from source to destination."
    ::= { hpnicfNqaGroupStatsJitterEntry 24 }

hpnicfNqaStatJitterAveNegSD OBJECT-TYPE
    SYNTAX      Gauge32
    UNITS       "milliseconds"
    MAX-ACCESS  read-only
    STATUS      current
    DESCRIPTION
        "The value of time that records the average negative jitter value
        from source to destination."
    ::= { hpnicfNqaGroupStatsJitterEntry 25 }

hpnicfNqaStatJitterAvePosDS OBJECT-TYPE
    SYNTAX      Gauge32
    UNITS       "milliseconds"
    MAX-ACCESS  read-only
    STATUS      current
    DESCRIPTION
        "The value of time that records the average positive jitter value
        from destination to source."
    ::= { hpnicfNqaGroupStatsJitterEntry 26 }

hpnicfNqaStatJitterAveNegDS OBJECT-TYPE
    SYNTAX      Gauge32
    UNITS       "milliseconds"
    MAX-ACCESS  read-only
    STATUS      current
    DESCRIPTION
        "The value of time that records the average negative jitter value
        from destination to source."
    ::= { hpnicfNqaGroupStatsJitterEntry 27 }

hpnicfNqaStatJitterPktLossUnknown OBJECT-TYPE
    SYNTAX      Counter32
    MAX-ACCESS  read-only
    STATUS      current
    DESCRIPTION
        "The number of packets which is lost with unknown reason."
    ::= { hpnicfNqaGroupStatsJitterEntry 28 }

hpnicfNqaStatJitterMaxOfICPIF OBJECT-TYPE
    SYNTAX      Gauge32
    MAX-ACCESS  read-only
    STATUS      current
    DESCRIPTION
        "The maximum of all ICPIF values in a statistic cycle for jitter test."
    ::= { hpnicfNqaGroupStatsJitterEntry 29 }

hpnicfNqaStatJitterMinOfICPIF OBJECT-TYPE
    SYNTAX      Gauge32
    MAX-ACCESS  read-only
    STATUS      current
    DESCRIPTION
        "The minimum of all ICPIF values in a statistic cycle for jitter test."
    ::= { hpnicfNqaGroupStatsJitterEntry 30 }

hpnicfNqaStatJitterMaxOfMOS OBJECT-TYPE
    SYNTAX      Gauge32
    MAX-ACCESS  read-only
    STATUS      current
    DESCRIPTION
        "The maximum of all MOS values in a statistic cycle for jitter test."
    ::= { hpnicfNqaGroupStatsJitterEntry 31 }

hpnicfNqaStatJitterMinOfMOS OBJECT-TYPE
    SYNTAX      Gauge32
    MAX-ACCESS  read-only
    STATUS      current
    DESCRIPTION
        "The minimum of all MOS values in a statistic cycle for jitter test."
    ::= { hpnicfNqaGroupStatsJitterEntry 32 }

-- Reaction Table
hpnicfNqaReactionTable OBJECT-TYPE
    SYNTAX      SEQUENCE OF HpnicfNqaReactionEntry
    MAX-ACCESS  not-accessible
    STATUS      current
    DESCRIPTION
        "A table of NQA test monitoring notification and
        reaction configuration definitions.

        An entry is removed from this table when its
        corresponding pingCtlEntry is deleted."
  ::= { hpnicfNqaObjects 13 }

hpnicfNqaReactionEntry OBJECT-TYPE
    SYNTAX      HpnicfNqaReactionEntry
    MAX-ACCESS  not-accessible
    STATUS      current
    DESCRIPTION
        "Defines an entry in the hpnicfNqaReactionTable. The first two index
        elements identify the pingCtlEntry that a hpnicfNqaReactItemIndex
        belongs to. The third index element selects a single reaction."
    INDEX
        {
            hpnicfNqaReactOwnerIndex,
            hpnicfNqaReactTestName,
            hpnicfNqaReactItemIndex
        }
    ::= { hpnicfNqaReactionTable 1 }

HpnicfNqaReactionEntry ::=
    SEQUENCE
        {
            hpnicfNqaReactOwnerIndex                   SnmpAdminString,
            hpnicfNqaReactTestName                     SnmpAdminString,
            hpnicfNqaReactItemIndex                    Unsigned32,
            hpnicfNqaReactCheckedElement               INTEGER,
            hpnicfNqaReactThresholdUpperLimit          Unsigned32,
            hpnicfNqaReactThresholdLowerLimit          Unsigned32,
            hpnicfNqaReactThresholdType                INTEGER,
            hpnicfNqaReactThresholdConsecNum           Unsigned32,
            hpnicfNqaReactThresholdAccumNum            Unsigned32,
            hpnicfNqaReactActionType                   INTEGER,
            hpnicfNqaReactCurrentStatus                INTEGER,
            hpnicfNqaReactRowStatus                    RowStatus,
            hpnicfNqaReactCheckedNum                   Unsigned32,
            hpnicfNqaReactThresholdNum                 Unsigned32
        }

hpnicfNqaReactOwnerIndex OBJECT-TYPE
    SYNTAX      SnmpAdminString (SIZE(0..32))
    MAX-ACCESS  accessible-for-notify
    STATUS      current
    DESCRIPTION
        "The first index of hpnicfNqaReactionTable, it is the same as
        pingCtlOwnerIndex in pingCtlTable. hpnicfNqaReactOwnerIndex and
        hpnicfNqaReactTestName identify an existed test."
    ::= { hpnicfNqaReactionEntry 1 }

hpnicfNqaReactTestName OBJECT-TYPE
    SYNTAX      SnmpAdminString (SIZE(0..32))
    MAX-ACCESS  accessible-for-notify
    STATUS      current
    DESCRIPTION
        "The second index of hpnicfNqaReactionTable, it is the same as
        pingCtlTestName in pingCtlTable. hpnicfNqaReactOwnerIndex and
        hpnicfNqaReactTestName identify an existed test."
    ::= { hpnicfNqaReactionEntry 2 }

hpnicfNqaReactItemIndex OBJECT-TYPE
    SYNTAX      Unsigned32 (1..10)
    MAX-ACCESS  accessible-for-notify
    STATUS      current
    DESCRIPTION
        "The third index of hpnicfNqaReactionTable, it definitely
        identifies one of the reaction configurations for a test."
    ::= { hpnicfNqaReactionEntry 3 }

hpnicfNqaReactCheckedElement OBJECT-TYPE
    SYNTAX      INTEGER {
                          probetime(1),
                          probefailure(2),
                          jitterrtt(3),
                          jitterpacketloss(4),
                          jittersd(5),
                          jitterds(6),
                          icpif(7),
                          mos(8),
                          jitterOwdSD(9),
                          jitterOwdDS(10)
                        }
    MAX-ACCESS  read-create
    STATUS      current
    DESCRIPTION
        "A list of reaction condition type.
        'probetime' and 'probefailure' are valid when pingCtlType of
        the test is not hpnicfNqajitter.

        'jitterOwdSD': one way time from source to destination in
                       jitter test.
        'jitterOwdDS': one way time from destination to source in
                       jitter test.

        'jitterrtt', 'jitterpacketloss', 'jittersd', 'jitterds',
        'jitterOwdSD' and 'jitterOwdDS' are valid when pingCtlType
        of the test is hpnicfNqajitter.

        'icpif' and 'mos' are valid when pingCtlType of the test is
        hpnicfNqajitter and hpnicfNqaCtlCodecType is 'g711Alaw' or 'g711Ulaw'
        or 'g729A'."
     ::= { hpnicfNqaReactionEntry 4 }

hpnicfNqaReactThresholdUpperLimit OBJECT-TYPE
    SYNTAX      Unsigned32
    MAX-ACCESS  read-create
    STATUS      current
    DESCRIPTION
        "This object defines an administrative upper-threshold value for
        hpnicfNqaReactCheckedElement.

        The value of this object is zero if hpnicfNqaReactCheckedElement is
        specified as 'jitterpacketloss' and 'probefailure'."
    DEFVAL { 0 }
    ::= { hpnicfNqaReactionEntry 5 }

hpnicfNqaReactThresholdLowerLimit OBJECT-TYPE
    SYNTAX      Unsigned32
    MAX-ACCESS  read-create
    STATUS      current
    DESCRIPTION
        "This object defines an administrative lower-threshold value for
        hpnicfNqaReactCheckedElement.

        The value of hpnicfNqaReactThresholdLowerLimit should be equal or less
        than the value of hpnicfNqaReactThresholdUpperLimit.

        The value of this object is zero if hpnicfNqaReactCheckedElement is
        specified as 'jitterpacketloss' and 'probefailure'."
    DEFVAL { 0 }
    ::= { hpnicfNqaReactionEntry 6 }

hpnicfNqaReactThresholdType OBJECT-TYPE
    SYNTAX      INTEGER {
                           invalid(0),
                           average(1),
                           consecutive(2),
                           accumulative(3)
                       }
    MAX-ACCESS  read-create
    STATUS      current
    DESCRIPTION
        "This object defines the reaction threshold types.

        invalid(0):     Invalid value.

        average(1):     If reaction threshold type is average and the average
                        value of watched operation exceeds threshold limit,
                        an action specified in hpnicfNqaReactActionType is
                        generated when hpnicfNqaReactCurrentStatus changes.

        consecutive(2): If reaction threshold type is consecutive and
                        the times of watched operation consecutively exceeds
                        the limit specified by hpnicfNqaReactThresholdConsecNum,
                        an action specified in hpnicfNqaReactActionType is
                        generated when hpnicfNqaReactCurrentStatus changes.

        accumulative(3): If reaction threshold type is accumulative and
                        the times of watched operation accumulatively exceeds
                        the limit specified by hpnicfNqaReactThresholdAccumNum,
                        an action specified in hpnicfNqaReactActionType is
                        generated when hpnicfNqaReactCurrentStatus changes.

        If reaction threshold type is not configured, the value of this
        object is 'invalid'."
    ::= { hpnicfNqaReactionEntry 7 }

hpnicfNqaReactThresholdConsecNum OBJECT-TYPE
    SYNTAX      Unsigned32
    MAX-ACCESS  read-create
    STATUS      current
    DESCRIPTION
        "This object defines a consecutive threshold limit.

        The value is zero when hpnicfNqaReactThresholdType
        is not 'consecutive'."
    DEFVAL { 0 }
    ::= { hpnicfNqaReactionEntry 8 }

hpnicfNqaReactThresholdAccumNum OBJECT-TYPE
    SYNTAX      Unsigned32
    MAX-ACCESS  read-create
    STATUS      current
    DESCRIPTION
        "This object defines an accumulative threshold limit.

        The value is zero when the hpnicfNqaReactThresholdType
        is not 'accumulative'."
    DEFVAL { 0 }
    ::= { hpnicfNqaReactionEntry 9 }

hpnicfNqaReactActionType OBJECT-TYPE
    SYNTAX      INTEGER {
                           none(0),
                           trapOnly(1),
                           triggerOnly(2),
                           trapAndTrigger(3)
                        }
    MAX-ACCESS  read-create
    STATUS      current
    DESCRIPTION
        "Specifies the type of reaction to generate if the specified
        violation type occurs for the monitored element:

        none               - No reaction is generated
        trapOnly           - A trap is generated
        triggerOnly        - All trigger actions defined for this
                             entry are generated
        trapAndTrigger     - Both a trap and all trigger actions
                             are generated "
    DEFVAL { none }
    ::= { hpnicfNqaReactionEntry 10 }

hpnicfNqaReactCurrentStatus OBJECT-TYPE
    SYNTAX      INTEGER {
                            invalid(1),
                            overThreshold(2),
                            belowThreshold(3)
                        }
    MAX-ACCESS  read-only
    STATUS      current
    DESCRIPTION
        "Specifies the current status of this reaction entry:

        invalid  - The status of the reaction entry is unknown.

        overThreshold   - The status of the reaction entry is overThreshold
                          when the monitored result exceeds the threshold
                          value for the hpnicfNqaReactThresholdType.

        belowThreshold  - The status of the reaction entry is belowThreshold
                          when the monitored result is under the threshold
                          value for the hpnicfNqaReactThresholdType."
    ::= { hpnicfNqaReactionEntry 11 }

hpnicfNqaReactRowStatus OBJECT-TYPE
    SYNTAX      RowStatus
    MAX-ACCESS  read-create
    STATUS      current
    DESCRIPTION
        "This object allows entries to be created and deleted
        in the hpnicfNqaReactionTable.

        Creation of an entry in this table results in a new set of reaction
        configurations which take effect immediately.

        Deletion of an entry in this table results in corresponding reaction
        configurations are being deleted and stop taking effect."
    REFERENCE
        "See definition of RowStatus in RFC 2579, 'Textual
        Conventions for SMIv2.'"
    ::= { hpnicfNqaReactionEntry 12 }

hpnicfNqaReactCheckedNum OBJECT-TYPE
    SYNTAX      Unsigned32
    MAX-ACCESS  read-only
    STATUS      current
    DESCRIPTION
        "The number of checked element samples that are monitored."
    DEFVAL { 0 }
    ::= { hpnicfNqaReactionEntry 13 }

hpnicfNqaReactThresholdNum OBJECT-TYPE
    SYNTAX      Unsigned32
    MAX-ACCESS  read-only
    STATUS      current
    DESCRIPTION
        "The number of checked element samples that are over threshold."
    DEFVAL { 0 }
    ::= { hpnicfNqaReactionEntry 14 }

-- Statistics Reaction Table
hpnicfNqaStatisticsReactionTable OBJECT-TYPE
    SYNTAX      SEQUENCE OF HpnicfNqaStatisticsReactionEntry
    MAX-ACCESS  not-accessible
    STATUS      current
    DESCRIPTION
        "A table of NQA test monitoring notification and
        reaction configuration definitions.

        An entry is removed from this table when its
        corresponding pingCtlEntry is deleted."
  ::= { hpnicfNqaObjects 14 }

hpnicfNqaStatisticsReactionEntry OBJECT-TYPE
    SYNTAX      HpnicfNqaStatisticsReactionEntry
    MAX-ACCESS  not-accessible
    STATUS      current
    DESCRIPTION
        "Defines an entry in the hpnicfNqaStatisticsReactionTable. The
        first two index elements identify the pingCtlEntry that a
        hpnicfNqaReactItemIndex belongs to. The third index element
        identifies an entry in the hpnicfNqaStatisticsResultsTable.
        The forth index element selects a single reaction."
    INDEX
        {
            hpnicfNqaStatReactOwnerIndex,
            hpnicfNqaStatReactTestName,
            hpnicfNqaStatReactIndex,
            hpnicfNqaStatReactItemIndex
        }
    ::= { hpnicfNqaStatisticsReactionTable 1 }

HpnicfNqaStatisticsReactionEntry ::=
    SEQUENCE
        {
            hpnicfNqaStatReactOwnerIndex               SnmpAdminString,
            hpnicfNqaStatReactTestName                 SnmpAdminString,
            hpnicfNqaStatReactIndex                    Unsigned32,
            hpnicfNqaStatReactItemIndex                Unsigned32,
            hpnicfNqaStatReactCheckedNum               Counter32,
            hpnicfNqaStatReactThresholdNum             Counter32
        }

hpnicfNqaStatReactOwnerIndex OBJECT-TYPE
    SYNTAX      SnmpAdminString (SIZE(0..32))
    MAX-ACCESS  not-accessible
    STATUS      current
    DESCRIPTION
        "The first index of hpnicfNqaStatisticsReactionTable, it is the same
        as pingCtlOwnerIndex in pingCtlTable."
    ::= { hpnicfNqaStatisticsReactionEntry 1 }

hpnicfNqaStatReactTestName OBJECT-TYPE
    SYNTAX      SnmpAdminString (SIZE(0..32))
    MAX-ACCESS  not-accessible
    STATUS      current
    DESCRIPTION
        "The second index of hpnicfNqaStatisticsReactionTable, it is the same
        as pingCtlTestName in pingCtlTable."
    ::= { hpnicfNqaStatisticsReactionEntry 2 }

hpnicfNqaStatReactIndex OBJECT-TYPE
    SYNTAX      Unsigned32
    MAX-ACCESS  not-accessible
    STATUS      current
    DESCRIPTION
        "The third index of hpnicfNqaStatisticsReactionTable. An entry in
        this table is created when the statistics result of a NQA probe
        is determined.

        An implementation MUST start assigning hpnicfNqaStatResIndex values
        at 1 and wrap after exceeding the maximum possible value as
        defined by the limit of this object ('ffffffff'h)."
    DEFVAL { 0 }
    ::= { hpnicfNqaStatisticsReactionEntry 3 }

hpnicfNqaStatReactItemIndex OBJECT-TYPE
    SYNTAX      Unsigned32
    MAX-ACCESS  not-accessible
    STATUS      current
    DESCRIPTION
        "The forth index of hpnicfNqaStatisticsReactionTable, it definitely
        identifies one of the reaction configurations for a test"
    DEFVAL { 0 }
    ::= { hpnicfNqaStatisticsReactionEntry 4 }

hpnicfNqaStatReactCheckedNum OBJECT-TYPE
    SYNTAX      Counter32
    MAX-ACCESS  read-only
    STATUS      current
    DESCRIPTION
        "The number of checked element samples that are monitored."
    DEFVAL { 0 }
    ::= { hpnicfNqaStatisticsReactionEntry 5 }

hpnicfNqaStatReactThresholdNum OBJECT-TYPE
    SYNTAX      Counter32
    MAX-ACCESS  read-only
    STATUS      current
    DESCRIPTION
        "The number of checked element samples that are over threshold."
    DEFVAL { 0 }
    ::= { hpnicfNqaStatisticsReactionEntry 6 }


-- Notification Definition section
hpnicfNqaNotifications  OBJECT IDENTIFIER ::= { hpnicfNqa 3 }
hpnicfNqaProbeTimeOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "It is generated when the value of hpnicfNqaReactCurrentStatus
        changes.
        The change may occur when the watched condition is over threshold
        or below threshold.

        The over threshold situations is specified as below.
          1. Probe time(equals to RTT for some type of tests) is not in
             the range hpnicfNqaReactThresholdLowerLimit through
             hpnicfNqaReactThresholdUpperLimit.
          2. The probe time is accumulatively not in the range
             hpnicfNqaReactThresholdLowerLimit through
             hpnicfNqaReactThresholdUpperLimit for a number of times
             specified in hpnicfNqaReactThresholdAccumNum.
          3. The probe time is consecutively in the range
             hpnicfNqaReactThresholdLowerLimit through
             hpnicfNqaReactThresholdUpperLimit for a number of times
             specified in hpnicfNqaReactThresholdConsecNum.

        This notification is valid only when hpnicfNqaReactActionType
        is 'trapOnly' or 'trapAndTrigger' and pingCtlType of the test
        is not hpnicfNqajitter."
    ::= { hpnicfNqaNotifications 1 }

hpnicfNqaJitterRTTOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "It is generated when the value of hpnicfNqaReactCurrentStatus
        changes.
        The change may occur when the watched condition is over threshold
        or below threshold.

        The over threshold situations is specified as below.
          1. The average NQA round-trip-time (RTT) of jitter packets
             is not in the range hpnicfNqaReactThresholdLowerLimit through
             hpnicfNqaReactThresholdUpperLimit.
          2. The RTT of jitter packets is accumulatively not in the range
             hpnicfNqaReactThresholdLowerLimit through
             hpnicfNqaReactThresholdUpperLimit for a number of times specified
             in hpnicfNqaReactThresholdAccumNum in one test.

        This notification is valid only when hpnicfNqaReactActionType
        is 'trapOnly' or 'trapAndTrigger' and pingCtlType of the test
        is hpnicfNqajitter."
    ::= { hpnicfNqaNotifications 2 }

hpnicfNqaProbeFailure NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "It is generated when the value of hpnicfNqaReactCurrentStatus
        changes.
        The change may occur when the watched condition is over threshold
        or below threshold.

        The over threshold situations is specified as below.
          1. When the probe test accumulatively failed for a
             number of times specified in hpnicfNqaReactThresholdAccumNum in one
             test while the value of hpnicfNqaReactThresholdType is 'accumulative'.
          2. When the probe test consecutively failed for
             a number of times specified in hpnicfNqaReactThresholdConsecNum in one
             test while the value of hpnicfNqaReactThresholdType is 'consecutive'.

        This notification is valid only when hpnicfNqaReactActionType
        is 'trapOnly' or 'trapAndTrigger' and pingCtlType of the test
        is not hpnicfNqajitter."
    ::= { hpnicfNqaNotifications 3 }

hpnicfNqaJitterPacketLoss NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "It is generated when the value of hpnicfNqaReactCurrentStatus
        changes.
        The change may occur when the watched condition is over threshold
        or below threshold.

        The over threshold situations is specified as below.
          1. When the jitter packets accumulatively lost for a
             number of times specified in hpnicfNqaReactThresholdAccumNum in one
             test while the value of hpnicfNqaReactThresholdType is 'accumulative'.

        This notification is valid only when hpnicfNqaReactActionType
        is 'trapOnly' or 'trapAndTrigger' and pingCtlType of the test
        is hpnicfNqajitter."
    ::= { hpnicfNqaNotifications 4 }

hpnicfNqaJitterSDOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "The SD means the jitter values from source to destination.

        It is generated when the value of hpnicfNqaReactCurrentStatus
        changes.
        The change may occur when the watched condition is over threshold
        or below threshold.

        The over threshold situations is specified as below.
          1. The average of SD in one jitter test is not in the range
             hpnicfNqaReactThresholdLowerLimit through
             hpnicfNqaReactThresholdUpperLimit and the
             hpnicfNqaReactThresholdType is specified as 'average' type.
          2. The average of SD in one jitter test is accumulatively
             not in the range hpnicfNqaReactThresholdLowerLimit through
             hpnicfNqaReactThresholdUpperLimit for a number of times specified
             in hpnicfNqaReactThresholdAccumNum and the
             hpnicfNqaReactThresholdType is specified as 'accumulative' type.

        This notification is valid only when hpnicfNqaReactActionType
        is 'trapOnly' or 'trapAndTrigger' and pingCtlType of the test
        is hpnicfNqajitter."
    ::= { hpnicfNqaNotifications 5 }

hpnicfNqaJitterDSOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactThresholdType,
            hpnicfNqaReactCurrentStatus
        }
    STATUS  current
    DESCRIPTION
        "The DS means the jitter values from destination to source.

        It is generated when the value of hpnicfNqaReactCurrentStatus
        changes.
        The change may occur when the watched condition is over threshold
        or below threshold.

        The over threshold situations is specified as below.
          1. The average of DS in one jitter test is not in the range
             hpnicfNqaReactThresholdLowerLimit through
             hpnicfNqaReactThresholdUpperLimit and the
             hpnicfNqaReactThresholdType is specified as 'average' type.
          2. The average of DS in one jitter test is accumulatively not
             in the range hpnicfNqaReactThresholdLowerLimit through
             hpnicfNqaReactThresholdUpperLimit for a number of times specified
             in hpnicfNqaReactThresholdAccumNum and the
             hpnicfNqaReactThresholdType is specified as 'accumulative' type.

        This notification is valid only when hpnicfNqaReactActionType
        is 'trapOnly' or 'trapAndTrigger' and pingCtlType of the test
        is hpnicfNqajitter."
    ::= { hpnicfNqaNotifications 6 }

hpnicfNqaICPIFOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactCurrentStatus
        }
    STATUS  current
    DESCRIPTION
        "It is generated when the value of hpnicfNqaReactCurrentStatus
        changes.
        The change may occur when the watched condition is over threshold
        or below threshold.

        The over threshold situations is specified as below.
          1. When the ICPIF value in one jitter test is not in
             the range hpnicfNqaReactThresholdLowerLimit through
             hpnicfNqaReactThresholdUpperLimit.

        This notification is valid only when hpnicfNqaReactActionType
        is 'trapOnly' or 'trapAndTrigger', pingCtlType of the test
        is hpnicfNqajitter and hpnicfNqaCtlCodecType is 'g711Alaw' or 'g711Ulaw'
        or 'g729A'."
    ::= { hpnicfNqaNotifications 7 }

hpnicfNqaMOSOverThreshold NOTIFICATION-TYPE
    OBJECTS {
            hpnicfNqaReactOwnerIndex,
            hpnicfNqaReactTestName,
            hpnicfNqaReactItemIndex,
            pingCtlTargetAddressType,
            pingCtlTargetAddress,
            pingCtlType,
            pingCtlDescr,
            hpnicfNqaReactCurrentStatus
        }
    STATUS  current
    DESCRIPTION
        "It is generated when the value of hpnicfNqaReactCurrentStatus
        changes.
        The change may occur when the watched condition is over threshold
        or below threshold.

        The over threshold situations is specified as below.
          1. When the MOS value in one jitter test is not in
             the range hpnicfNqaReactThresholdLowerLimit through
             hpnicfNqaReactThresholdUpperLimit.

        This notification is valid only when hpnicfNqaReactActionType
        is 'trapOnly' or 'trapAndTrigger', pingCtlType of the test
        is hpnicfNqajitter and hpnicfNqaCtlCodecType is 'g711Alaw' or 'g711Ulaw'
        or 'g729A'."
    ::= { hpnicfNqaNotifications 8 }

END
