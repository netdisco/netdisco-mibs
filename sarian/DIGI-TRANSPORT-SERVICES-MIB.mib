DIGI-TRANSPORT-SERVICES-MIB DEFINITIONS ::= BEGIN
--
-- Copyright (c) 2014 Digi International Inc. All rights reserved.
--
-- Digi Transport Services MIB
--
-- Updates
--
--  24 May 2016 Created
--

IMPORTS
    enterprises                                 FROM RFC1155-SMI
    MODULE-IDENTITY, OBJECT-TYPE, Integer32,
    Unsigned32, Counter32, Counter64, IpAddress FROM SNMPv2-SMI
    DisplayString, MacAddress, TruthValue       FROM SNMPv2-TC;

digiServicesMIB MODULE-IDENTITY
	LAST-UPDATED "201605240000Z"	-- 24 May 2016
	ORGANIZATION
		"Digi International, Inc."
	CONTACT-INFO
		"Digi International Tech Support

		 Phone: 877 912 3444     (US and Canada)
		 		+1 952 912 3456  (Worldwide)
		 Email: <Tech.Support@digi.com>"
	DESCRIPTION
		"The Digi Services MIB for managing the Services configuration on the 
		 Digi TransPort product range."
	::= { sarian 10002 }


sarian OBJECT IDENTIFIER ::= { enterprises 16378 }
digiServices OBJECT IDENTIFIER ::= { sarian 10002 }
services-config OBJECT IDENTIFIER ::= { digiServices 1 }

--
-- Services config
--

servicesTelnet    OBJECT-TYPE
    SYNTAX      INTEGER { off (0), on (1) }
    MAX-ACCESS  read-only
    STATUS      current
    DESCRIPTION
        "Telnet server. (on/off)"
    ::= { services-config 1 }

servicesHttp    OBJECT-TYPE
    SYNTAX      INTEGER { off (0), on (1) }
    MAX-ACCESS  read-only
    STATUS      current
    DESCRIPTION
        "HTTP server. (on/off)"
    ::= { services-config 2 }

servicesTelnets    OBJECT-TYPE
    SYNTAX      INTEGER { off (0), on (1) }
    MAX-ACCESS  read-only
    STATUS      current
    DESCRIPTION
        "Secure Telnet server. (on/off)"
    ::= { services-config 3 }

servicesHttps    OBJECT-TYPE
    SYNTAX      INTEGER { off (0), on (1) }
    MAX-ACCESS  read-only
    STATUS      current
    DESCRIPTION
        "HTTPs server. (on/off)"
    ::= { services-config 4 }

servicesSsh    OBJECT-TYPE
    SYNTAX      INTEGER { off (0), on (1) }
    MAX-ACCESS  read-only
    STATUS      current
    DESCRIPTION
        "SSH server. (on/off)"
    ::= { services-config 5 }

servicesFtp    OBJECT-TYPE
    SYNTAX      INTEGER { off (0), on (1) }
    MAX-ACCESS  read-only
    STATUS      current
    DESCRIPTION
        "FTP server. (on/off)"
    ::= { services-config 6 }

servicesAsyTcp    OBJECT-TYPE
    SYNTAX      INTEGER { off (0), on (1) }
    MAX-ACCESS  read-only
    STATUS      current
    DESCRIPTION
        "ASY to TCP support. (on/off)"
    ::= { services-config 7 }

servicesZing    OBJECT-TYPE
    SYNTAX      INTEGER { off (0), on (1) }
    MAX-ACCESS  read-only
    STATUS      current
    DESCRIPTION
        "Zing support. (on/off)"
    ::= { services-config 8 }

END
