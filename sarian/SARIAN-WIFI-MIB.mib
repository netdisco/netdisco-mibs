SARIAN-WIFI-MIB DEFINITIONS ::= BEGIN
--
-- Copyright (c) 2014 Digi International Inc. All rights reserved.
--
-- Sarian Wi-Fi MIB
--
-- Updates
--
--  7 Jan 2010 Created
-- 28 Jan 2014 Updated to support multiple Wi-Fi modules.
--

IMPORTS
    enterprises                                 FROM RFC1155-SMI
    MODULE-IDENTITY, OBJECT-TYPE, Integer32,
    Unsigned32, Counter32, Counter64, IpAddress FROM SNMPv2-SMI
    DisplayString, MacAddress, TruthValue       FROM SNMPv2-TC;

sarianWifiMIB MODULE-IDENTITY
	LAST-UPDATED "201401290000Z"	-- 29 Jan 2014
	ORGANIZATION
		"Digi International, Inc."
	CONTACT-INFO
		"Digi International Tech Support

		 Phone: 877 912 3444     (US and Canada)
		 		+1 952 912 3456  (Worldwide)
		 EMail: <Tech.Support@digi.com>"
	DESCRIPTION
		"The Sarian WiFi MIB for managing the WiFi interfaces on the 
		 Digi TransPort product range."
	REVISION	"201401290000Z"	-- 29 Jan 2014
	DESCRIPTION
		"Updated to support the Dual-WiFi feature."
	::= { sarian 11001 }


sarian           OBJECT IDENTIFIER ::= { enterprises 16378 }
sarian-wifi      OBJECT IDENTIFIER ::= { sarian 10001 }

wifi-config      OBJECT IDENTIFIER ::= { sarian-wifi 1 }
wifi-node-config OBJECT IDENTIFIER ::= { sarian-wifi 2 }
wifi-connections OBJECT IDENTIFIER ::= { sarian-wifi 3 }
wifi-stats       OBJECT IDENTIFIER ::= { sarian-wifi 4 }
wifi-iface-stats OBJECT IDENTIFIER ::= { sarian-wifi 5 }
wifi-client-connections OBJECT IDENTIFIER ::= { sarian-wifi 6 }
wifi-module-config      OBJECT IDENTIFIER ::= { sarian-wifi 7 }
wifi-module-stats       OBJECT IDENTIFIER ::= { sarian-wifi 8 }
wifi-module-iface-stats OBJECT IDENTIFIER ::= { sarian-wifi 9 }

--
-- Sarian Wifi config (global)
--

wifiCountry     OBJECT-TYPE
    SYNTAX      OCTET STRING
    MAX-ACCESS  read-write
    STATUS      deprecated
    DESCRIPTION
           "The Wifi Country code."
        ::= { wifi-config 1 }

wifiChannel OBJECT-TYPE
    SYNTAX      OCTET STRING
    MAX-ACCESS  read-write
    STATUS      deprecated
    DESCRIPTION
        "The channel number."
    ::= { wifi-config 2 }

wifiMACFilter  OBJECT-TYPE
    SYNTAX      INTEGER  { enabled (1), disabled (2) }
    MAX-ACCESS  read-write
    STATUS      deprecated
    DESCRIPTION
        "MAC filtering functionality. This allows clients to
        be allowed or denied a connection to the host based
        on their MAC address."
    ::= { wifi-config 3 }

wifiAnalyzer    OBJECT-TYPE
    SYNTAX      INTEGER
    MAX-ACCESS  read-write
    STATUS      deprecated
    DESCRIPTION
        "Packet analyzer function. (on/off)"
    ::= { wifi-config 4 }

wifiAnaMgmt     OBJECT-TYPE
    SYNTAX      INTEGER { none (1),
                      nobeacons (2),
                      all (3) }
    MAX-ACCESS  read-write
    STATUS      deprecated
    DESCRIPTION
          "Which wifi management frames to capture/process/display."
    ::= { wifi-config 5 }

wifiAnaData     OBJECT-TYPE
    SYNTAX      INTEGER {
                     none (1),
                     nonull (2),
                     all (3)
                    } 
    MAX-ACCESS  read-write
    STATUS      deprecated
    DESCRIPTION
         "Which data packets to capture/process/dispay."
    ::= { wifi-config 6 }

wifiNumNodes    OBJECT-TYPE
    SYNTAX      INTEGER ( 1..4 )
    MAX-ACCESS  read-only
    STATUS      deprecated
    DESCRIPTION
         "The number of Wifi interfaces (Access Points/Clients)
         that the module supports."
    ::= { wifi-config 7 }

--
-- Sarian Wifi node config
--
wifiNodeTable   OBJECT-TYPE
    SYNTAX      SEQUENCE OF WifiNodeEntry
    MAX-ACCESS  not-accessible
    STATUS      current
    DESCRIPTION
         "A table containing configuration information on a per
          node basis."
    ::= { wifi-node-config 1 }

wifiNodeEntry   OBJECT-TYPE
    SYNTAX      WifiNodeEntry
    MAX-ACCESS  not-accessible
    STATUS      current
    DESCRIPTION
             "An entry containing configuration for a particular Wifi node."
    INDEX { wifiNodeIndex }
    ::= { wifiNodeTable 1 }

WifiNodeEntry ::=
    SEQUENCE{
    wifiNodeIndex               INTEGER,
    wifiNodeDescription         OCTET STRING,
    wifiNodeEnabled             INTEGER,
    wifiNodeSSID                OCTET STRING,
    wifiNodeIsolation           TruthValue,
    wifiNodeInactTimeout        INTEGER,
    wifiNodeSecurity            INTEGER,
    wifiNodeWEPType             INTEGER,
    wifiNodeWEPKeyLen           INTEGER,
    wifiNodeWEPKeyIndex         INTEGER,
    wifiNodeWPAType             INTEGER,
    wifiNodeSharedKey           OCTET STRING,
	wifiNodeMode				OCTET STRING
    }

wifiNodeIndex   OBJECT-TYPE
    SYNTAX      INTEGER (0..128)
    MAX-ACCESS  read-write
    STATUS      current
    DESCRIPTION
         "Index into the node table"
    ::= { wifiNodeEntry 1 }

wifiNodeDescription OBJECT-TYPE
    SYNTAX      OCTET STRING
    MAX-ACCESS  read-write
    STATUS      current
    DESCRIPTION
         "A short text description of the unit."
    ::= { wifiNodeEntry 2 }

wifiNodeEnabled OBJECT-TYPE
    SYNTAX      INTEGER { enabled (1), disabled (2) } 
    MAX-ACCESS  read-write
    STATUS      current
    DESCRIPTION
         "On/off status of the module."
    ::= { wifiNodeEntry 3 }

wifiNodeSSID OBJECT-TYPE
    SYNTAX      OCTET STRING (SIZE (0..32))
    MAX-ACCESS  read-write
    STATUS      current
    DESCRIPTION
         "The SSID of the module."
    ::= { wifiNodeEntry 4 }

wifiNodeIsolation OBJECT-TYPE
    SYNTAX      TruthValue
    MAX-ACCESS  read-write
    STATUS      current
    DESCRIPTION
         "Whether or not the clients are isolated from each other.
         That is - whether or not they can see each other's traffic."
    ::= { wifiNodeEntry 5 }

wifiNodeInactTimeout OBJECT-TYPE
    SYNTAX      INTEGER (0..2147483647)
    MAX-ACCESS  read-write
    STATUS      current
    DESCRIPTION
         "Inactivity timeout - the period after which an inactive client
         (cached) will be forcibly disconnected. The period is the
         number of 15 second intervals so the default of 300 will
         give a timeout period of 4500s (75 minutes)."
    ::= { wifiNodeEntry 6 }

wifiNodeSecurity     OBJECT-TYPE
    SYNTAX      INTEGER {
                      none (1),
                      wep (2),
                      wpapsk (3),
                      wpa2psk (4)
                      } 
    MAX-ACCESS  read-write
    STATUS      current
    DESCRIPTION
         "Security setting WEP/WPA."
    ::= { wifiNodeEntry 7 }

wifiNodeWEPType      OBJECT-TYPE
    SYNTAX   INTEGER {
                      open (1),
                      sharedkey (2)
                     } 
    MAX-ACCESS  read-write
    STATUS      current
    DESCRIPTION
         "Whether authentication is open or uses a
          a shared key."
    ::= { wifiNodeEntry 8 }

wifiNodeWEPKeyLen    OBJECT-TYPE
    SYNTAX      INTEGER ( 64 | 128 )
    MAX-ACCESS  read-write
    STATUS      current
    DESCRIPTION
         "The length of the WEP key."
    ::= { wifiNodeEntry 9 }

wifiNodeWEPKeyIndex  OBJECT-TYPE
    SYNTAX      INTEGER ( 1..4 )
    MAX-ACCESS  read-write
    STATUS      current
    DESCRIPTION
         "Where to find the WEP key in the list of global keys."
    ::= { wifiNodeEntry 10 }

wifiNodeWPAType      OBJECT-TYPE
    SYNTAX   INTEGER {
                      tkip (1),
                      aes (2)
                     } 
    MAX-ACCESS  read-write
    STATUS      current
    DESCRIPTION
         "The encryption method to use - TKIP/AES."
    ::= { wifiNodeEntry 11 }

wifiNodeSharedKey    OBJECT-TYPE
    SYNTAX      OCTET STRING (SIZE (0..64))
    MAX-ACCESS  read-only
    STATUS      current
    DESCRIPTION
         "The passphrase used to generate the WPA group key."
    ::= { wifiNodeEntry 12 }

wifiNodeMode    OBJECT-TYPE
    SYNTAX      OCTET STRING (SIZE (0..64))
    MAX-ACCESS  read-only
    STATUS      current
    DESCRIPTION
         "The operating mode (AP or client)."
    ::= { wifiNodeEntry 13 }

--
-- Wifi Connection Table
--
wifiConnTable   OBJECT-TYPE
    SYNTAX      SEQUENCE OF ConnEntry
    MAX-ACCESS  not-accessible
    STATUS      current
    DESCRIPTION
         "A list of entries containing information on all
         Wifi clients on this system."
    ::= { wifi-connections 1 }

wifiConnEntry   OBJECT-TYPE
    SYNTAX      ConnEntry
    MAX-ACCESS  not-accessible
    STATUS      current
    DESCRIPTION
         "An entry containing connection information for a particular
         Wifi client."
    INDEX { wifiConnModule, wifiConnNode }
    ::= { wifiConnTable 1 }

ConnEntry ::=
        SEQUENCE {
                wifiConnNode       MacAddress,
                wifiConnRSSI       INTEGER,
                wifiConnFlags      DisplayString,
                wifiConnPowerSave  DisplayString,
                wifiConnNegRates   DisplayString,
                wifiConnCapability DisplayString,
                wifiConnModule     INTEGER,
                wifiConnMode       DisplayString,
                wifiConnTxRate     DisplayString,
                wifiConnRxRate     DisplayString,
                wifiConnChannel    INTEGER
        }

wifiConnNode OBJECT-TYPE
    SYNTAX      MacAddress
    MAX-ACCESS  read-only
    STATUS      current
    DESCRIPTION
         "The MAC address of the connected client."
    ::= { wifiConnEntry 1 }

wifiConnRSSI OBJECT-TYPE
    SYNTAX      INTEGER
    MAX-ACCESS  read-only
    STATUS      current
    DESCRIPTION
         "The received signal strength indication."
    ::= { wifiConnEntry 2 }

wifiConnFlags OBJECT-TYPE
    SYNTAX      DisplayString
    MAX-ACCESS  read-only
    STATUS      current
    DESCRIPTION
         "A list of the flags set by the client eg. ERP if using
          extended rate protocol etc."
    ::= { wifiConnEntry 3 }

wifiConnPowerSave OBJECT-TYPE
    SYNTAX      DisplayString
    MAX-ACCESS  read-only
    STATUS      current
    DESCRIPTION
         "Power save status of client ie whether it is awake or
          asleep."
    ::= { wifiConnEntry 4 }

wifiConnNegRates OBJECT-TYPE
    SYNTAX      DisplayString
    MAX-ACCESS  read-only
    STATUS      current
    DESCRIPTION
         "A list of the negotiated data rates."
    ::= { wifiConnEntry 5 }

wifiConnCapability OBJECT-TYPE
    SYNTAX      DisplayString
    MAX-ACCESS  read-only
    STATUS      current
    DESCRIPTION
         "Capability information for the connected client.
         This includes such information as whether the
         client support short preambles, privacy etc."
    ::= { wifiConnEntry 6 }

wifiConnModule OBJECT-TYPE
    SYNTAX      INTEGER ( 1..2 )
    MAX-ACCESS  read-only
    STATUS      current
    DESCRIPTION
         "Wi-Fi module on which this connection is on."
    ::= { wifiConnEntry 7 }

wifiConnMode OBJECT-TYPE
    SYNTAX      DisplayString
    MAX-ACCESS  read-only
    STATUS      current
    DESCRIPTION
         "Connection mode for the connected client."
    ::= { wifiConnEntry 8 }

wifiConnTxRate OBJECT-TYPE
    SYNTAX      DisplayString
    MAX-ACCESS  read-only
    STATUS      current
    DESCRIPTION
         "Transmit rate for the connected client."
    ::= { wifiConnEntry 9 }

wifiConnRxRate OBJECT-TYPE
    SYNTAX      DisplayString
    MAX-ACCESS  read-only
    STATUS      current
    DESCRIPTION
         "Receive rate for the connected client."
    ::= { wifiConnEntry 10 }

wifiConnChannel OBJECT-TYPE
    SYNTAX      INTEGER
    MAX-ACCESS  read-only
    STATUS      current
    DESCRIPTION
         "Channel for the connected client."
    ::= { wifiConnEntry 11 }

--
-- Wifi Stats
--
wifiAdminStatus  OBJECT-TYPE
    SYNTAX      INTEGER { up (1), down (2) } 
    MAX-ACCESS  read-only
    STATUS      deprecated
    DESCRIPTION
         "The administrative status of the interface ie whether the
          interface is up or down."
    ::= { wifi-stats 1 }

wifiOperStatus   OBJECT-TYPE
    SYNTAX      INTEGER { up (1), down (2) } 
    MAX-ACCESS  read-only
    STATUS      deprecated
    DESCRIPTION
         "The operational status of the interface ie up/down."
    ::= { wifi-stats 2 }

wifiMACAddress   OBJECT-TYPE
    SYNTAX      MacAddress
    MAX-ACCESS  read-only
    STATUS      deprecated
    DESCRIPTION
         "The MAC address of the wifi module."
    ::= { wifi-stats 3 }

wifiChannelUsed  OBJECT-TYPE
    SYNTAX      INTEGER
    MAX-ACCESS  read-only
    STATUS      deprecated
    DESCRIPTION
         "The channel being used for the connection."
    ::= { wifi-stats 4 }

wifiRxPackets   OBJECT-TYPE
    SYNTAX      Counter32
    MAX-ACCESS  read-only
    STATUS      deprecated
    DESCRIPTION
         "The number of packets received."
    ::= { wifi-stats 5 }

wifiRxBytes     OBJECT-TYPE
    SYNTAX      Counter32
    MAX-ACCESS  read-only
    STATUS      deprecated
    DESCRIPTION
        "The number of bytes received."
    ::= { wifi-stats 6 }
                  
wifiRxDropped   OBJECT-TYPE
    SYNTAX      Counter32
    MAX-ACCESS  read-only
    STATUS      deprecated
    DESCRIPTION
        "The number of dropped frames."
    ::= { wifi-stats 7 }
                  
wifiRxErrors    OBJECT-TYPE
    SYNTAX      Counter32
    MAX-ACCESS  read-only
    STATUS      deprecated
    DESCRIPTION
        "The number of receive errors."
    ::= { wifi-stats 8 }
                  
wifiTxPackets   OBJECT-TYPE
    SYNTAX      Counter32
    MAX-ACCESS  read-only
    STATUS      deprecated
    DESCRIPTION
        "The number of packets transmitted."
    ::= { wifi-stats 9 }
                  
wifiTxBytes     OBJECT-TYPE
    SYNTAX      Counter32
    MAX-ACCESS  read-only
    STATUS      deprecated
    DESCRIPTION
        "The number of bytes transmitted."
    ::= { wifi-stats 10 }
                  
wifiTxErrors    OBJECT-TYPE
    SYNTAX      Counter32
    MAX-ACCESS  read-only
    STATUS      deprecated
    DESCRIPTION
        "The number of transmit errors."
    ::= { wifi-stats 11 }

--
-- Wifi Interface Stats.
--
wifiStatRxBadVersion OBJECT-TYPE
    SYNTAX      Counter32
    MAX-ACCESS  read-only
    STATUS      current
    DESCRIPTION
         "Frame received with incorrect version number."
    ::= { wifi-iface-stats 1 }

wifiStatRxTooShort   OBJECT-TYPE
    SYNTAX      Counter32
    MAX-ACCESS  read-only
    STATUS      current
    DESCRIPTION
         "Received frame too short."
    ::= { wifi-iface-stats 2 }

 wifiStatRxWrongBSS   OBJECT-TYPE
    SYNTAX      Counter32
    MAX-ACCESS  read-only
    STATUS      current
    DESCRIPTION
         "Received frame has incorrect BSS."
    ::= { wifi-iface-stats 3 }

 wifiStatRxDuplicate  OBJECT-TYPE
    SYNTAX      Counter32
    MAX-ACCESS  read-only
    STATUS      current
    DESCRIPTION
         "Duplicate frame received."
    ::= { wifi-iface-stats 4 }

 wifiStatRxWrongDir   OBJECT-TYPE
    SYNTAX      Counter32
    MAX-ACCESS  read-only
    STATUS      current
    DESCRIPTION
         "Frame received with incorrect direction flag."
    ::= { wifi-iface-stats 5 }

 wifiStatRxMcastEcho  OBJECT-TYPE
    SYNTAX      Counter32
    MAX-ACCESS  read-only
    STATUS      current
    DESCRIPTION
         "Multicast echo frame received."
    ::= { wifi-iface-stats 6 }

 wifiStatRxNotAssoc   OBJECT-TYPE
    SYNTAX      Counter32
    MAX-ACCESS  read-only
    STATUS      current
    DESCRIPTION
         "Frame received from non-associated client."
    ::= { wifi-iface-stats 7 }

 wifiStatRxNoWEP      OBJECT-TYPE
    SYNTAX      Counter32
    MAX-ACCESS  read-only
    STATUS      current
    DESCRIPTION
         "WEP frame expected but WEP flag not set."
    ::= { wifi-iface-stats 8 }

 wifiStatRxUnencrypted OBJECT-TYPE
    SYNTAX      Counter32
    MAX-ACCESS  read-only
    STATUS      current
    DESCRIPTION
         "Unencrypted frame count."
    ::= { wifi-iface-stats 9 }

 wifiStatRxWEPFail    OBJECT-TYPE
    SYNTAX      Counter32
    MAX-ACCESS  read-only
    STATUS      current
    DESCRIPTION
         "WEP fail count."
    ::= { wifi-iface-stats 10 }

 wifiStatRxDecapFail  OBJECT-TYPE
    SYNTAX      Counter32
    MAX-ACCESS  read-only
    STATUS      current
    DESCRIPTION
         "Frame decapsulation fail count."
    ::= { wifi-iface-stats 11 }

 wifiStatRxMgmtDiscard OBJECT-TYPE
    SYNTAX      Counter32
    MAX-ACCESS  read-only
    STATUS      current
    DESCRIPTION
         "Management frame discard count."
    ::= { wifi-iface-stats 12 }

 wifiStatRxCtrlDiscard OBJECT-TYPE
    SYNTAX      Counter32
    MAX-ACCESS  read-only
    STATUS      current
    DESCRIPTION
         "Control frame discard count."
    ::= { wifi-iface-stats 13 }

 wifiStatRxRSTooBig   OBJECT-TYPE
    SYNTAX      Counter32
    MAX-ACCESS  read-only
    STATUS      current
    DESCRIPTION
         "Rate set too big."
    ::= { wifi-iface-stats 14 }

wifiStatRxElemMissing OBJECT-TYPE
    SYNTAX      Counter32
    MAX-ACCESS  read-only
    STATUS      current
    DESCRIPTION
        "Element missing from Rx frame." 
    ::= { wifi-iface-stats 15 }

 wifiStatRxElemTooBig OBJECT-TYPE
    SYNTAX      Counter32
    MAX-ACCESS  read-only
    STATUS      current
    DESCRIPTION
         "Element field in frame too big." 
    ::= { wifi-iface-stats 16 }

 wifiStatRxElemTooSmall OBJECT-TYPE
    SYNTAX      Counter32
    MAX-ACCESS  read-only
    STATUS      current
    DESCRIPTION
         "Element field in frame is too small." 
    ::= { wifi-iface-stats 17 }

 wifiStatRxElemUnknown OBJECT-TYPE
    SYNTAX      Counter32
    MAX-ACCESS  read-only
    STATUS      current
    DESCRIPTION
         "Unknown element in Rx frame." 
    ::= { wifi-iface-stats 18 }

 wifiStatRxBadChannel OBJECT-TYPE
    SYNTAX      Counter32
    MAX-ACCESS  read-only
    STATUS      current
    DESCRIPTION
         "Frame received with unexpected channel number." 
    ::= { wifi-iface-stats 19 }

 wifiStatRxChanMismatch OBJECT-TYPE
    SYNTAX      Counter32
    MAX-ACCESS  read-only
    STATUS      current
    DESCRIPTION
         "Channel mismatch error count. This can happen
         due to channel leakage." 
    ::= { wifi-iface-stats 20 }

 wifiStatRxNodeAlloc  OBJECT-TYPE
    SYNTAX      Counter32
    MAX-ACCESS  read-only
    STATUS      current
    DESCRIPTION
         "Node allocation count." 
    ::= { wifi-iface-stats 21 }

 wifiStatRxSSIDMismatch OBJECT-TYPE
    SYNTAX      Counter32
    MAX-ACCESS  read-only
    STATUS      current
    DESCRIPTION
         "SSID mismatch." 
    ::= { wifi-iface-stats 22 }

 wifiStatRxAuthUnsupported OBJECT-TYPE
    SYNTAX      Counter32
    MAX-ACCESS  read-only
    STATUS      current
    DESCRIPTION
         "We are doing encryption and received a frame for
         the wrong port number." 
    ::= { wifi-iface-stats 23 }

 wifiStatRxAuthFailed  OBJECT-TYPE
    SYNTAX      Counter32
    MAX-ACCESS  read-only
    STATUS      current
    DESCRIPTION
         "Authentication failure count." 
    ::= { wifi-iface-stats 24 }

 wifiStatRxAssocWrong OBJECT-TYPE
    SYNTAX      Counter32
    MAX-ACCESS  read-only
    STATUS      current
    DESCRIPTION
         "We received an association frame from a BSS
         we don't recognize." 
    ::= { wifi-iface-stats 25 }

 wifiStatRxAssocNotAuth OBJECT-TYPE
    SYNTAX      Counter32
    MAX-ACCESS  read-only
    STATUS      current
    DESCRIPTION
         "Count of the number of times we denied an association
         request from an unauthenticated source." 
    ::= { wifi-iface-stats 26 }

 wifiStatRxAssocCapMismatch OBJECT-TYPE
    SYNTAX      Counter32
    MAX-ACCESS  read-only
    STATUS      current
    DESCRIPTION
         "Association capabilities mismatch count." 
    ::= { wifi-iface-stats 27 }

 wifiStatRxAssocNoRate OBJECT-TYPE
    SYNTAX      Counter32
    MAX-ACCESS  read-only
    STATUS      current
    DESCRIPTION
         "Association frame with no rate set." 
    ::= { wifi-iface-stats 28 }

 wifiStatRxDeauthenticate OBJECT-TYPE
    SYNTAX      Counter32
    MAX-ACCESS  read-only
    STATUS      current
    DESCRIPTION
         "Deauthentication frame count." 
    ::= { wifi-iface-stats 29 }

 wifiStatRxDeassociate OBJECT-TYPE
    SYNTAX      Counter32
    MAX-ACCESS  read-only
    STATUS      current
    DESCRIPTION
         "Deassociation frame count." 
    ::= { wifi-iface-stats 30 }

 wifiStatRxBadSubtype OBJECT-TYPE
    SYNTAX      Counter32
    MAX-ACCESS  read-only
    STATUS      current
    DESCRIPTION
         "Bad subframe type count." 
    ::= { wifi-iface-stats 31 }

 wifiStatRxNoMbuf     OBJECT-TYPE
    SYNTAX      Counter32
    MAX-ACCESS  read-only
    STATUS      current
    DESCRIPTION
         "No Mbufs available to hold Rx frame." 
    ::= { wifi-iface-stats 32 }

 wifiStatRxDecryptCRC OBJECT-TYPE
    SYNTAX      Counter32
    MAX-ACCESS  read-only
    STATUS      current
    DESCRIPTION
         "Decryption CRC fail count." 
    ::= { wifi-iface-stats 33 }

 wifiStatRxAdhocDemo  OBJECT-TYPE
    SYNTAX      Counter32
    MAX-ACCESS  read-only
    STATUS      current
    DESCRIPTION
         "Count of Ad hoc demo frames." 
    ::= { wifi-iface-stats 34 }

 wifiStatRxBadAuth    OBJECT-TYPE
    SYNTAX      Counter32
    MAX-ACCESS  read-only
    STATUS      current
    DESCRIPTION
         "Count of bad authentication frames received." 
    ::= { wifi-iface-stats 35 }

 wifiStatRxBadRSNIE   OBJECT-TYPE
    SYNTAX      Counter32
    MAX-ACCESS  read-only
    STATUS      current
    DESCRIPTION
         "Count of frames with bad Robust Security Network
          information elements." 
    ::= { wifi-iface-stats 36 }

 wifiStatRxNoAuth     OBJECT-TYPE
    SYNTAX      Counter32
    MAX-ACCESS  read-only
    STATUS      current
    DESCRIPTION
         "Frame count for connections with no authentication." 
    ::= { wifi-iface-stats 37 }

 wifiStatRxEAPOLKey   OBJECT-TYPE
    SYNTAX      Counter32
    MAX-ACCESS  read-only
    STATUS      current
    DESCRIPTION
         "EAPOL key frame count." 
    ::= { wifi-iface-stats 38 }

 wifiStatRxEAPOLReplays OBJECT-TYPE
    SYNTAX      Counter32
    MAX-ACCESS  read-only
    STATUS      current
    DESCRIPTION
         "EAPOL replay count." 
    ::= { wifi-iface-stats 39 }

 wifiStatRxEAPOLBadMIC OBJECT-TYPE
    SYNTAX      Counter32
    MAX-ACCESS  read-only
    STATUS      current
    DESCRIPTION
         "Count of EAPOL frames with bad MIC." 
    ::= { wifi-iface-stats 40 }

 wifiStatRxRemMICFail OBJECT-TYPE
    SYNTAX      Counter32
    MAX-ACCESS  read-only
    STATUS      current
    DESCRIPTION
         "Remote MIC failures count." 
    ::= { wifi-iface-stats 41 }

 wifiStatRxLocMICFail OBJECT-TYPE
    SYNTAX      Counter32
    MAX-ACCESS  read-only
    STATUS      current
    DESCRIPTION
         "Local MIC fail count." 
    ::= { wifi-iface-stats 42 }

 wifiStatTxNoMbuf     OBJECT-TYPE
    SYNTAX      Counter32
    MAX-ACCESS  read-only
    STATUS      current
    DESCRIPTION
         "Tx failed due to no Mbuf resource." 
    ::= { wifi-iface-stats 43 }

 wifiStatTxNoNode     OBJECT-TYPE
    SYNTAX      Counter32
    MAX-ACCESS  read-only
    STATUS      current
    DESCRIPTION
         "Tx failed due to no node in table." 
    ::= { wifi-iface-stats 44 }

 wifiStatTxUnknownMgmt OBJECT-TYPE
    SYNTAX      Counter32
    MAX-ACCESS  read-only
    STATUS      current
    DESCRIPTION
         "Unknown management frame type." 
    ::= { wifi-iface-stats 45 }

 wifiStatTxNoAuth     OBJECT-TYPE
    SYNTAX      Counter32
    MAX-ACCESS  read-only
    STATUS      current
    DESCRIPTION
         "Transmit frame failed due to no authentication method." 
    ::= { wifi-iface-stats 46 }

 wifiStatActiveScans  OBJECT-TYPE
    SYNTAX      Counter32
    MAX-ACCESS  read-only
    STATUS      current
    DESCRIPTION
         "Number of active scans performed." 
    ::= { wifi-iface-stats 47 }

 wifiStatPassiveScans OBJECT-TYPE
    SYNTAX      Counter32
    MAX-ACCESS  read-only
    STATUS      current
    DESCRIPTION
         "Number of passive scans performed." 
    ::= { wifi-iface-stats 48 }

 wifiStatNodeTimeout  OBJECT-TYPE
    SYNTAX      Counter32
    MAX-ACCESS  read-only
    STATUS      current
    DESCRIPTION
         "Node timeout count." 
    ::= { wifi-iface-stats 49 }

 wifiStatCryptoNoMem  OBJECT-TYPE
    SYNTAX      Counter32
    MAX-ACCESS  read-only
    STATUS      current
    DESCRIPTION
         "No memory availble for encryption." 
    ::= { wifi-iface-stats 50 }

 wifiStatTKIPReplays  OBJECT-TYPE
    SYNTAX      Counter32
    MAX-ACCESS  read-only
    STATUS      current
    DESCRIPTION
         "Count of TKIP replays." 
    ::= { wifi-iface-stats 51 }

 wifiStatTKIPICVErrors OBJECT-TYPE
    SYNTAX      Counter32
    MAX-ACCESS  read-only
    STATUS      current
    DESCRIPTION
         "Count of TKIP ICV errors." 
    ::= { wifi-iface-stats 52 }

 wifiStatCCMPReplays  OBJECT-TYPE
    SYNTAX      Counter32
    MAX-ACCESS  read-only
    STATUS      current
    DESCRIPTION
         "Count of CCMP replays." 
    ::= { wifi-iface-stats 53 }

 wifiStatCCMPDecryptErrors OBJECT-TYPE
    SYNTAX      Counter32
    MAX-ACCESS  read-only
    STATUS      current
    DESCRIPTION
         "Count of CCMP decryption errors." 
    ::= { wifi-iface-stats 54 }

 wifiStatCMACReplays OBJECT-TYPE
    SYNTAX      Counter32
    MAX-ACCESS  read-only
    STATUS      current
    DESCRIPTION
         "Count of CMAC replays." 
    ::= { wifi-iface-stats 55 }

wifiStatCMACICVErrors OBJECT-TYPE
    SYNTAX      Counter32
    MAX-ACCESS  read-only
    STATUS      current
    DESCRIPTION
         "Number of CMAC ICV errors." 
    ::= { wifi-iface-stats 56 }

wifiStatPBACErrors OBJECT-TYPE
    SYNTAX      Counter32
    MAX-ACCESS  read-only
    STATUS      current
    DESCRIPTION
         "Count of PBAC errors." 
    ::= { wifi-iface-stats 57 }

wifiStatNodeClean OBJECT-TYPE
    SYNTAX      Counter32
    MAX-ACCESS  read-only
    STATUS      current
    DESCRIPTION
         "Cleaning Node."
    ::= { wifi-iface-stats 58 }


--
-- Wifi Client Connections Table
--
wifiClientConnTable   OBJECT-TYPE
    SYNTAX      SEQUENCE OF ClientConnEntry
    MAX-ACCESS  not-accessible
    STATUS      current
    DESCRIPTION
         "A list of entries containing information on all
         Wifi clients on this system."
    ::= { wifi-client-connections 1 }

wifiClientConnEntry   OBJECT-TYPE
    SYNTAX      ClientConnEntry
    MAX-ACCESS  not-accessible
    STATUS      current
    DESCRIPTION
         "An entry containing connection information for a particular
         Wifi client."
    INDEX { wifiClientConnModule, wifiClientConnNode }
    ::= { wifiClientConnTable 1 }

ClientConnEntry ::=
        SEQUENCE {
                wifiClientConnNode         MacAddress,
                wifiClientConnSSID         DisplayString,
                wifiClientConnRSSI         INTEGER,
                wifiClientConnFlags        DisplayString,
                wifiClientConnPowerSave    DisplayString,
                wifiClientConnNegRates     DisplayString,
                wifiClientConnCapability   DisplayString,
                wifiClientConnModule       INTEGER,
                wifiClientConnMode         DisplayString,
                wifiClientConnTxRate       DisplayString,
                wifiClientConnRxRate       DisplayString,
                wifiClientConnChannel      INTEGER
        }

wifiClientConnNode OBJECT-TYPE
    SYNTAX      MacAddress
    MAX-ACCESS  read-only
    STATUS      current
    DESCRIPTION
         "The MAC address of the Access Point that unit is connected to."
    ::= { wifiClientConnEntry 1 }

wifiClientConnSSID OBJECT-TYPE
    SYNTAX      DisplayString
    MAX-ACCESS  read-only
    STATUS      current
    DESCRIPTION
         "SSID of the Access Point that unit is connected to."
    ::= { wifiClientConnEntry 2 }

wifiClientConnRSSI OBJECT-TYPE
    SYNTAX      INTEGER
    MAX-ACCESS  read-only
    STATUS      current
    DESCRIPTION
         "The received signal strength indication."
    ::= { wifiClientConnEntry 3 }

wifiClientConnFlags OBJECT-TYPE
    SYNTAX      DisplayString
    MAX-ACCESS  read-only
    STATUS      current
    DESCRIPTION
         "A list of the flags set by the client eg. ERP if using
          extended rate protocol etc."
    ::= { wifiClientConnEntry 4 }

wifiClientConnPowerSave OBJECT-TYPE
    SYNTAX      DisplayString
    MAX-ACCESS  read-only
    STATUS      current
    DESCRIPTION
         "Power save status of client ie whether it is awake or
          asleep."
    ::= { wifiClientConnEntry 5 }

wifiClientConnNegRates OBJECT-TYPE
    SYNTAX      DisplayString
    MAX-ACCESS  read-only
    STATUS      current
    DESCRIPTION
         "A list of the negotiated data rates."
    ::= { wifiClientConnEntry 6 }

wifiClientConnCapability OBJECT-TYPE
    SYNTAX      DisplayString
    MAX-ACCESS  read-only
    STATUS      current
    DESCRIPTION
         "Capability information for the connected client.
         This includes such information as whether the
         client support short preambles, privacy etc."
    ::= { wifiClientConnEntry 7 }

wifiClientConnModule OBJECT-TYPE
    SYNTAX      INTEGER ( 0..1 )
    MAX-ACCESS  read-only
    STATUS      current
    DESCRIPTION
         "Wi-Fi module on which this connection is on."
    ::= { wifiClientConnEntry 8 }

wifiClientConnMode OBJECT-TYPE
    SYNTAX      DisplayString
    MAX-ACCESS  read-only
    STATUS      current
    DESCRIPTION
         "Connection mode."
    ::= { wifiClientConnEntry 9 }

wifiClientConnTxRate OBJECT-TYPE
    SYNTAX      DisplayString
    MAX-ACCESS  read-only
    STATUS      current
    DESCRIPTION
         "Transmit rate for this connection."
    ::= { wifiClientConnEntry 10 }

wifiClientConnRxRate OBJECT-TYPE
    SYNTAX      DisplayString
    MAX-ACCESS  read-only
    STATUS      current
    DESCRIPTION
         "Receive rate for this connection."
    ::= { wifiClientConnEntry 11 }

wifiClientConnChannel OBJECT-TYPE
    SYNTAX      INTEGER
    MAX-ACCESS  read-only
    STATUS      current
    DESCRIPTION
         "Channel for this connection."
    ::= { wifiClientConnEntry 12 }

--
-- Wifi Module Config Table
--
-- This replaces the deprecated wifi-config group.
--
wifiModuleTable   OBJECT-TYPE
    SYNTAX      SEQUENCE OF WifiModuleEntry
    MAX-ACCESS  not-accessible
    STATUS      current
    DESCRIPTION
         "A table containing configuration information on a per
          module basis."
    ::= { wifi-module-config 1 }

wifiModuleEntry   OBJECT-TYPE
    SYNTAX      WifiModuleEntry
    MAX-ACCESS  not-accessible
    STATUS      current
    DESCRIPTION
             "An entry containing configuration for a particular Wifi module."
    INDEX { wifiModuleIndex }
    ::= { wifiModuleTable 1 }

WifiModuleEntry ::=
    SEQUENCE{
    wifiModuleIndex     INTEGER,
    wifiModuleCountry   OCTET STRING,
    wifiModuleChannel   OCTET STRING,
    wifiModuleMACFilter INTEGER,
    wifiModuleAnalyzer  INTEGER,
    wifiModuleAnaMgmt   INTEGER,
    wifiModuleAnaData   INTEGER,
    wifiModuleNumNodes  INTEGER
    }

wifiModuleIndex   OBJECT-TYPE
    SYNTAX      INTEGER (0..1)
    MAX-ACCESS  read-write
    STATUS      current
    DESCRIPTION
         "Index into the module table"
    ::= { wifiModuleEntry 1 }

wifiModuleCountry     OBJECT-TYPE
    SYNTAX      OCTET STRING
    MAX-ACCESS  read-write
    STATUS      current
    DESCRIPTION
           "The country code for this module. All modules will report the same
            country code."
        ::= { wifiModuleEntry 2 }

wifiModuleChannel OBJECT-TYPE
    SYNTAX      OCTET STRING
    MAX-ACCESS  read-write
    STATUS      current
    DESCRIPTION
        "The channel number for this module."
    ::= { wifiModuleEntry 3 }

wifiModuleMACFilter  OBJECT-TYPE
    SYNTAX      INTEGER  { enabled (1), disabled (2) }
    MAX-ACCESS  read-write
    STATUS      current
    DESCRIPTION
        "MAC filtering functionality. This allows clients to
        be allowed or denied a connection to the host based
        on their MAC address."
    ::= { wifiModuleEntry 4 }

wifiModuleAnalyzer    OBJECT-TYPE
    SYNTAX      INTEGER
    MAX-ACCESS  read-write
    STATUS      current
    DESCRIPTION
        "Packet analyzer function. (on/off)"
    ::= { wifiModuleEntry 5 }

wifiModuleAnaMgmt     OBJECT-TYPE
    SYNTAX      INTEGER { none (1),
                      nobeacons (2),
                      all (3) }
    MAX-ACCESS  read-write
    STATUS      current
    DESCRIPTION
          "Which wifi management frames to capture/process/display."
    ::= { wifiModuleEntry 6 }

wifiModuleAnaData     OBJECT-TYPE
    SYNTAX      INTEGER {
                     none (1),
                     nonull (2),
                     all (3)
                    } 
    MAX-ACCESS  read-write
    STATUS      current
    DESCRIPTION
         "Which data packets to capture/process/dispay."
    ::= { wifiModuleEntry 7 }

wifiModuleNumNodes    OBJECT-TYPE
    SYNTAX      INTEGER ( 1..4 )
    MAX-ACCESS  read-only
    STATUS      current
    DESCRIPTION
         "The number of Wifi interfaces (Access Points/Clients)
         that the module supports."
    ::= { wifiModuleEntry 8 }



--
-- Wifi Module Stats Table
--
-- This replaces the deprecated wifi-stats group.
--

wifiModuleStatsTable   OBJECT-TYPE
    SYNTAX      SEQUENCE OF WifiModuleStatsEntry
    MAX-ACCESS  not-accessible
    STATUS      current
    DESCRIPTION
         "A table containing statistics on a per module basis."
    ::= { wifi-module-stats 1 }

wifiModuleStatsEntry   OBJECT-TYPE
    SYNTAX      WifiModuleStatsEntry
    MAX-ACCESS  not-accessible
    STATUS      current
    DESCRIPTION
         "An entry containing statistics for a particular Wifi module."
    INDEX { wifiModuleStatsIndex }
    ::= { wifiModuleStatsTable 1 }

WifiModuleStatsEntry ::=
    SEQUENCE{
    wifiModuleStatsIndex     INTEGER,
	wifiModuleAdminStatus    INTEGER,
	wifiModuleOperStatus     INTEGER,
	wifiModuleMACAddress     MacAddress,
	wifiModuleChannelUsed    INTEGER,
	wifiModuleRxPackets      Counter32,
	wifiModuleRxBytes        Counter32,
	wifiModuleRxDropped      Counter32,
	wifiModuleRxErrors       Counter32,
	wifiModuleTxPackets      Counter32,
	wifiModuleTxBytes        Counter32,
	wifiModuleTxErrors       Counter32
    }

wifiModuleStatsIndex   OBJECT-TYPE
    SYNTAX      INTEGER (0..1)
    MAX-ACCESS  read-write
    STATUS      current
    DESCRIPTION
         "Index into the module table"
    ::= { wifiModuleStatsEntry 1 }

wifiModuleAdminStatus  OBJECT-TYPE
    SYNTAX      INTEGER { up (1), down (2) } 
    MAX-ACCESS  read-only
    STATUS      current
    DESCRIPTION
         "The administrative status of the interface ie whether the
          interface is up or down."
    ::= { wifiModuleStatsEntry 2 }

wifiModuleOperStatus   OBJECT-TYPE
    SYNTAX      INTEGER { up (1), down (2) } 
    MAX-ACCESS  read-only
    STATUS      current
    DESCRIPTION
         "The operational status of the interface ie up/down."
    ::= { wifiModuleStatsEntry 3 }

wifiModuleMACAddress   OBJECT-TYPE
    SYNTAX      MacAddress
    MAX-ACCESS  read-only
    STATUS      current
    DESCRIPTION
         "The MAC address of the wifi module."
    ::= { wifiModuleStatsEntry 4 }

wifiModuleChannelUsed  OBJECT-TYPE
    SYNTAX      INTEGER
    MAX-ACCESS  read-only
    STATUS      current
    DESCRIPTION
         "The channel being used for the connection."
    ::= { wifiModuleStatsEntry 5 }

wifiModuleRxPackets   OBJECT-TYPE
    SYNTAX      Counter32
    MAX-ACCESS  read-only
    STATUS      current
    DESCRIPTION
         "The number of packets received."
    ::= { wifiModuleStatsEntry 6 }

wifiModuleRxBytes     OBJECT-TYPE
    SYNTAX      Counter32
    MAX-ACCESS  read-only
    STATUS      current
    DESCRIPTION
        "The number of bytes received."
    ::= { wifiModuleStatsEntry 7 }
                  
wifiModuleRxDropped   OBJECT-TYPE
    SYNTAX      Counter32
    MAX-ACCESS  read-only
    STATUS      current
    DESCRIPTION
        "The number of dropped frames."
    ::= { wifiModuleStatsEntry 8 }
                  
wifiModuleRxErrors    OBJECT-TYPE
    SYNTAX      Counter32
    MAX-ACCESS  read-only
    STATUS      current
    DESCRIPTION
        "The number of receive errors."
    ::= { wifiModuleStatsEntry 9 }
                  
wifiModuleTxPackets   OBJECT-TYPE
    SYNTAX      Counter32
    MAX-ACCESS  read-only
    STATUS      current
    DESCRIPTION
        "The number of packets transmitted."
    ::= { wifiModuleStatsEntry 10 }
                  
wifiModuleTxBytes     OBJECT-TYPE
    SYNTAX      Counter32
    MAX-ACCESS  read-only
    STATUS      current
    DESCRIPTION
        "The number of bytes transmitted."
    ::= { wifiModuleStatsEntry 11 }
                  
wifiModuleTxErrors    OBJECT-TYPE
    SYNTAX      Counter32
    MAX-ACCESS  read-only
    STATUS      current
    DESCRIPTION
        "The number of transmit errors."
    ::= { wifiModuleStatsEntry 12 }


--
-- Wifi Module Interface Stats Table
--
-- This replaces the deprecated wifi-iface-stats group.
--

wifiModuleInterfaceStatsTable   OBJECT-TYPE
    SYNTAX      SEQUENCE OF WifiModuleInterfaceStatsEntry
    MAX-ACCESS  not-accessible
    STATUS      current
    DESCRIPTION
         "A table containing interface statistics on a per module basis."
    ::= { wifi-module-iface-stats 1 }

wifiModuleInterfaceStatsEntry   OBJECT-TYPE
    SYNTAX      WifiModuleInterfaceStatsEntry
    MAX-ACCESS  not-accessible
    STATUS      current
    DESCRIPTION
             "An entry containing interface statistics for a particular Wifi module."
    INDEX { wifiInterfaceStatModuleIndex }
    ::= { wifiModuleInterfaceStatsTable 1 }

WifiModuleInterfaceStatsEntry ::=
    SEQUENCE{
	wifiInterfaceStatModuleIndex         INTEGER,
	wifiInterfaceStatRxBadVersion        Counter32,
	wifiInterfaceStatRxTooShort          Counter32,
	wifiInterfaceStatRxWrongBSS          Counter32,
	wifiInterfaceStatRxDuplicate         Counter32,
	wifiInterfaceStatRxWrongDir          Counter32,
	wifiInterfaceStatRxMcastEcho         Counter32,
	wifiInterfaceStatRxNotAssoc          Counter32,
	wifiInterfaceStatRxNoWEP             Counter32,
	wifiInterfaceStatRxUnencrypted       Counter32,
	wifiInterfaceStatRxWEPFail           Counter32,
	wifiInterfaceStatRxDecapFail         Counter32,
	wifiInterfaceStatRxMgmtDiscard       Counter32,
	wifiInterfaceStatRxCtrlDiscard       Counter32,
	wifiInterfaceStatRxRSTooBig          Counter32,
	wifiInterfaceStatRxElemMissing       Counter32,
	wifiInterfaceStatRxElemTooBig        Counter32,
	wifiInterfaceStatRxElemTooSmall      Counter32,
	wifiInterfaceStatRxElemUnknown       Counter32,
	wifiInterfaceStatRxBadChannel        Counter32,
	wifiInterfaceStatRxChanMismatch      Counter32,
	wifiInterfaceStatRxNodeAlloc         Counter32,
	wifiInterfaceStatRxSSIDMismatch      Counter32,
	wifiInterfaceStatRxAuthUnsupported   Counter32,
	wifiInterfaceStatRxAuthFailed        Counter32,
	wifiInterfaceStatRxAssocWrong        Counter32,
	wifiInterfaceStatRxAssocNotAuth      Counter32,
	wifiInterfaceStatRxAssocCapMismatch  Counter32,
	wifiInterfaceStatRxAssocNoRate       Counter32,
	wifiInterfaceStatRxDeauthenticate    Counter32,
	wifiInterfaceStatRxDeassociate       Counter32,
	wifiInterfaceStatRxBadSubtype        Counter32,
	wifiInterfaceStatRxNoMbuf            Counter32,
	wifiInterfaceStatRxDecryptCRC        Counter32,
	wifiInterfaceStatRxAdhocDemo         Counter32,
	wifiInterfaceStatRxBadAuth           Counter32,
	wifiInterfaceStatRxBadRSNIE          Counter32,
	wifiInterfaceStatRxNoAuth            Counter32,
	wifiInterfaceStatRxEAPOLKey          Counter32,
	wifiInterfaceStatRxEAPOLReplays      Counter32,
	wifiInterfaceStatRxEAPOLBadMIC       Counter32,
	wifiInterfaceStatRxRemMICFail        Counter32,
	wifiInterfaceStatRxLocMICFail        Counter32,
	wifiInterfaceStatTxNoMbuf            Counter32,
	wifiInterfaceStatTxNoNode            Counter32,
	wifiInterfaceStatTxUnknownMgmt       Counter32,
	wifiInterfaceStatTxNoAuth            Counter32,
	wifiInterfaceStatActiveScans         Counter32,
	wifiInterfaceStatPassiveScans        Counter32,
	wifiInterfaceStatNodeTimeout         Counter32,
	wifiInterfaceStatCryptoNoMem         Counter32,
	wifiInterfaceStatTKIPReplays         Counter32,
	wifiInterfaceStatTKIPICVErrors       Counter32,
	wifiInterfaceStatCCMPReplays         Counter32,
	wifiInterfaceStatCCMPDecryptErrors   Counter32,
	wifiInterfaceStatCMACReplays         Counter32,
	wifiInterfaceStatCMACICVErrors       Counter32,
	wifiInterfaceStatPBACErrors          Counter32,
	wifiInterfaceStatNodeClean           Counter32
	}

wifiInterfaceStatModuleIndex   OBJECT-TYPE
    SYNTAX      INTEGER (0..1)
    MAX-ACCESS  read-write
    STATUS      current
    DESCRIPTION
         "Index into the module table"
    ::= { wifiModuleInterfaceStatsEntry 1 }


wifiInterfaceStatRxBadVersion OBJECT-TYPE
    SYNTAX      Counter32
    MAX-ACCESS  read-only
    STATUS      current
    DESCRIPTION
         "Frame received with incorrect version number."
    ::= { wifiModuleInterfaceStatsEntry 2 }

wifiInterfaceStatRxTooShort   OBJECT-TYPE
    SYNTAX      Counter32
    MAX-ACCESS  read-only
    STATUS      current
    DESCRIPTION
         "Received frame too short."
    ::= { wifiModuleInterfaceStatsEntry 3 }

 wifiInterfaceStatRxWrongBSS   OBJECT-TYPE
    SYNTAX      Counter32
    MAX-ACCESS  read-only
    STATUS      current
    DESCRIPTION
         "Received frame has incorrect BSS."
    ::= { wifiModuleInterfaceStatsEntry 4 }

 wifiInterfaceStatRxDuplicate  OBJECT-TYPE
    SYNTAX      Counter32
    MAX-ACCESS  read-only
    STATUS      current
    DESCRIPTION
         "Duplicate frame received."
    ::= { wifiModuleInterfaceStatsEntry 5 }

 wifiInterfaceStatRxWrongDir   OBJECT-TYPE
    SYNTAX      Counter32
    MAX-ACCESS  read-only
    STATUS      current
    DESCRIPTION
         "Frame received with incorrect direction flag."
    ::= { wifiModuleInterfaceStatsEntry 6 }

 wifiInterfaceStatRxMcastEcho  OBJECT-TYPE
    SYNTAX      Counter32
    MAX-ACCESS  read-only
    STATUS      current
    DESCRIPTION
         "Multicast echo frame received."
    ::= { wifiModuleInterfaceStatsEntry 7 }

 wifiInterfaceStatRxNotAssoc   OBJECT-TYPE
    SYNTAX      Counter32
    MAX-ACCESS  read-only
    STATUS      current
    DESCRIPTION
         "Frame received from non-associated client."
    ::= { wifiModuleInterfaceStatsEntry 8 }

 wifiInterfaceStatRxNoWEP      OBJECT-TYPE
    SYNTAX      Counter32
    MAX-ACCESS  read-only
    STATUS      current
    DESCRIPTION
         "WEP frame expected but WEP flag not set."
    ::= { wifiModuleInterfaceStatsEntry 9 }

 wifiInterfaceStatRxUnencrypted OBJECT-TYPE
    SYNTAX      Counter32
    MAX-ACCESS  read-only
    STATUS      current
    DESCRIPTION
         "Unencrypted frame count."
    ::= { wifiModuleInterfaceStatsEntry 10 }

 wifiInterfaceStatRxWEPFail    OBJECT-TYPE
    SYNTAX      Counter32
    MAX-ACCESS  read-only
    STATUS      current
    DESCRIPTION
         "WEP fail count."
    ::= { wifiModuleInterfaceStatsEntry 11 }

 wifiInterfaceStatRxDecapFail  OBJECT-TYPE
    SYNTAX      Counter32
    MAX-ACCESS  read-only
    STATUS      current
    DESCRIPTION
         "Frame decapsulation fail count."
    ::= { wifiModuleInterfaceStatsEntry 12 }

 wifiInterfaceStatRxMgmtDiscard OBJECT-TYPE
    SYNTAX      Counter32
    MAX-ACCESS  read-only
    STATUS      current
    DESCRIPTION
         "Management frame discard count."
    ::= { wifiModuleInterfaceStatsEntry 13 }

 wifiInterfaceStatRxCtrlDiscard OBJECT-TYPE
    SYNTAX      Counter32
    MAX-ACCESS  read-only
    STATUS      current
    DESCRIPTION
         "Control frame discard count."
    ::= { wifiModuleInterfaceStatsEntry 14 }

 wifiInterfaceStatRxRSTooBig   OBJECT-TYPE
    SYNTAX      Counter32
    MAX-ACCESS  read-only
    STATUS      current
    DESCRIPTION
         "Rate set too big."
    ::= { wifiModuleInterfaceStatsEntry 15 }

wifiInterfaceStatRxElemMissing OBJECT-TYPE
    SYNTAX      Counter32
    MAX-ACCESS  read-only
    STATUS      current
    DESCRIPTION
        "Element missing from Rx frame." 
    ::= { wifiModuleInterfaceStatsEntry 16 }

 wifiInterfaceStatRxElemTooBig OBJECT-TYPE
    SYNTAX      Counter32
    MAX-ACCESS  read-only
    STATUS      current
    DESCRIPTION
         "Element field in frame too big." 
    ::= { wifiModuleInterfaceStatsEntry 17 }

 wifiInterfaceStatRxElemTooSmall OBJECT-TYPE
    SYNTAX      Counter32
    MAX-ACCESS  read-only
    STATUS      current
    DESCRIPTION
         "Element field in frame is too small." 
    ::= { wifiModuleInterfaceStatsEntry 18 }

 wifiInterfaceStatRxElemUnknown OBJECT-TYPE
    SYNTAX      Counter32
    MAX-ACCESS  read-only
    STATUS      current
    DESCRIPTION
         "Unknown element in Rx frame." 
    ::= { wifiModuleInterfaceStatsEntry 19 }

 wifiInterfaceStatRxBadChannel OBJECT-TYPE
    SYNTAX      Counter32
    MAX-ACCESS  read-only
    STATUS      current
    DESCRIPTION
         "Frame received with unexpected channel number." 
    ::= { wifiModuleInterfaceStatsEntry 20 }

 wifiInterfaceStatRxChanMismatch OBJECT-TYPE
    SYNTAX      Counter32
    MAX-ACCESS  read-only
    STATUS      current
    DESCRIPTION
         "Channel mismatch error count. This can happen
         due to channel leakage." 
    ::= { wifiModuleInterfaceStatsEntry 21 }

 wifiInterfaceStatRxNodeAlloc  OBJECT-TYPE
    SYNTAX      Counter32
    MAX-ACCESS  read-only
    STATUS      current
    DESCRIPTION
         "Node allocation count." 
    ::= { wifiModuleInterfaceStatsEntry 22 }

 wifiInterfaceStatRxSSIDMismatch OBJECT-TYPE
    SYNTAX      Counter32
    MAX-ACCESS  read-only
    STATUS      current
    DESCRIPTION
         "SSID mismatch." 
    ::= { wifiModuleInterfaceStatsEntry 23 }

 wifiInterfaceStatRxAuthUnsupported OBJECT-TYPE
    SYNTAX      Counter32
    MAX-ACCESS  read-only
    STATUS      current
    DESCRIPTION
         "We are doing encryption and received a frame for
         the wrong port number." 
    ::= { wifiModuleInterfaceStatsEntry 24 }

 wifiInterfaceStatRxAuthFailed  OBJECT-TYPE
    SYNTAX      Counter32
    MAX-ACCESS  read-only
    STATUS      current
    DESCRIPTION
         "Authentication failure count." 
    ::= { wifiModuleInterfaceStatsEntry 25 }

 wifiInterfaceStatRxAssocWrong OBJECT-TYPE
    SYNTAX      Counter32
    MAX-ACCESS  read-only
    STATUS      current
    DESCRIPTION
         "We received an association frame from a BSS
         we don't recognize." 
    ::= { wifiModuleInterfaceStatsEntry 26 }

 wifiInterfaceStatRxAssocNotAuth OBJECT-TYPE
    SYNTAX      Counter32
    MAX-ACCESS  read-only
    STATUS      current
    DESCRIPTION
         "Count of the number of times we denied an association
         request from an unauthenticated source." 
    ::= { wifiModuleInterfaceStatsEntry 27 }

 wifiInterfaceStatRxAssocCapMismatch OBJECT-TYPE
    SYNTAX      Counter32
    MAX-ACCESS  read-only
    STATUS      current
    DESCRIPTION
         "Association capabilities mismatch count." 
    ::= { wifiModuleInterfaceStatsEntry 28 }

 wifiInterfaceStatRxAssocNoRate OBJECT-TYPE
    SYNTAX      Counter32
    MAX-ACCESS  read-only
    STATUS      current
    DESCRIPTION
         "Association frame with no rate set." 
    ::= { wifiModuleInterfaceStatsEntry 29 }

 wifiInterfaceStatRxDeauthenticate OBJECT-TYPE
    SYNTAX      Counter32
    MAX-ACCESS  read-only
    STATUS      current
    DESCRIPTION
         "Deauthentication frame count." 
    ::= { wifiModuleInterfaceStatsEntry 30 }

 wifiInterfaceStatRxDeassociate OBJECT-TYPE
    SYNTAX      Counter32
    MAX-ACCESS  read-only
    STATUS      current
    DESCRIPTION
         "Deassociation frame count." 
    ::= { wifiModuleInterfaceStatsEntry 31 }

 wifiInterfaceStatRxBadSubtype OBJECT-TYPE
    SYNTAX      Counter32
    MAX-ACCESS  read-only
    STATUS      current
    DESCRIPTION
         "Bad subframe type count." 
    ::= { wifiModuleInterfaceStatsEntry 32 }

 wifiInterfaceStatRxNoMbuf     OBJECT-TYPE
    SYNTAX      Counter32
    MAX-ACCESS  read-only
    STATUS      current
    DESCRIPTION
         "No Mbufs available to hold Rx frame." 
    ::= { wifiModuleInterfaceStatsEntry 33 }

 wifiInterfaceStatRxDecryptCRC OBJECT-TYPE
    SYNTAX      Counter32
    MAX-ACCESS  read-only
    STATUS      current
    DESCRIPTION
         "Decryption CRC fail count." 
    ::= { wifiModuleInterfaceStatsEntry 34 }

 wifiInterfaceStatRxAdhocDemo  OBJECT-TYPE
    SYNTAX      Counter32
    MAX-ACCESS  read-only
    STATUS      current
    DESCRIPTION
         "Count of Ad hoc demo frames." 
    ::= { wifiModuleInterfaceStatsEntry 35 }

 wifiInterfaceStatRxBadAuth    OBJECT-TYPE
    SYNTAX      Counter32
    MAX-ACCESS  read-only
    STATUS      current
    DESCRIPTION
         "Count of bad authentication frames received." 
    ::= { wifiModuleInterfaceStatsEntry 36 }

 wifiInterfaceStatRxBadRSNIE   OBJECT-TYPE
    SYNTAX      Counter32
    MAX-ACCESS  read-only
    STATUS      current
    DESCRIPTION
         "Count of frames with bad Robust Security Network
          information elements." 
    ::= { wifiModuleInterfaceStatsEntry 37 }

 wifiInterfaceStatRxNoAuth     OBJECT-TYPE
    SYNTAX      Counter32
    MAX-ACCESS  read-only
    STATUS      current
    DESCRIPTION
         "Frame count for connections with no authentication." 
    ::= { wifiModuleInterfaceStatsEntry 38 }

 wifiInterfaceStatRxEAPOLKey   OBJECT-TYPE
    SYNTAX      Counter32
    MAX-ACCESS  read-only
    STATUS      current
    DESCRIPTION
         "EAPOL key frame count." 
    ::= { wifiModuleInterfaceStatsEntry 39 }

 wifiInterfaceStatRxEAPOLReplays OBJECT-TYPE
    SYNTAX      Counter32
    MAX-ACCESS  read-only
    STATUS      current
    DESCRIPTION
         "EAPOL replay count." 
    ::= { wifiModuleInterfaceStatsEntry 40 }

 wifiInterfaceStatRxEAPOLBadMIC OBJECT-TYPE
    SYNTAX      Counter32
    MAX-ACCESS  read-only
    STATUS      current
    DESCRIPTION
         "Count of EAPOL frames with bad MIC." 
    ::= { wifiModuleInterfaceStatsEntry 41 }

 wifiInterfaceStatRxRemMICFail OBJECT-TYPE
    SYNTAX      Counter32
    MAX-ACCESS  read-only
    STATUS      current
    DESCRIPTION
         "Remote MIC failures count." 
    ::= { wifiModuleInterfaceStatsEntry 42 }

 wifiInterfaceStatRxLocMICFail OBJECT-TYPE
    SYNTAX      Counter32
    MAX-ACCESS  read-only
    STATUS      current
    DESCRIPTION
         "Local MIC fail count." 
    ::= { wifiModuleInterfaceStatsEntry 43 }

 wifiInterfaceStatTxNoMbuf     OBJECT-TYPE
    SYNTAX      Counter32
    MAX-ACCESS  read-only
    STATUS      current
    DESCRIPTION
         "Tx failed due to no Mbuf resource." 
    ::= { wifiModuleInterfaceStatsEntry 44 }

 wifiInterfaceStatTxNoNode     OBJECT-TYPE
    SYNTAX      Counter32
    MAX-ACCESS  read-only
    STATUS      current
    DESCRIPTION
         "Tx failed due to no node in table." 
    ::= { wifiModuleInterfaceStatsEntry 45 }

 wifiInterfaceStatTxUnknownMgmt OBJECT-TYPE
    SYNTAX      Counter32
    MAX-ACCESS  read-only
    STATUS      current
    DESCRIPTION
         "Unknown management frame type." 
    ::= { wifiModuleInterfaceStatsEntry 46 }

 wifiInterfaceStatTxNoAuth     OBJECT-TYPE
    SYNTAX      Counter32
    MAX-ACCESS  read-only
    STATUS      current
    DESCRIPTION
         "Transmit frame failed due to no authentication method." 
    ::= { wifiModuleInterfaceStatsEntry 47 }

 wifiInterfaceStatActiveScans  OBJECT-TYPE
    SYNTAX      Counter32
    MAX-ACCESS  read-only
    STATUS      current
    DESCRIPTION
         "Number of active scans performed." 
    ::= { wifiModuleInterfaceStatsEntry 48 }

 wifiInterfaceStatPassiveScans OBJECT-TYPE
    SYNTAX      Counter32
    MAX-ACCESS  read-only
    STATUS      current
    DESCRIPTION
         "Number of passive scans performed." 
    ::= { wifiModuleInterfaceStatsEntry 49 }

 wifiInterfaceStatNodeTimeout  OBJECT-TYPE
    SYNTAX      Counter32
    MAX-ACCESS  read-only
    STATUS      current
    DESCRIPTION
         "Node timeout count." 
    ::= { wifiModuleInterfaceStatsEntry 50 }

 wifiInterfaceStatCryptoNoMem  OBJECT-TYPE
    SYNTAX      Counter32
    MAX-ACCESS  read-only
    STATUS      current
    DESCRIPTION
         "No memory availble for encryption." 
    ::= { wifiModuleInterfaceStatsEntry 51 }

 wifiInterfaceStatTKIPReplays  OBJECT-TYPE
    SYNTAX      Counter32
    MAX-ACCESS  read-only
    STATUS      current
    DESCRIPTION
         "Count of TKIP replays." 
    ::= { wifiModuleInterfaceStatsEntry 52 }

 wifiInterfaceStatTKIPICVErrors OBJECT-TYPE
    SYNTAX      Counter32
    MAX-ACCESS  read-only
    STATUS      current
    DESCRIPTION
         "Count of TKIP ICV errors." 
    ::= { wifiModuleInterfaceStatsEntry 53 }

 wifiInterfaceStatCCMPReplays  OBJECT-TYPE
    SYNTAX      Counter32
    MAX-ACCESS  read-only
    STATUS      current
    DESCRIPTION
         "Count of CCMP replays." 
    ::= { wifiModuleInterfaceStatsEntry 54 }

 wifiInterfaceStatCCMPDecryptErrors OBJECT-TYPE
    SYNTAX      Counter32
    MAX-ACCESS  read-only
    STATUS      current
    DESCRIPTION
         "Count of CCMP decryption errors." 
    ::= { wifiModuleInterfaceStatsEntry 55 }

 wifiInterfaceStatCMACReplays OBJECT-TYPE
    SYNTAX      Counter32
    MAX-ACCESS  read-only
    STATUS      current
    DESCRIPTION
         "Count of CMAC replays." 
    ::= { wifiModuleInterfaceStatsEntry 56 }

wifiInterfaceStatCMACICVErrors OBJECT-TYPE
    SYNTAX      Counter32
    MAX-ACCESS  read-only
    STATUS      current
    DESCRIPTION
         "Number of CMAC ICV errors." 
    ::= { wifiModuleInterfaceStatsEntry 57 }

wifiInterfaceStatPBACErrors OBJECT-TYPE
    SYNTAX      Counter32
    MAX-ACCESS  read-only
    STATUS      current
    DESCRIPTION
         "Count of PBAC errors." 
    ::= { wifiModuleInterfaceStatsEntry 58 }

wifiInterfaceStatNodeClean OBJECT-TYPE
    SYNTAX      Counter32
    MAX-ACCESS  read-only
    STATUS      current
    DESCRIPTION
         "Cleaning Node."
    ::= { wifiModuleInterfaceStatsEntry 59 }


END
