DIGI-TRANSPORT-APVC-MIB DEFINITIONS ::= BEGIN
--
-- Copyright (c) 2014 Digi International Inc. All rights reserved.
--
-- Digi Transport APVC MIB
--
-- 25 May 2016 Created
--

IMPORTS
    enterprises                                 FROM RFC1155-SMI
    MODULE-IDENTITY, OBJECT-TYPE, Integer32,
    Unsigned32, Counter32, Counter64, IpAddress FROM SNMPv2-SMI
    DisplayString, MacAddress, TruthValue       FROM SNMPv2-TC;

digiApvcMIB MODULE-IDENTITY
	LAST-UPDATED "201605250000Z"	-- 25 May 2016
	ORGANIZATION
		"Digi International, Inc."
	CONTACT-INFO
		"Digi International Tech Support

		 Phone: 877 912 3444     (US and Canada)
		 		+1 952 912 3456  (Worldwide)
		 Email: <Tech.Support@digi.com>"
	DESCRIPTION
		"The Digi APVC MIB for managing the APVC configuration on the 
		 Digi TransPort product range."
	::= { sarian 10003 }


sarian           OBJECT IDENTIFIER ::= { enterprises 16378 }
sarian-apvc      OBJECT IDENTIFIER ::= { sarian 10003 }
apvc-config      OBJECT IDENTIFIER ::= { sarian-apvc 1 }

--
-- APVC Config Table
--
apvcTable   OBJECT-TYPE
    SYNTAX      SEQUENCE OF ApvcEntry
    MAX-ACCESS  not-accessible
    STATUS      current
    DESCRIPTION
         "A table containing configuration information on a per
          APVC basis."
    ::= { apvc-config 1 }

apvcEntry   OBJECT-TYPE
    SYNTAX      ApvcEntry
    MAX-ACCESS  not-accessible
    STATUS      current
    DESCRIPTION
             "An entry containing configuration for a particular apvc."
    INDEX { apvcIndex }
    ::= { apvcTable 1 }

ApvcEntry ::=
    SEQUENCE{
    apvcIndex     INTEGER,
	apvcEnabled INTEGER,
	apvcEncapsulation OCTET_STRING,
	apvcBridge INTEGER,
	apvcVPI INTEGER,
	apvcVCI INTEGER,
	apvcOamManage INTEGER,
	apvcServiceCategory OCTET_STRING,
	apvcPCR INTEGER,
	apvcSCR INTEGER,
	apvcMBS INTEGER,
	apvcCDVT INTEGER,
	apvcATMAnalysis INTEGER
    }

apvcIndex   OBJECT-TYPE
    SYNTAX      INTEGER
    MAX-ACCESS  read-only
    STATUS      current
    DESCRIPTION
         "Index into the APVC table"
    ::= { apvcEntry 1 }

apvcEnabled   OBJECT-TYPE
    SYNTAX      INTEGER { off (0), on (1) }
    MAX-ACCESS  read-only
    STATUS      current
    DESCRIPTION
         "Enable"
    ::= { apvcEntry 2 }

apvcEncapsulation     OBJECT-TYPE
    SYNTAX      OCTET STRING
    MAX-ACCESS  read-only
    STATUS      current
    DESCRIPTION
           "Encapsulation"
        ::= { apvcEntry 3 }

apvcBridge   OBJECT-TYPE
    SYNTAX      INTEGER { off (0), on (1) }
    MAX-ACCESS  read-only
    STATUS      current
    DESCRIPTION
         "Connect to the bridge"
    ::= { apvcEntry 4 }

apvcVPI   OBJECT-TYPE
    SYNTAX      INTEGER
    MAX-ACCESS  read-only
    STATUS      current
    DESCRIPTION
         "VPI"
    ::= { apvcEntry 5 }

apvcVCI   OBJECT-TYPE
    SYNTAX      INTEGER
    MAX-ACCESS  read-only
    STATUS      current
    DESCRIPTION
         "VCI"
    ::= { apvcEntry 6 }

apvcOamManage   OBJECT-TYPE
    SYNTAX      INTEGER { off (0), on (1) }
    MAX-ACCESS  read-only
    STATUS      current
    DESCRIPTION
         "OAM Management"
    ::= { apvcEntry 7 }

apvcServiceCategory     OBJECT-TYPE
    SYNTAX      OCTET STRING
    MAX-ACCESS  read-only
    STATUS      current
    DESCRIPTION
           "Service Category"
        ::= { apvcEntry 8 }

apvcPCR   OBJECT-TYPE
    SYNTAX      INTEGER
    MAX-ACCESS  read-only
    STATUS      current
    DESCRIPTION
         "PCR"
    ::= { apvcEntry 9 }

apvcSCR   OBJECT-TYPE
    SYNTAX      INTEGER
    MAX-ACCESS  read-only
    STATUS      current
    DESCRIPTION
         "SCR"
    ::= { apvcEntry 10 }

apvcMBS   OBJECT-TYPE
    SYNTAX      INTEGER
    MAX-ACCESS  read-only
    STATUS      current
    DESCRIPTION
         "MBS"
    ::= { apvcEntry 11 }

apvcCDVT   OBJECT-TYPE
    SYNTAX      INTEGER
    MAX-ACCESS  read-only
    STATUS      current
    DESCRIPTION
         "MBS"
    ::= { apvcEntry 12 }

apvcATMAnalysis   OBJECT-TYPE
    SYNTAX      INTEGER { off (0), on (1) }
    MAX-ACCESS  read-only
    STATUS      current
    DESCRIPTION
         "ATM Analysis"
    ::= { apvcEntry 13 }


END
