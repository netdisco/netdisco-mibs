DIGI-TRANSPORT-ETHERNET-MIB DEFINITIONS ::= BEGIN
--
-- Copyright (c) 2014 Digi International Inc. All rights reserved.
--
-- Digi Transport Ethernet MIB
--
-- 25 May 2016 Created
--

IMPORTS
    enterprises                                 FROM RFC1155-SMI
    MODULE-IDENTITY, OBJECT-TYPE, Integer32,
    Unsigned32, Counter32, Counter64, IpAddress FROM SNMPv2-SMI
    DisplayString, MacAddress, TruthValue       FROM SNMPv2-TC;

digiEthMIB MODULE-IDENTITY
	LAST-UPDATED "201605250000Z"	-- 25 May 2016
	ORGANIZATION
		"Digi International, Inc."
	CONTACT-INFO
		"Digi International Tech Support

		 Phone: 877 912 3444     (US and Canada)
		 		+1 952 912 3456  (Worldwide)
		 Email: <Tech.Support@digi.com>"
	DESCRIPTION
		"The Digi Ethernet MIB for managing the Ethernet statistics on the 
		 Digi TransPort product range."
	::= { sarian 10004 }


sarian         OBJECT IDENTIFIER ::= { enterprises 16378 }
sarian-eth     OBJECT IDENTIFIER ::= { sarian 10004 }
eth-stats      OBJECT IDENTIFIER ::= { sarian-eth 1 }

--
-- Eth Table
--
ethTable   OBJECT-TYPE
    SYNTAX      SEQUENCE OF EthEntry
    MAX-ACCESS  not-accessible
    STATUS      current
    DESCRIPTION
         "A table containing statistics information on a per
          Ethernet interface basis."
    ::= { eth-stats 1 }

ethEntry   OBJECT-TYPE
    SYNTAX      EthEntry
    MAX-ACCESS  not-accessible
    STATUS      current
    DESCRIPTION
             "An entry containing statistics for a particular Ethernet interface."
    INDEX { ethIndex }
    ::= { ethTable 1 }

EthEntry ::=
    SEQUENCE{
    ethIndex     INTEGER,
    }

ethIndex   OBJECT-TYPE
    SYNTAX      INTEGER
    MAX-ACCESS  read-only
    STATUS      current
    DESCRIPTION
         "Index into the ETH table"
    ::= { ethEntry 1 }

ethTxBytes   OBJECT-TYPE
	SYNTAX      Counter32
	MAX-ACCESS  read-only
	STATUS      current
	DESCRIPTION
		"The number of bytes transmitted."
	::= { ethEntry 2 }

ethRxBytes   OBJECT-TYPE
	SYNTAX      Counter32
	MAX-ACCESS  read-only
	STATUS      current
	DESCRIPTION
		"The number of bytes received."
	::= { ethEntry 3 }

ethTxPackets   OBJECT-TYPE
	SYNTAX      Counter32
	MAX-ACCESS  read-only
	STATUS      current
	DESCRIPTION
		"The number of packets transmitted."
	::= { ethEntry 4 }

ethTxUnicastPackets   OBJECT-TYPE
	SYNTAX      Counter32
	MAX-ACCESS  read-only
	STATUS      current
	DESCRIPTION
		"The number of unicast packets transmitted."
	::= { ethEntry 5 }

ethTxNonUnicastPackets   OBJECT-TYPE
	SYNTAX      Counter32
	MAX-ACCESS  read-only
	STATUS      current
	DESCRIPTION
		"The number of non-unicast packets transmitted."
	::= { ethEntry 6 }

ethRxPackets   OBJECT-TYPE
	SYNTAX      Counter32
	MAX-ACCESS  read-only
	STATUS      current
	DESCRIPTION
		"The number of packets received."
	::= { ethEntry 7 }

ethRxUnicastPackets   OBJECT-TYPE
	SYNTAX      Counter32
	MAX-ACCESS  read-only
	STATUS      current
	DESCRIPTION
		"The number of unicast packets received."
	::= { ethEntry 8 }

ethRxNonUnicastPackets   OBJECT-TYPE
	SYNTAX      Counter32
	MAX-ACCESS  read-only
	STATUS      current
	DESCRIPTION
		"The number of non-unicast packets received."
	::= { ethEntry 9 }

ethRxUnknownPackets   OBJECT-TYPE
	SYNTAX      Counter32
	MAX-ACCESS  read-only
	STATUS      current
	DESCRIPTION
		"The number of unknown packets received."
	::= { ethEntry 10 }

ethBcdDrop   OBJECT-TYPE
	SYNTAX      Counter32
	MAX-ACCESS  read-only
	STATUS      current
	DESCRIPTION
		"The number of BCD drops."
	::= { ethEntry 11 }

ethTxDrop   OBJECT-TYPE
	SYNTAX      Counter32
	MAX-ACCESS  read-only
	STATUS      current
	DESCRIPTION
		"The number of TX packets dropped."
	::= { ethEntry 12 }

ethCollisions   OBJECT-TYPE
	SYNTAX      Counter32
	MAX-ACCESS  read-only
	STATUS      current
	DESCRIPTION
		"The number of collisions."
	::= { ethEntry 13 }

ethRxOverruns   OBJECT-TYPE
	SYNTAX      Counter32
	MAX-ACCESS  read-only
	STATUS      current
	DESCRIPTION
		"The number of RX overruns."
	::= { ethEntry 14 }

ethOver   OBJECT-TYPE
	SYNTAX      Counter32
	MAX-ACCESS  read-only
	STATUS      current
	DESCRIPTION
		"Over."
	::= { ethEntry 15 }

ethAlignError   OBJECT-TYPE
	SYNTAX      Counter32
	MAX-ACCESS  read-only
	STATUS      current
	DESCRIPTION
		"Alignment errors."
	::= { ethEntry 16 }

ethCrcError   OBJECT-TYPE
	SYNTAX      Counter32
	MAX-ACCESS  read-only
	STATUS      current
	DESCRIPTION
		"CRC errors."
	::= { ethEntry 17 }

ethLongError   OBJECT-TYPE
	SYNTAX      Counter32
	MAX-ACCESS  read-only
	STATUS      current
	DESCRIPTION
		"Long packet errors."
	::= { ethEntry 18 }

ethRxParityError   OBJECT-TYPE
	SYNTAX      Counter32
	MAX-ACCESS  read-only
	STATUS      current
	DESCRIPTION
		"Receive parity errors."
	::= { ethEntry 19 }

ethTxDeffered   OBJECT-TYPE
	SYNTAX      Counter32
	MAX-ACCESS  read-only
	STATUS      current
	DESCRIPTION
		"The number of deferred transmits."
	::= { ethEntry 20 }

ethNoCarrier   OBJECT-TYPE
	SYNTAX      Counter32
	MAX-ACCESS  read-only
	STATUS      current
	DESCRIPTION
		"Carrier errors."
	::= { ethEntry 21 }

ethlateCollisions   OBJECT-TYPE
	SYNTAX      Counter32
	MAX-ACCESS  read-only
	STATUS      current
	DESCRIPTION
		"Late collisions."
	::= { ethEntry 22 }

ethTxParityError   OBJECT-TYPE
	SYNTAX      Counter32
	MAX-ACCESS  read-only
	STATUS      current
	DESCRIPTION
		"Transmit parity errors."
	::= { ethEntry 23 }

ethRxBufferShortage   OBJECT-TYPE
	SYNTAX      Counter32
	MAX-ACCESS  read-only
	STATUS      current
	DESCRIPTION
		"The number of receive buffer shortages."
	::= { ethEntry 24 }

ethOtherErrors   OBJECT-TYPE
	SYNTAX      Counter32
	MAX-ACCESS  read-only
	STATUS      current
	DESCRIPTION
		"Other errors."
	::= { ethEntry 25 }

ethFloodProtection   OBJECT-TYPE
	SYNTAX      Counter32
	MAX-ACCESS  read-only
	STATUS      current
	DESCRIPTION
		"The number of times flood protection has occurred."
	::= { ethEntry 26 }

ethHalted   OBJECT-TYPE
	SYNTAX      Counter32
	MAX-ACCESS  read-only
	STATUS      current
	DESCRIPTION
		"Halted."
	::= { ethEntry 27 }

ethUnder   OBJECT-TYPE
	SYNTAX      Counter32
	MAX-ACCESS  read-only
	STATUS      current
	DESCRIPTION
		"Underruns."
	::= { ethEntry 28 }

ethDefer   OBJECT-TYPE
	SYNTAX      Counter32
	MAX-ACCESS  read-only
	STATUS      current
	DESCRIPTION
		"Defers."
	::= { ethEntry 29 }

ethMissedError   OBJECT-TYPE
	SYNTAX      Counter32
	MAX-ACCESS  read-only
	STATUS      current
	DESCRIPTION
		"Missed errors."
	::= { ethEntry 30 }

ethMaxRxQueueLength   OBJECT-TYPE
	SYNTAX      Counter32
	MAX-ACCESS  read-only
	STATUS      current
	DESCRIPTION
		"Maximum receive queue length."
	::= { ethEntry 31 }

ethUnknownMac   OBJECT-TYPE
	SYNTAX      Counter32
	MAX-ACCESS  read-only
	STATUS      current
	DESCRIPTION
		"Unknown MAC addresses."
	::= { ethEntry 32 }

ethTxDropVrrpBackup   OBJECT-TYPE
	SYNTAX      Counter32
	MAX-ACCESS  read-only
	STATUS      current
	DESCRIPTION
		"Transmit packets dropped in VRRP backup mode."
	::= { ethEntry 33 }


END
