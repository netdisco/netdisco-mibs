SARIAN-EVENT-MIB DEFINITIONS ::= BEGIN

IMPORTS
   enterprises, MODULE-IDENTITY, NOTIFICATION-TYPE, 
   OBJECT-TYPE   										FROM SNMPv2-SMI;

   sarian-events MODULE-IDENTITY
   LAST-UPDATED		"201511230000Z"
   ORGANIZATION		
   			"Digi International Inc."
   CONTACT-INFO
			"Digi International Tech Support

			Phone: 	877 912 3444					(US and Canada)
					+1 952 912 3456					(Worldwide)
			Email:	Tech.Support@digi.com"

   DESCRIPTION
   			"SNMPv2 traps MIB for TransPort WR platforms"

   REVISION		"201511230000Z"
   DESCRIPTION  "Updated for SNMPv2"

   ::= { sarian 11002 }
			
   sarian                  OBJECT IDENTIFIER ::= { enterprises 16378 }
   event                   OBJECT IDENTIFIER ::= { sarian 16 }
   description             OBJECT IDENTIFIER ::= { sarian 17 }


ePowerup NOTIFICATION-TYPE
	STATUS current
	DESCRIPTION
	    "Power up."
	::= { event 1 }

eClearEvent NOTIFICATION-TYPE
	STATUS current
	DESCRIPTION
	    "The event log has been cleared."
	::= { event 2 }

eReboot NOTIFICATION-TYPE
	STATUS current
	DESCRIPTION
	    "Reboot."
	::= { event 3 }

eEntityUp NOTIFICATION-TYPE
	STATUS current
	DESCRIPTION
	    "Entity up."
	::= { event 4 }

eEntityDown NOTIFICATION-TYPE
	STATUS current
	DESCRIPTION
	    "Entity down."
	::= { event 5 }

eSendMessageFail NOTIFICATION-TYPE
	STATUS current
	DESCRIPTION
	    "Sendmessage() failure."
	::= { event 6 }

eLoginOK NOTIFICATION-TYPE
	STATUS current
	DESCRIPTION
	    "Login success."
	::= { event 7 }

eLoginFail NOTIFICATION-TYPE
	STATUS current
	DESCRIPTION
	    "Login failure."
	::= { event 8 }

eClockSet NOTIFICATION-TYPE
	STATUS current
	DESCRIPTION
	    "Clock set."
	::= { event 9 }

eUsernameChange NOTIFICATION-TYPE
	STATUS current
	DESCRIPTION
	    "Username Changed."
	::= { event 10 }

ePasswordChange NOTIFICATION-TYPE
	STATUS current
	DESCRIPTION
	    "Password changed."
	::= { event 11 }

eHostnameChange NOTIFICATION-TYPE
	STATUS current
	DESCRIPTION
	    "Hostname changed."
	::= { event 12 }

eWebRestart NOTIFICATION-TYPE
	STATUS current
	DESCRIPTION
	    "WEB server restarted."
	::= { event 13 }

eProtocolStart NOTIFICATION-TYPE
	STATUS current
	DESCRIPTION
	    "Protocol negotiation starting."
	::= { event 14 }

eAsyncSync NOTIFICATION-TYPE
	STATUS current
	DESCRIPTION
	    "Async->Sync PPP starting."
	::= { event 15 }

eLogHeld NOTIFICATION-TYPE
	STATUS current
	DESCRIPTION
	    "Logging held events."
	::= { event 16 }

eSMTPReq NOTIFICATION-TYPE
	STATUS current
	DESCRIPTION
	    "SMTP request."
	::= { event 17 }

eSMTPSuccess NOTIFICATION-TYPE
	STATUS current
	DESCRIPTION
	    "SMTP success."
	::= { event 18 }

eSMTPRej NOTIFICATION-TYPE
	STATUS current
	DESCRIPTION
	    "SMTP request rejected."
	::= { event 19 }

eSMTPErr NOTIFICATION-TYPE
	STATUS current
	DESCRIPTION
	    "SMTP error."
	::= { event 20 }

eTelnetClose NOTIFICATION-TYPE
	STATUS current
	DESCRIPTION
	    "TELNET session closed."
	::= { event 21 }

eNewLogcodes NOTIFICATION-TYPE
	STATUS current
	DESCRIPTION
	    "New logcodes file."
	::= { event 22 }

eRemCfg NOTIFICATION-TYPE
	STATUS current
	DESCRIPTION
	    "Remote config request received."
	::= { event 23 }

eAnonFTP NOTIFICATION-TYPE
	STATUS current
	DESCRIPTION
	    "Anonymous FTP started."
	::= { event 24 }

eFTPClose NOTIFICATION-TYPE
	STATUS current
	DESCRIPTION
	    "FTP session closed."
	::= { event 25 }

eX25CallReq NOTIFICATION-TYPE
	STATUS current
	DESCRIPTION
	    "X.25 call request."
	::= { event 26 }

eX25ConnIn NOTIFICATION-TYPE
	STATUS current
	DESCRIPTION
	    "X.25 connection made."
	::= { event 27 }

eX25CallClear NOTIFICATION-TYPE
	STATUS current
	DESCRIPTION
	    "X.25 call cleared."
	::= { event 28 }

eX25ClearReq NOTIFICATION-TYPE
	STATUS current
	DESCRIPTION
	    "X.25 call clear request."
	::= { event 29 }

eX25CallIn NOTIFICATION-TYPE
	STATUS current
	DESCRIPTION
	    "Incoming X.25 call."
	::= { event 30 }

eBChanUp NOTIFICATION-TYPE
	STATUS current
	DESCRIPTION
	    "B channel up."
	::= { event 31 }

eLAPDCallReq NOTIFICATION-TYPE
	STATUS current
	DESCRIPTION
	    "LAPD call request."
	::= { event 32 }

eBChanDown NOTIFICATION-TYPE
	STATUS current
	DESCRIPTION
	    "B channel down."
	::= { event 33 }

eCallClearReq NOTIFICATION-TYPE
	STATUS current
	DESCRIPTION
	    "Call clear request."
	::= { event 34 }

eCallClear NOTIFICATION-TYPE
	STATUS current
	DESCRIPTION
	    "Clearing Call."
	::= { event 36 }

eCallIn NOTIFICATION-TYPE
	STATUS current
	DESCRIPTION
	    "Incoming call."
	::= { event 38 }

eX25BackupCall NOTIFICATION-TYPE
	STATUS current
	DESCRIPTION
	    "Backup X.25 call."
	::= { event 39 }

eWatchdog NOTIFICATION-TYPE
	STATUS current
	DESCRIPTION
	    "Watchdog occurred."
	::= { event 40 }

eCmdErr NOTIFICATION-TYPE
	STATUS current
	DESCRIPTION
	    "Command line error."
	::= { event 41 }

eV120Disconnect NOTIFICATION-TYPE
	STATUS current
	DESCRIPTION
	    "V120 disconnected."
	::= { event 42 }

eLAPBInact NOTIFICATION-TYPE
	STATUS current
	DESCRIPTION
	    "LAPB Inactivity."
	::= { event 43 }

eBIOSBufs NOTIFICATION-TYPE
	STATUS current
	DESCRIPTION
	    "BIOS Buffers warning."
	::= { event 44 }

eActReq NOTIFICATION-TYPE
	STATUS current
	DESCRIPTION
	    "Activation Request."
	::= { event 45 }

eDNSQuery NOTIFICATION-TYPE
	STATUS current
	DESCRIPTION
	    "DNS query activation."
	::= { event 46 }

eDatTriggerMatch NOTIFICATION-TYPE
	STATUS current
	DESCRIPTION
	    "Data trigger match."
	::= { event 47 }

eASYTxWatchdog NOTIFICATION-TYPE
	STATUS current
	DESCRIPTION
	    "ASY transmit watchdog."
	::= { event 48 }

eTestEmail NOTIFICATION-TYPE
	STATUS current
	DESCRIPTION
	    "Test email."
	::= { event 49 }

eTPADNoResp NOTIFICATION-TYPE
	STATUS current
	DESCRIPTION
	    "No response to TPAD Transaction."
	::= { event 50 }

eTPADOverlapped NOTIFICATION-TYPE
	STATUS current
	DESCRIPTION
	    "Overlapped TPAD transaction."
	::= { event 51 }

eLAPD16Up NOTIFICATION-TYPE
	STATUS current
	DESCRIPTION
	    "LAPD Sapi16 link up."
	::= { event 52 }

eLAPD16Down NOTIFICATION-TYPE
	STATUS current
	DESCRIPTION
	    "LAPD 16 link down."
	::= { event 53 }

eSNTPTimeCheck NOTIFICATION-TYPE
	STATUS current
	DESCRIPTION
	    "SNTP time check."
	::= { event 54 }

eSMTPRetry NOTIFICATION-TYPE
	STATUS current
	DESCRIPTION
	    "SMTP email retry."
	::= { event 55 }

eExcessiveTransactionTime NOTIFICATION-TYPE
	STATUS current
	DESCRIPTION
	    "Excessive transaction time."
	::= { event 56 }

ePPPMap NOTIFICATION-TYPE
	STATUS current
	DESCRIPTION
	    "PPP mapping to different number."
	::= { event 57 }

eDefaultRouteOOS NOTIFICATION-TYPE
	STATUS current
	DESCRIPTION
	    "Default IP route unavailable."
	::= { event 58 }

eRouteOOS NOTIFICATION-TYPE
	STATUS current
	DESCRIPTION
	    "IP route unavailable."
	::= { event 59 }

eDefaultRouteAvailable NOTIFICATION-TYPE
	STATUS current
	DESCRIPTION
	    "Default IP route available."
	::= { event 60 }

eRouteAvailable NOTIFICATION-TYPE
	STATUS current
	DESCRIPTION
	    "IP route available."
	::= { event 61 }

eDNSFail NOTIFICATION-TYPE
	STATUS current
	DESCRIPTION
	    "DNS query failed."
	::= { event 62 }

eTCPReqFail NOTIFICATION-TYPE
	STATUS current
	DESCRIPTION
	    "TCP request failed."
	::= { event 63 }

eTPADTIDActive NOTIFICATION-TYPE
	STATUS current
	DESCRIPTION
	    "TID authorising active on TPAD."
	::= { event 64 }

eTPADTIDOff NOTIFICATION-TYPE
	STATUS current
	DESCRIPTION
	    "TID authorising off on TPAD."
	::= { event 65 }

eTPADNoPoll NOTIFICATION-TYPE
	STATUS current
	DESCRIPTION
	    "TPAD hasn't been polled for a while."
	::= { event 66 }

eTIDChange NOTIFICATION-TYPE
	STATUS current
	DESCRIPTION
	    "TIDs set on a port have changed."
	::= { event 67 }

eX25DeactIn NOTIFICATION-TYPE
	STATUS current
	DESCRIPTION
	    "X.25 call gone because of lower layer failure."
	::= { event 68 }

eX25DeactUp NOTIFICATION-TYPE
	STATUS current
	DESCRIPTION
	    "X.25 deactivating upper layer."
	::= { event 69 }

eEventCounterReset NOTIFICATION-TYPE
	STATUS current
	DESCRIPTION
	    "Event log max/day counters reset."
	::= { event 70 }

eEventCounterReached NOTIFICATION-TYPE
	STATUS current
	DESCRIPTION
	    "Event log max/day counters reached."
	::= { event 71 }

eDLEBNoResp NOTIFICATION-TYPE
	STATUS current
	DESCRIPTION
	    "No response to <DLE>B poll."
	::= { event 72 }

eSReg0Change NOTIFICATION-TYPE
	STATUS current
	DESCRIPTION
	    "S Register 0 has changed with a command."
	::= { event 73 }

eTCPConnReq NOTIFICATION-TYPE
	STATUS current
	DESCRIPTION
	    "Attempting Outgoing TCP connection."
	::= { event 74 }

eJLATempAlarm NOTIFICATION-TYPE
	STATUS current
	DESCRIPTION
	    "JLA temperature alarm."
	::= { event 75 }

eADSLModemReset NOTIFICATION-TYPE
	STATUS current
	DESCRIPTION
	    "ADSL modem reset."
	::= { event 76 }

eADSLConnOpened NOTIFICATION-TYPE
	STATUS current
	DESCRIPTION
	    "ADSL connection opened."
	::= { event 77 }

eADSLConnClosed NOTIFICATION-TYPE
	STATUS current
	DESCRIPTION
	    "ADSL connection closed."
	::= { event 78 }

eADSLOpenFailed NOTIFICATION-TYPE
	STATUS current
	DESCRIPTION
	    "ADSL open failed."
	::= { event 79 }

eADSLInitFailed NOTIFICATION-TYPE
	STATUS current
	DESCRIPTION
	    "ADSL initialisation failed."
	::= { event 80 }

eV110Connect NOTIFICATION-TYPE
	STATUS current
	DESCRIPTION
	    "Connected with V110 rate adaption."
	::= { event 81 }

eFTPCliResult NOTIFICATION-TYPE
	STATUS current
	DESCRIPTION
	    "FPT client result."
	::= { event 82 }


eFTPCliReq NOTIFICATION-TYPE
	STATUS current
	DESCRIPTION
	    "FTP client request."
	::= { event 83 }

eFTPCliClosed NOTIFICATION-TYPE
	STATUS current
	DESCRIPTION
	    "FTP client session closed."
	::= { event 84 }

eADSLShutdown NOTIFICATION-TYPE
	STATUS current
	DESCRIPTION
	    "ADSL orderly shutdown."
	::= { event 85 }

eNewIPsecSA NOTIFICATION-TYPE
	STATUS current
	DESCRIPTION
	    "New IPSec SA created."
	::= { event 86 }

eNewIKESession NOTIFICATION-TYPE
	STATUS current
	DESCRIPTION
	    "New IKE session started."
	::= { event 87 }

eIPSecSADeleted NOTIFICATION-TYPE
	STATUS current
	DESCRIPTION
	    "IPSec SA deleted."
	::= { event 88 }

eFTPCliQuit NOTIFICATION-TYPE
	STATUS current
	DESCRIPTION
	    "FTP client quitting session."
	::= { event 89 }

eISDNStateChange NOTIFICATION-TYPE
	STATUS current
	DESCRIPTION
	    "ISDN line state change."
	::= { event 90 }

eIKEFailed NOTIFICATION-TYPE
	STATUS current
	DESCRIPTION
	    "IKE session failed."
	::= { event 91 }

eIKEKeyGen NOTIFICATION-TYPE
	STATUS current
	DESCRIPTION
	    "IKE Keys Negotiated."
	::= { event 92 }

eIKEReq NOTIFICATION-TYPE
	STATUS current
	DESCRIPTION
	    "IKE request received from IPSec."
	::= { event 93 }

eIKESADel NOTIFICATION-TYPE
	STATUS current
	DESCRIPTION
	    "IKE SA deleted."
	::= { event 94 }

eModemRetry NOTIFICATION-TYPE
	STATUS current
	DESCRIPTION
	    "Number of GPRS link attempt retries reached."
	::= { event 95 }

eIKENotification NOTIFICATION-TYPE
	STATUS current
	DESCRIPTION
	    "IKE notification send/received."
	::= { event 96 }

eNoIKEKey NOTIFICATION-TYPE
	STATUS current
	DESCRIPTION
	    "Failed to retrieve private key from file."
	::= { event 97 }

eSSLErr NOTIFICATION-TYPE
	STATUS current
	DESCRIPTION
	    "SSL error."
	::= { event 98 }

eFirewallLog NOTIFICATION-TYPE
	STATUS current
	DESCRIPTION
	    "Firewall log event."
	::= { event 99 }

eDataAbort NOTIFICATION-TYPE
	STATUS current
	DESCRIPTION
	    "Data abort."
	::= { event 100 }

eTCPDebug NOTIFICATION-TYPE
	STATUS current
	DESCRIPTION
	    "TCP debug event."
	::= { event 101 }

eTCPBackupOn NOTIFICATION-TYPE
	STATUS current
	DESCRIPTION
	    "TCP backup is on."
	::= { event 102 }

eTCPBackupOff NOTIFICATION-TYPE
	STATUS current
	DESCRIPTION
	    "TCP backup is off."
	::= { event 103 }

eRxSMS NOTIFICATION-TYPE
	STATUS current
	DESCRIPTION
	    "received SMS message."
	::= { event 104 }

ePPPoEStart NOTIFICATION-TYPE
	STATUS current
	DESCRIPTION
	    "PPPoE discovery started."
	::= { event 105 }

ePPPoEEstablished NOTIFICATION-TYPE
	STATUS current
	DESCRIPTION
	    "PPPoE session established."
	::= { event 106 }

ePPPoETerm NOTIFICATION-TYPE
	STATUS current
	DESCRIPTION
	    "PPPoE session terminated."
	::= { event 107 }

ePPPoEErr NOTIFICATION-TYPE
	STATUS current
	DESCRIPTION
	    "PPPoE error."
	::= { event 108 }

eTxSMS NOTIFICATION-TYPE
	STATUS current
	DESCRIPTION
	    "Sent SMS message."
	::= { event 109 }

ePPPDataLimit NOTIFICATION-TYPE
	STATUS current
	DESCRIPTION
	    "PPP data limit reached."
	::= { event 110 }

ePPPDataLimitRst NOTIFICATION-TYPE
	STATUS current
	DESCRIPTION
	    "PPP data limit reset."
	::= { event 111 }

eMUXNotSupported NOTIFICATION-TYPE
	STATUS current
	DESCRIPTION
	    "MUX mode not supported."
	::= { event 112 }

ePBEvent NOTIFICATION-TYPE
	STATUS current
	DESCRIPTION
	    "Pushbutton event."
	::= { event 113 }

eRxUnsupportedMUXMsg NOTIFICATION-TYPE
	STATUS current
	DESCRIPTION
	    "Received unsupported MUX message."
	::= { event 114 }

eUseBackupAPN NOTIFICATION-TYPE
	STATUS current
	DESCRIPTION
	    "Using backup APN."
	::= { event 115 }

eTBandOn NOTIFICATION-TYPE
	STATUS current
	DESCRIPTION
	    "Timeband changed state to ON."
	::= { event 116 }

eTBandOff NOTIFICATION-TYPE
	STATUS current
	DESCRIPTION
	    "Timeband changed state to OFF."
	::= { event 117 }

ePPPUpTime NOTIFICATION-TYPE
	STATUS current
	DESCRIPTION
	    "PPP has reached configured uptime value."
	::= { event 118 }

eLAPDRej NOTIFICATION-TYPE
	STATUS current
	DESCRIPTION
	    "Sent LAPD Reject."
	::= { event 119 }

eUSBHostAttached NOTIFICATION-TYPE
	STATUS current
	DESCRIPTION
	    "New USB host attached."
	::= { event 120 }

eUSBHubOverCurrent NOTIFICATION-TYPE
	STATUS current
	DESCRIPTION
	    "USB hub over-current condition detected/cleared."
	::= { event 121 }

eUSBPortOverCurrent NOTIFICATION-TYPE
	STATUS current
	DESCRIPTION
	    "USB port over-current condition detected/cleared."
	::= { event 122 }

eGPRSPinErr NOTIFICATION-TYPE
	STATUS current
	DESCRIPTION
	    "GPRS PIN error."
	::= { event 123 }

eGPRSOutOfMux NOTIFICATION-TYPE
	STATUS current
	DESCRIPTION
	    "GPRS out of mux detected."
	::= { event 124 }

eErouteOos NOTIFICATION-TYPE
	STATUS current
	DESCRIPTION
	    "Eroute out of service."
	::= { event 125 }

eErouteAvail NOTIFICATION-TYPE
	STATUS current
	DESCRIPTION
	    "Eroute available."
	::= { event 126 }

ePPPReboot NOTIFICATION-TYPE
	STATUS current
	DESCRIPTION
	    "PPP failed. Doing Reboot."
	::= { event 127 }

eGPRSReg NOTIFICATION-TYPE
	STATUS current
	DESCRIPTION
	    "Change in GPRS registration status."
	::= { event 128 }

eGPRSAtt NOTIFICATION-TYPE
	STATUS current
	DESCRIPTION
	    "Change in GPRS attachment status."
	::= { event 129 }

eSWMon NOTIFICATION-TYPE
	STATUS current
	DESCRIPTION
	    "Software monitor event."
	::= { event 130 }

eJLADryerFault NOTIFICATION-TYPE
	STATUS current
	DESCRIPTION
	    "JLA dryer fault."
	::= { event 131 }

eGPRSCellID NOTIFICATION-TYPE
	STATUS current
	DESCRIPTION
	    "GPRS cell ID changed."
	::= { event 132 }

eGPRSDTROFF NOTIFICATION-TYPE
	STATUS current
	DESCRIPTION
	    "GPRS module DTR went off unexpectedly."
	::= { event 133 }

ePPPTimeLimit NOTIFICATION-TYPE
	STATUS current
	DESCRIPTION
	    "PPP time limit reached."
	::= { event 134 }

eSyncTXWatchdog NOTIFICATION-TYPE
	STATUS current
	DESCRIPTION
	    "Physical sync transmit watchdog."
	::= { event 135 }

eBufLow NOTIFICATION-TYPE
	STATUS current
	DESCRIPTION
	    "Low on system buffers."
	::= { event 136 }

eGPRSCause NOTIFICATION-TYPE
    STATUS current
    DESCRIPTION
        "GPRS Cause."
    ::= { event 137 }

eGPRSConnectionStatus NOTIFICATION-TYPE
    STATUS current
    DESCRIPTION
        "GPRS Connection Status."
    ::= { event 138 }

eGPRSManufacturer NOTIFICATION-TYPE
    STATUS current
    DESCRIPTION
        "GPRS Manufacturer."
    ::= { event 139 }

eGPRSURC NOTIFICATION-TYPE
    STATUS current
    DESCRIPTION
        "GPRS URC."
    ::= { event 140 }

ePowerFail NOTIFICATION-TYPE
    STATUS current
    DESCRIPTION
        "Power Fail."
    ::= { event 141 }

ePADInactivity NOTIFICATION-TYPE
    STATUS current
    DESCRIPTION
        "PAD Inactivity."
    ::= { event 142 }

eLAPDExcessiveRejsSent NOTIFICATION-TYPE
    STATUS current
    DESCRIPTION
        "LAPD Excessive Rejs Sent."
    ::= { event 143 }

eGPRSusingSIM NOTIFICATION-TYPE
    STATUS current
    DESCRIPTION
        "GPRS using SIM."
    ::= { event 144 }

eGPRSSIM NOTIFICATION-TYPE
    STATUS current
    DESCRIPTION
        "GPRS SIM."
    ::= { event 145 }

eUserEevent NOTIFICATION-TYPE
    STATUS current
    DESCRIPTION
        "User event"
    ::= { event 146 }

eOutOfService NOTIFICATION-TYPE
    STATUS current
    DESCRIPTION
        "Out Of Service."
    ::= { event 147 }

eAvailable NOTIFICATION-TYPE
    STATUS current
    DESCRIPTION
        "Available."
    ::= { event 148 }

eRecoveryCompleted NOTIFICATION-TYPE
    STATUS current
    DESCRIPTION
        "Recovery Completed."
    ::= { event 149 }

eLogicalInterfaceOutOfService NOTIFICATION-TYPE
    STATUS current
    DESCRIPTION
        "Logical Interface Out Of Service."
    ::= { event 150 }

eLogicalInterfaceAvailable NOTIFICATION-TYPE
    STATUS current
    DESCRIPTION
        "Logical Interface Available."
    ::= { event 151 }

ePPP0up NOTIFICATION-TYPE
    STATUS current
    DESCRIPTION
        "PPP 0 up."
    ::= { event 152 }

ePPP1up NOTIFICATION-TYPE
    STATUS current
    DESCRIPTION
        "PPP 1 up."
    ::= { event 153 }

ePPP2up NOTIFICATION-TYPE
    STATUS current
    DESCRIPTION
        "PPP 2 up."
    ::= { event 154 }

ePPP3up NOTIFICATION-TYPE
    STATUS current
    DESCRIPTION
        "PPP 3 up."
    ::= { event 155 }

ePPP4up NOTIFICATION-TYPE
    STATUS current
    DESCRIPTION
        "PPP 4 up."
    ::= { event 156 }

eLowSystemMessages NOTIFICATION-TYPE
    STATUS current
    DESCRIPTION
        "Low System Messages."
    ::= { event 157 }

eVRRP NOTIFICATION-TYPE
    STATUS current
    DESCRIPTION
        "VRRP."
    ::= { event 158 }

ePADConnectionExcessive NOTIFICATION-TYPE
    STATUS current
    DESCRIPTION
        "PAD Connection Excessive."
    ::= { event 159 }

ePDebug NOTIFICATION-TYPE
    STATUS current
    DESCRIPTION
        "PDebug."
    ::= { event 160 }

eDynDNSDisabled NOTIFICATION-TYPE
    STATUS current
    DESCRIPTION
        "DynDNS disabled."
    ::= { event 161 }

eDynDNSReenabled NOTIFICATION-TYPE
    STATUS current
    DESCRIPTION
        "DynDNS reenabled."
    ::= { event 162 }

eDynDNSHostStopped NOTIFICATION-TYPE
    STATUS current
    DESCRIPTION
        "DynDNS host stopped."
    ::= { event 163 }

eDynDNSHostUpdated NOTIFICATION-TYPE
    STATUS current
    DESCRIPTION
        "DynDNS host updated."
    ::= { event 164 }

eDynDNSUpdateFailed NOTIFICATION-TYPE
    STATUS current
    DESCRIPTION
        "DynDNS update failed."
    ::= { event 165 }

eMobitexNetworkContact NOTIFICATION-TYPE
    STATUS current
    DESCRIPTION
        "Mobitex network contact"
    ::= { event 166 }

eMobitexIASConnection NOTIFICATION-TYPE
    STATUS current
    DESCRIPTION
        "Mobitex IAS connection."
    ::= { event 167 }

eMobitexModemStatus NOTIFICATION-TYPE
    STATUS current
    DESCRIPTION
        "Mobitex modem status."
    ::= { event 168 }

eHighSystemBuffers NOTIFICATION-TYPE
    STATUS current
    DESCRIPTION
        "High System Buffers."
    ::= { event 169 }

eDTRUpASY NOTIFICATION-TYPE
    STATUS current
    DESCRIPTION
        "DTR Up ASY."
    ::= { event 171 }

eDTRDownASY NOTIFICATION-TYPE
    STATUS current
    DESCRIPTION
        "DTR Down ASY."
    ::= { event 172 }

eNewIKEv2NegotiationPeer NOTIFICATION-TYPE
    STATUS current
    DESCRIPTION
        "New IKEv2 Negotiation peer."
    ::= { event 173 }

eIKEv2NegotiationCompletedPeer NOTIFICATION-TYPE
    STATUS current
    DESCRIPTION
        "IKEv2 Negotiation completed peer."
    ::= { event 174 }

eIKEv2RekeyCompletedPeer NOTIFICATION-TYPE
    STATUS current
    DESCRIPTION
        "IKEv2 Rekey completed peer."
    ::= { event 175 }

eRoomO3Level NOTIFICATION-TYPE
    STATUS current
    DESCRIPTION
        "Room O3 Level."
    ::= { event 176 }

eL2TPTunnelUp NOTIFICATION-TYPE
    STATUS current
    DESCRIPTION
        "L2TP Tunnel up."
    ::= { event 177 }

eL2TPTunnelDown NOTIFICATION-TYPE
    STATUS current
    DESCRIPTION
        "L2TP Tunnel down."
    ::= { event 178 }

eL2TPCallUp NOTIFICATION-TYPE
    STATUS current
    DESCRIPTION
        "L2TP Call up."
    ::= { event 179 }

eL2TPCallDown NOTIFICATION-TYPE
    STATUS current
    DESCRIPTION
        "L2TP Call down."
    ::= { event 180 }

eGPSocketConnected NOTIFICATION-TYPE
    STATUS current
    DESCRIPTION
        "GP socket connected."
    ::= { event 181 }

eNVReset NOTIFICATION-TYPE
    STATUS current
    DESCRIPTION
        "NV Reset."
    ::= { event 182 }

eX25CallsPersec NOTIFICATION-TYPE
    STATUS current
    DESCRIPTION
        "X25 Calls per sec."
    ::= { event 183 }

eMsgQs NOTIFICATION-TYPE
    STATUS current
    DESCRIPTION
        "MsgQs."
    ::= { event 184 }

eModemResponse NOTIFICATION-TYPE
    STATUS current
    DESCRIPTION
        "Modem Response."
    ::= { event 185 }

eVXNError NOTIFICATION-TYPE
    STATUS current
    DESCRIPTION
        "VXN error."
    ::= { event 187 }

eSocketMaxACKTimerExpired NOTIFICATION-TYPE
    STATUS current
    DESCRIPTION
        "Socket Max ACK timer expired."
    ::= { event 188 }

eUSBDeviceConnected NOTIFICATION-TYPE
    STATUS current
    DESCRIPTION
        "USB device connected."
    ::= { event 189 }

eUSBDeviceDisconnected NOTIFICATION-TYPE
    STATUS current
    DESCRIPTION
        "USB device disconnected."
    ::= { event 190 }

eASYAssigned NOTIFICATION-TYPE
    STATUS current
    DESCRIPTION
        "ASY assigned"
    ::= { event 191 }

eASYUnassigned NOTIFICATION-TYPE
    STATUS current
    DESCRIPTION
        "ASY unassigned."
    ::= { event 192 }

eAverageTransactionTimeLimit NOTIFICATION-TYPE
    STATUS current
    DESCRIPTION
        "Average transaction time limit."
    ::= { event 193 }

eConsecutiveFailuresLimit NOTIFICATION-TYPE
    STATUS current
    DESCRIPTION
        "Consecutive failures limit."
    ::= { event 194 }

eADSLline NOTIFICATION-TYPE
    STATUS current
    DESCRIPTION
        "ADSL line."
    ::= { event 195 }

eErouteVPNUpPeer NOTIFICATION-TYPE
    STATUS current
    DESCRIPTION
        "Eroute VPN up peer."
    ::= { event 196 }

eErouteVPNDownPeer NOTIFICATION-TYPE
    STATUS current
    DESCRIPTION
        "Eroute VPN down peer."
    ::= { event 197 }

eVXNOPNSNegotiationSuccessful NOTIFICATION-TYPE
    STATUS current
    DESCRIPTION
        "VXN OPNS negotiation successful."
    ::= { event 198 }

eSNAIPPeerConnected NOTIFICATION-TYPE
    STATUS current
    DESCRIPTION
        "SNAIP Peer connected."
    ::= { event 199 }

eSNAIPPeerDisconnected NOTIFICATION-TYPE
    STATUS current
    DESCRIPTION
        "SNAIP Peer disconnected."
    ::= { event 200 }

eSNAIPSAPStateChange NOTIFICATION-TYPE
    STATUS current
    DESCRIPTION
        "SNAIP SAP state change."
    ::= { event 201 }

eSNAIPSAPPUDown NOTIFICATION-TYPE
    STATUS current
    DESCRIPTION
        "SNAIP SAP PU Down."
    ::= { event 202 }

eSNAIPSAPPUUp NOTIFICATION-TYPE
    STATUS current
    DESCRIPTION
        "SNAIP SAP PU Up."
    ::= { event 203 }

eUnableToActivate NOTIFICATION-TYPE
    STATUS current
    DESCRIPTION
        "Unable to activate."
    ::= { event 204 }

eLAPDHealthy NOTIFICATION-TYPE
    STATUS current
    DESCRIPTION
        "LAPD healthy."
    ::= { event 205 }

eLAPDUnhealthy NOTIFICATION-TYPE
    STATUS current
    DESCRIPTION
        "LAPD unhealthy."
    ::= { event 206 }

eMobitexSwitchingInterface NOTIFICATION-TYPE
    STATUS current
    DESCRIPTION
        "Mobitex switching to interface."
    ::= { event 207 }

eGSMRegistration NOTIFICATION-TYPE
    STATUS current
    DESCRIPTION
        "GSM Registration."
    ::= { event 208 }

eADSLModemPowerCycled NOTIFICATION-TYPE
    STATUS current
    DESCRIPTION
        "ADSL modem power-cycled."
    ::= { event 210 }

eMC75FwUpdate NOTIFICATION-TYPE
    STATUS current
    DESCRIPTION
        "MC75 f/w update."
    ::= { event 211 }

eIPMobSocketConnected NOTIFICATION-TYPE
    STATUS current
    DESCRIPTION
        "IP->Mob socket connected."
    ::= { event 212 }

eIPMobSocketDisconnected NOTIFICATION-TYPE
    STATUS current
    DESCRIPTION
        "IP->Mob socket disconnected."
    ::= { event 213 }

eMobIPSocketConnected NOTIFICATION-TYPE
    STATUS current
    DESCRIPTION
        "Mob->IP socket connected."
    ::= { event 214 }

eMobIPSocketDisconnected NOTIFICATION-TYPE
    STATUS current
    DESCRIPTION
        "Mob->IP socket disconnected."
    ::= { event 215 }

eDeactivatedByVRRP NOTIFICATION-TYPE
    STATUS current
    DESCRIPTION
        "Deactivated by VRRP."
    ::= { event 216 }

eReactivated NOTIFICATION-TYPE
    STATUS current
    DESCRIPTION
        "Reactivated"
    ::= { event 217 }

eSNAIPSAPDisconnected NOTIFICATION-TYPE
    STATUS current
    DESCRIPTION
        "SNAIP SAP Disconnected."
    ::= { event 218 }

eSustainedHighCPUUsage NOTIFICATION-TYPE
    STATUS current
    DESCRIPTION
        "Sustained high CPU usage."
    ::= { event 219 }

eIKEErrorDetected NOTIFICATION-TYPE
    STATUS current
    DESCRIPTION
        "IKE error detected."
    ::= { event 220 }

eNetworkTechnologyChanged NOTIFICATION-TYPE
    STATUS current
    DESCRIPTION
        "Network technology changed."
    ::= { event 221 }

eTPADPINChange NOTIFICATION-TYPE
    STATUS current
    DESCRIPTION
        "TPAD PIN change."
    ::= { event 222 }

eIllegalExceptionAtAddress NOTIFICATION-TYPE
    STATUS current
    DESCRIPTION
        "Illegal Exception At Address."
    ::= { event 223 }

eWAPConfiguration NOTIFICATION-TYPE
    STATUS current
    DESCRIPTION
        "WAP configuration."
    ::= { event 224 }

eModemDialingOnAsy NOTIFICATION-TYPE
    STATUS current
    DESCRIPTION
        "Modem dialing on asy."
    ::= { event 225 }

eModemConnectedOnAsy NOTIFICATION-TYPE
    STATUS current
    DESCRIPTION
        "Modem connected on asy."
    ::= { event 226 }

eModemDisconnectedOnAsy NOTIFICATION-TYPE
    STATUS current
    DESCRIPTION
        "Modem disconnected on asy."
    ::= { event 227 }

eLockedTask NOTIFICATION-TYPE
    STATUS current
    DESCRIPTION
        "Locked task."
    ::= { event 228 }

eGPRSSignalStrength NOTIFICATION-TYPE
    STATUS current
    DESCRIPTION
        "GPRS Signal Strength."
    ::= { event 229 }

eSensor NOTIFICATION-TYPE
    STATUS current
    DESCRIPTION
        "Sensor."
    ::= { event 230 }

ePPTPTunnelUp NOTIFICATION-TYPE
    STATUS current
    DESCRIPTION
        "PPTP Tunnel up."
    ::= { event 231 }

ePPTPTunnelDown NOTIFICATION-TYPE
    STATUS current
    DESCRIPTION
        "PPTP Tunnel down."
    ::= { event 232 }

ePPTPCallUp NOTIFICATION-TYPE
    STATUS current
    DESCRIPTION
        "PPTP Call up."
    ::= { event 233 }

ePPTPCallDown NOTIFICATION-TYPE
    STATUS current
    DESCRIPTION
        "PPTP Call down."
    ::= { event 234 }

eUSBDeviceDisabled NOTIFICATION-TYPE
    STATUS current
    DESCRIPTION
        "USB device disabled."
    ::= { event 235 }

eUSBDeviceEnabled NOTIFICATION-TYPE
    STATUS current
    DESCRIPTION
        "USB device enabled."
    ::= { event 236 }

eNovatelFwUpdate NOTIFICATION-TYPE
    STATUS current
    DESCRIPTION
        "Novatel f/w update."
    ::= { event 237 }

eADSLWatchdog NOTIFICATION-TYPE
    STATUS current
    DESCRIPTION
        "ADSL Watchdog."
    ::= { event 238 }

eParChange NOTIFICATION-TYPE
    STATUS current
    DESCRIPTION
        "Parameter change."
    ::= { event 239 }

eWifiAccessPointUp NOTIFICATION-TYPE
    STATUS current
    DESCRIPTION
        "Wi-Fi Access Point up."
    ::= { event 240 }

eWifiAccessPointDown NOTIFICATION-TYPE
    STATUS current
    DESCRIPTION
        "Wi-Fi Access Point down."
    ::= { event 241 }

eWifiClientJoined NOTIFICATION-TYPE
    STATUS current
    DESCRIPTION
        "Wi-Fi client joined."
    ::= { event 242 }

eWifiClientRejoined NOTIFICATION-TYPE
    STATUS current
    DESCRIPTION
        "Wi-Fi client rejoined."
    ::= { event 243 }

eWifiClientLeft NOTIFICATION-TYPE
    STATUS current
    DESCRIPTION
        "Wi-Fi client left."
    ::= { event 244 }

eSTPCannotBeEnabled NOTIFICATION-TYPE
    STATUS current
    DESCRIPTION
        "STP cannot be enabled."
    ::= { event 245 }

eWatchdogwarning NOTIFICATION-TYPE
    STATUS current
    DESCRIPTION
        "Watchdog warning."
    ::= { event 246 }

eSDMMCDeviceConnected NOTIFICATION-TYPE
    STATUS current
    DESCRIPTION
        "SD/MMC device connected."
    ::= { event 247 }

eSDMMCDeviceDisconnected NOTIFICATION-TYPE
    STATUS current
    DESCRIPTION
        "SD/MMC device disconnected."
    ::= { event 248 }

eZingTaskInfo NOTIFICATION-TYPE
	STATUS current
	DESCRIPTION
		"Zing task info"
	::= { event 249 }

eRourceShortage NOTIFICATION-TYPE
	STATUS current
	DESCRIPTION
		"Resource shortage"
	::= { event 250 }

eFtpTx NOTIFICATION-TYPE
	STATUS current
	DESCRIPTION
		"FTP file send"
	::= { event 251 }

eFtpFileRenamed NOTIFICATION-TYPE
	STATUS current
	DESCRIPTION
		"FTP file renamed"
	::= { event 252 }

eFtpFileDeleted NOTIFICATION-TYPE
	STATUS current
	DESCRIPTION
		"FTP file deleted"
	::= { event 253 }

eFtpFileError NOTIFICATION-TYPE
	STATUS current
	DESCRIPTION
		"FTP file error"
	::= { event 254 }

eFtpRx NOTIFICATION-TYPE
	STATUS current
	DESCRIPTION
		"FTP file receive"
	::= { event 255 }

ePowerControlActivated NOTIFICATION-TYPE
	STATUS current
	DESCRIPTION
		"Power control profile activated"
	::= { event 256 }

eAtmPvcDown NOTIFICATION-TYPE
	STATUS current
	DESCRIPTION
		"ATM PVC down"
	::= { event 257 }

eAtmPvcUp NOTIFICATION-TYPE
	STATUS current
	DESCRIPTION
		"ATM PVC up"
	::= { event 258 }

eFwUpdateByCloud NOTIFICATION-TYPE
	STATUS current
	DESCRIPTION
		"Firmware update done via cloud"
	::= { event 259 }

eFactoryDefaultByCloud NOTIFICATION-TYPE
	STATUS current
	DESCRIPTION
		"Factory default done via cloud"
	::= { event 260 }

eModifiedFactoryDefaultByCloud NOTIFICATION-TYPE
	STATUS current
	DESCRIPTION
		"Modified factory default done via cloud"
	::= { event 261 }

eConfigRestoredByCloud NOTIFICATION-TYPE
	STATUS current
	DESCRIPTION
		"Configuration restored via cloud"
	::= { event 262 }

ePowerSupplyGood NOTIFICATION-TYPE
	STATUS current
	DESCRIPTION
		"Power supply good"
	::= { event 263 }

ePowerSupplyFail NOTIFICATION-TYPE
	STATUS current
	DESCRIPTION
		"Power supply failed"
	::= { event 264 }

eFactoryDefaultByButton NOTIFICATION-TYPE
	STATUS current
	DESCRIPTION
		"Factory default done via reset button"
	::= { event 265 }

eGobiDownload NOTIFICATION-TYPE
	STATUS current
	DESCRIPTION
		"GOBI download"
	::= { event 266 }

eWiFiModuleReset NOTIFICATION-TYPE
	STATUS current
	DESCRIPTION
		"Wi-Fi module resetted"
	::= { event 267 }

eUsbReset NOTIFICATION-TYPE
	STATUS current
	DESCRIPTION
		"USB resetted"
	::= { event 268 }

eWiFiNodeConnected NOTIFICATION-TYPE
	STATUS current
	DESCRIPTION
		"Wi-Fi node connected"
	::= { event 269 }

eWiFiNodeDisconnected NOTIFICATION-TYPE
	STATUS current
	DESCRIPTION
		"Wi-Fi node disconnected"
	::= { event 270 }

eCloudConnected NOTIFICATION-TYPE
	STATUS current
	DESCRIPTION
		"Cloud connection established"
	::= { event 271 }

eCloudDisconnected NOTIFICATION-TYPE
	STATUS current
	DESCRIPTION
		"Cloud connection down"
	::= { event 272 }

eWiFiNodeReassociated NOTIFICATION-TYPE
	STATUS current
	DESCRIPTION
		"Wi-Fi node reassociated"
	::= { event 273 }

eWiFiClientProbing NOTIFICATION-TYPE
	STATUS current
	DESCRIPTION
		"Wi-Fi client node probing"
	::= { event 274 }

eRealPortConnected NOTIFICATION-TYPE
	STATUS current
	DESCRIPTION
		"RealPort connected"
	::= { event 275 }

eRealPortDisconnected NOTIFICATION-TYPE
	STATUS current
	DESCRIPTION
		"RealPort disconnected"
	::= { event 276 }

eRealPortFail NOTIFICATION-TYPE
	STATUS current
	DESCRIPTION
		"RealPort failed"
	::= { event 277 }

eRealPortInfo NOTIFICATION-TYPE
	STATUS current
	DESCRIPTION
		"RealPort information"
	::= { event 278 }

eWiFiRogueDetected NOTIFICATION-TYPE
	STATUS current
	DESCRIPTION
		"Wi-Fi rogue AP detected"
	::= { event 279 }

eNoSNMPInformResponse NOTIFICATION-TYPE
	STATUS current
	DESCRIPTION
		"No SNMP Inform response received"
	::= { event 280 }

eReceivedDisconnectFromCloud NOTIFICATION-TYPE
	STATUS current
	DESCRIPTION
		"Disconnect received from cloud server"
	::= { event 281 }

eReconnectingToCloud NOTIFICATION-TYPE
	STATUS current
	DESCRIPTION
		"Reconnecting to cloud server"
	::= { event 282 }

eCloudServerNotResponding NOTIFICATION-TYPE
	STATUS current
	DESCRIPTION
		"Cloud server not responding"
	::= { event 283 }

eCloudSocketOpened NOTIFICATION-TYPE
	STATUS current
	DESCRIPTION
		"Cloud socket opened"
	::= { event 284 }

eCloudReconnectTimerStarted NOTIFICATION-TYPE
	STATUS current
	DESCRIPTION
		"Cloud reconnect timer started"
	::= { event 285 }

eCloudReconnectTimerExpired NOTIFICATION-TYPE
	STATUS current
	DESCRIPTION
		"Cloud reconnect timer expired"
	::= { event 286 }

eOpenConnectionToCloud NOTIFICATION-TYPE
	STATUS current
	DESCRIPTION
		"Open connecto to Cloud"
	::= { event 287 }

eWiFiNodeDeauthed NOTIFICATION-TYPE
	STATUS current
	DESCRIPTION
		"Wi-Fi node deauthorised"
	::= { event 288 }

eEscpResetRequested NOTIFICATION-TYPE
	STATUS current
	DESCRIPTION
		"Reset requested by ESCP"
	::= { event 289 }

eEthernetNotification NOTIFICATION-TYPE
	STATUS current
	DESCRIPTION
		"Ethernet notification"
	::= { event 290 }

eDSLReset NOTIFICATION-TYPE
	STATUS current
	DESCRIPTION
		"DSL card reset"
	::= { event 291 }

eDslLine NOTIFICATION-TYPE
	STATUS current
	DESCRIPTION
		"DSL line status"
	::= { event 292 }

eCloudSocketClosed NOTIFICATION-TYPE
	STATUS current
	DESCRIPTION
		"Cloud socket closed"
	::= { event 293 }

eInvalidLicenseFile NOTIFICATION-TYPE
	STATUS current
	DESCRIPTION
		"Invalid license file"
	::= { event 294 }

eFusionModule NOTIFICATION-TYPE
	STATUS current
	DESCRIPTION
		"Fusion module status"
	::= { event 295 }

eSmsMsgReceived NOTIFICATION-TYPE
	STATUS current
	DESCRIPTION
		"Cloud SMS message received"
	::= { event 296 }

eSmsOptInSent NOTIFICATION-TYPE
	STATUS current
	DESCRIPTION
		"Cloud SMS opt-in message sent"
	::= { event 297 }

eGPRS NOTIFICATION-TYPE
	STATUS current
	DESCRIPTION
		"GPRS event"
	::= { event 298 }

eUsbDisconnectEvent NOTIFICATION-TYPE
	STATUS current
	DESCRIPTION
		"Unexpected USB disconnect event"
	::= { event 299 }

eUsbDisconnectEvent2 NOTIFICATION-TYPE
	STATUS current
	DESCRIPTION
		"Unexpected USB disconnect event 2"
	::= { event 300 }

eTempWarning NOTIFICATION-TYPE
	STATUS current
	DESCRIPTION
		"Temperature warning"
	::= { event 301 }

eDmnrUp NOTIFICATION-TYPE
	STATUS current
	DESCRIPTION
		"DMNR tunnel up"
	::= { event 302 }

eDmnrDown NOTIFICATION-TYPE
	STATUS current
	DESCRIPTION
		"DMNR tunnel down"
	::= { event 303 }

eDmnrRegPacketDiscarded NOTIFICATION-TYPE
	STATUS current
	DESCRIPTION
		"DMNR registration packet discarded"
	::= { event 304 }

eCertEnrolFailure NOTIFICATION-TYPE
	STATUS current
	DESCRIPTION
		"Certificate enrol failure"
	::= { event 305 }

eCertEnrolSuccess NOTIFICATION-TYPE
	STATUS current
	DESCRIPTION
		"Certificate enrol success"
	::= { event 306 }

eModemState NOTIFICATION-TYPE
	STATUS current
	DESCRIPTION
		"Cottonmouth modem status"
	::= { event 307 }

eQmiInterfaceAttached NOTIFICATION-TYPE
	STATUS current
	DESCRIPTION
		"QMI interface attached"
	::= { event 308 }

eQmiInterfaceDetached NOTIFICATION-TYPE
	STATUS current
	DESCRIPTION
		"QMI interface detached"
	::= { event 309 }

eTelitOma NOTIFICATION-TYPE
	STATUS current
	DESCRIPTION
		"Telit OMA"
	::= { event 310 }

eTelitUpdate NOTIFICATION-TYPE
	STATUS current
	DESCRIPTION
		"Telit firmware update"
	::= { event 311 }

eTelitUpdateSuccess NOTIFICATION-TYPE
	STATUS current
	DESCRIPTION
		"Telit firmware update success"
	::= { event 312 }

eTelitUpdateFailure NOTIFICATION-TYPE
	STATUS current
	DESCRIPTION
		"Telit firmware update failure"
	::= { event 313 }

eEthCableDisconnect NOTIFICATION-TYPE
	STATUS current
	DESCRIPTION
		"Ethernet cable disconnected"
	::= { event 314 }

eEthCableConnect NOTIFICATION-TYPE
	STATUS current
	DESCRIPTION
		"Ethernet cable connected"
	::= { event 315 }

eSetBackoffTimer NOTIFICATION-TYPE
	STATUS current
	DESCRIPTION
		"PPP backoff timer set"
	::= { event 316 }

eTempNormal NOTIFICATION-TYPE
	STATUS current
	DESCRIPTION
		"Temperature normal"
	::= { event 317 }

ePowerControlCpuSpeedChange NOTIFICATION-TYPE
	STATUS current
	DESCRIPTION
		"Power controll changed CPU speed"
	::= { event 318 }

ePowerControlSubsystemOff NOTIFICATION-TYPE
	STATUS current
	DESCRIPTION
		"Power control turned off subsystem"
	::= { event 319 }

ePowerControlSubsystemOn NOTIFICATION-TYPE
	STATUS current
	DESCRIPTION
		"Power control turned on subsystem"
	::= { event 320 }

eLoginAddress NOTIFICATION-TYPE
	STATUS current
	DESCRIPTION
		"Login address"
	::= { event 321 }

eWebFormMissingCSRF NOTIFICATION-TYPE
	STATUS current
	DESCRIPTION
		"Web form missing CSRF token"
	::= { event 322 }

END
