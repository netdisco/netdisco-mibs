SARIAN-MONITOR-MIB DEFINITIONS ::= BEGIN
--
-- Copyright (c) 2011 Digi International Inc. All rights reserved.
--
-- Sarian Monitor MIB
--

IMPORTS
	enterprises, MODULE-IDENTITY, OBJECT-TYPE, 	
	Counter64, IpAddress,Integer32				FROM SNMPv2-SMI
	MODULE-COMPLIANCE, OBJECT-GROUP				FROM SNMPv2-CONF
	DisplayString								FROM SNMPv2-TC;

sarianMonitorMIB MODULE-IDENTITY
	LAST-UPDATED "201305280000Z"	-- 28 May 2013
	ORGANIZATION
		"Digi International, Inc."
	CONTACT-INFO
		"Digi International Tech Support

		 Phone: 877 912 3444     (US and Canada)
		 		+1 952 912 3456  (Worldwide)
		 EMail: <Tech.Support@digi.com>"
	DESCRIPTION
		"The Sarian Monitor MIB for managing the Digi TransPort product range."
	REVISION	"201305280000Z"	-- 28 May 2013
	DESCRIPTION
		"Updated to comply with SMI-v2 syntax definitions."
	::= { sarian 11000 }

sarian			OBJECT IDENTIFIER ::= { enterprises 16378 }
sarianMonitor	OBJECT IDENTIFIER ::= { sarian 10000 }

sarianPPP		OBJECT IDENTIFIER ::= { sarianMonitor 1 }
sarianGPRS		OBJECT IDENTIFIER ::= { sarianMonitor 2 }
sarianSystem	OBJECT IDENTIFIER ::= { sarianMonitor 3 }
sarianConfig	OBJECT IDENTIFIER ::= { sarianMonitor 4 }
sarianCDMA		OBJECT IDENTIFIER ::= { sarianMonitor 5 }


--
-- Sarian PPP
--
numPPPInterfaces	OBJECT-TYPE
	SYNTAX		Integer32
	MAX-ACCESS	read-only
	STATUS		current
	DESCRIPTION
		"The number of PPP interfaces."
	::= { sarianPPP 1 }

sarianPPPTable	OBJECT-TYPE
	SYNTAX		SEQUENCE OF SarianPPPEntry
	MAX-ACCESS	not-accessible
	STATUS		current
	DESCRIPTION
		"A list of entries containing status information for all
		PPP entities on this system."
	::= { sarianPPP 2 }

sarianPPPEntry	OBJECT-TYPE
	SYNTAX		SarianPPPEntry
	MAX-ACCESS	not-accessible
	STATUS		current
	DESCRIPTION
		"An entry containing status information for a particular
		PPP entity."
	INDEX { ifIndex }
	::= { sarianPPPTable 1 }

SarianPPPEntry ::=
	SEQUENCE {
		ifIndex			  	Integer32,
		pppDLTotalData	  	Counter64,
		pppDLWarn		  	Counter64,
		pppDLStop		  	Counter64,
		pppDLDayReset	  	Integer32,
		pppDLLastReset	  	DisplayString,
		pppDLResetTotalData	Integer32,
		pppUserName	  	    DisplayString,
		pppUptime	Integer32
}

ifIndex 		OBJECT-TYPE
	SYNTAX	Integer32 (0..2147483647)
	MAX-ACCESS	read-only
	STATUS	current
	DESCRIPTION
		"A unique value assigned to each interface."
	::= { sarianPPPEntry 1 }

pppDLTotalData	OBJECT-TYPE
	SYNTAX	Counter64
	MAX-ACCESS	read-only
	STATUS	current
	DESCRIPTION
		"Total amount of data (in bytes) transferred in this PPP
		entity during the data limit period."
	::= { sarianPPPEntry 2 }

pppDLWarn	OBJECT-TYPE
	SYNTAX	Counter64
	MAX-ACCESS	read-only
	STATUS	current
	DESCRIPTION
		"The PPP data limit (in bytes) at which point a warning
		event is generated."
	::= { sarianPPPEntry 3 }

pppDLStop	OBJECT-TYPE
	SYNTAX	Counter64
	MAX-ACCESS	read-only
	STATUS	current
	DESCRIPTION
		"The PPP data limit (in bytes) at which point no more
		traffic is transferred."
	::= { sarianPPPEntry 4 }

pppDLDayReset	OBJECT-TYPE
	SYNTAX	Integer32 (0..31)
	MAX-ACCESS	read-write
	STATUS	current
	DESCRIPTION
		"The day of the month on which the total data transferred 
		is reset. If this object is zero, the total data 
		transferred needs to be manually reset."
	::= { sarianPPPEntry 5 }

pppDLLastReset	OBJECT-TYPE
	SYNTAX	DisplayString
	MAX-ACCESS	read-only
	STATUS	current
	DESCRIPTION
		"The data on which the last reset of the total data
		transferred was reset."
	::= { sarianPPPEntry 6 }

pppDLResetTotalData	OBJECT-TYPE
	SYNTAX	Integer32
	MAX-ACCESS	read-write
	STATUS	current
	DESCRIPTION
		"Writing to this object will reset the total data
		counter. Reading this value will always return 0."
	::= { sarianPPPEntry 7 }

pppUserName	OBJECT-TYPE
	SYNTAX	DisplayString
	MAX-ACCESS	read-write
	STATUS	current
	DESCRIPTION
		"The username used during authentication."
	::= { sarianPPPEntry 8 }

pppUptime	OBJECT-TYPE
	SYNTAX	Integer32
	MAX-ACCESS	read-write
	STATUS	current
	DESCRIPTION
		"The time in seconds that this connection has been up."
	::= { sarianPPPEntry 9 }

--
-- Sarian GPRS
--
gprsSignalStrength	OBJECT-TYPE
	SYNTAX	Integer32
	MAX-ACCESS	read-only
	STATUS	current
	DESCRIPTION
		"The GPRS signal strength."
	::= { sarianGPRS 1 }

gprsRegistered	OBJECT-TYPE
	SYNTAX	INTEGER {
				notRegisteredNotSearching(0),
				registeredHomeNetwork(1),
				notRegisteredSearching(2),
				registerationDenied(3),
				unknown(4),
				registeredRoaming(5),
				unrecognised(6)
			}
	MAX-ACCESS	read-only
	STATUS	current
	DESCRIPTION
		"The GPRS Registeration Status."
	::= { sarianGPRS 2 }

gprsAttached	OBJECT-TYPE
	SYNTAX	INTEGER {
				notAttached(0),
				attached(1)
			}
	MAX-ACCESS	read-only
	STATUS	current
	DESCRIPTION
		"The GPRS Attachment Status."
	::= { sarianGPRS 3 }

gprsPPPIP		OBJECT-TYPE
	SYNTAX	IpAddress
	MAX-ACCESS	read-only
	STATUS	current
	DESCRIPTION
		"The IP address of the PPP interface using GPRS."
	::= { sarianGPRS 4 }

gprsAreaID		OBJECT-TYPE
	SYNTAX	Integer32
	MAX-ACCESS	read-only
	STATUS	current
	DESCRIPTION
		"The GPRS Location Area Code."
	::= { sarianGPRS 5 }

gprsCellID		OBJECT-TYPE
	SYNTAX	Integer32
	MAX-ACCESS	read-only
	STATUS	current
	DESCRIPTION
		"The GPRS Cell ID."
	::= { sarianGPRS 6 }

gprsNetworkTechnology	OBJECT-TYPE
	SYNTAX	INTEGER {
				unknown(1),
				gprs(2),
				edge(3),
				umts(4),
				hsdpa(5),
				hsupa(6),
				hspa(7),
				lte(8)
			}
	MAX-ACCESS	read-only
	STATUS	current
	DESCRIPTION
		"The GPRS Network Technology in use."
	::= { sarianGPRS 7 }

gprsCdmaEcio	OBJECT-TYPE
	SYNTAX	DisplayString
	MAX-ACCESS	read-only
	STATUS	deprecated
	DESCRIPTION
		"The CDMA ECIO."
	::= { sarianGPRS 8 }

gprsCdmaPilotPN	OBJECT-TYPE
	SYNTAX	Integer32
	MAX-ACCESS	read-only
	STATUS	deprecated
	DESCRIPTION
		"The CDMA Pilot PN."
	::= { sarianGPRS 9 }

gprsCdmaDRC		OBJECT-TYPE
	SYNTAX	DisplayString
	MAX-ACCESS	read-only
	STATUS	deprecated
	DESCRIPTION
		"The CDMA DRC."
	::= { sarianGPRS 10 }

gprsCdmaESN OBJECT-TYPE
	SYNTAX	DisplayString
	MAX-ACCESS	read-only
	STATUS	deprecated
	DESCRIPTION
		"The CMDA Electronic Serial Number."
	::= { sarianGPRS 11 }

gprsCdmaMEID OBJECT-TYPE
	SYNTAX	DisplayString
	MAX-ACCESS	read-only
	STATUS	deprecated
	DESCRIPTION
		"The CMDA Mobile Equipment Manufacturer ID."
	::= { sarianGPRS 12 }

gprsCdmaMDN OBJECT-TYPE
	SYNTAX	DisplayString
	MAX-ACCESS	read-only
	STATUS	deprecated
	DESCRIPTION
		"The CMDA Mobile Directory Number."
	::= { sarianGPRS 13 }

gprsCdmaMIN OBJECT-TYPE
	SYNTAX	DisplayString
	MAX-ACCESS	read-only
	STATUS	deprecated
	DESCRIPTION
		"The CMDA Mobile Identification Number."
	::= { sarianGPRS 14 }

gprsCdmaSignalStrength	OBJECT-TYPE
	SYNTAX	Integer32
	MAX-ACCESS	read-only
	STATUS	deprecated
	DESCRIPTION
		"The CDMA signal strength."
	::= { sarianGPRS 15 }

gprsEvdoSignalStrength	OBJECT-TYPE
	SYNTAX	Integer32
	MAX-ACCESS	read-only
	STATUS	deprecated
	DESCRIPTION
		"The EVDO signal strength."
	::= { sarianGPRS 16 }

gprsEvdoEcio	OBJECT-TYPE
	SYNTAX	DisplayString
	MAX-ACCESS	read-only
	STATUS	deprecated
	DESCRIPTION
		"The EVDO ECIO."
	::= { sarianGPRS 17 }
	
gprsRadioTechnology	OBJECT-TYPE
	SYNTAX	INTEGER {
				unknown(1),
				gsm(2),
				cdma(3),
				wcdma(4),
				lte(5)
			}
	MAX-ACCESS	read-only
	STATUS	current
	DESCRIPTION
		"The Radio Technology in use."
	::= { sarianGPRS 18 }

gprsIMEI		OBJECT-TYPE
	SYNTAX	DisplayString
	MAX-ACCESS	read-only
	STATUS	current
	DESCRIPTION
		"The International Mobile Equipment Identity (IMSI) of the device."
	::= { sarianGPRS 19 }

gprsICCID		OBJECT-TYPE
	SYNTAX	DisplayString
	MAX-ACCESS	read-only
	STATUS	current
	DESCRIPTION
		"The Integrated Circuit Card ID (ICCID) of the SIM card."
	::= { sarianGPRS 20 }

gprsIMSI		OBJECT-TYPE
	SYNTAX	DisplayString
	MAX-ACCESS	read-only
	STATUS	current
	DESCRIPTION
		"The International Mobile Subscriber Identity (IMSI) of the SIM card."
	::= { sarianGPRS 21 }

gprsNetwork		OBJECT-TYPE
	SYNTAX	DisplayString
	MAX-ACCESS	read-only
	STATUS	current
	DESCRIPTION
		"The network to which the device is connected to."
	::= { sarianGPRS 22 }
	
gprsLteRSRP		OBJECT-TYPE
	SYNTAX	Integer32
	MAX-ACCESS	read-only
	STATUS	current
	DESCRIPTION
		"The LTE RSRP signal strength."
	::= { sarianGPRS 23 }

gprsLteRSRQ		OBJECT-TYPE
	SYNTAX	Integer32
	MAX-ACCESS	read-only
	STATUS	current
	DESCRIPTION
		"The LTE RSRQ signal quality."
	::= { sarianGPRS 24 }

gprsLteSINR		OBJECT-TYPE
	SYNTAX	DisplayString
	MAX-ACCESS	read-only
	STATUS	current
	DESCRIPTION
		"The LTE signal to interference plus noise ratio."
	::= { sarianGPRS 25 }

gprsSIMStatus		OBJECT-TYPE
	SYNTAX	DisplayString
	MAX-ACCESS	read-only
	STATUS	current
	DESCRIPTION
		"The SIM status."
	::= { sarianGPRS 26 }

gprsAPN		OBJECT-TYPE
	SYNTAX	DisplayString
	MAX-ACCESS	read-only
	STATUS	current
	DESCRIPTION
		"The primary APN."
	::= { sarianGPRS 27 }

gprsAPNBackup		OBJECT-TYPE
	SYNTAX	DisplayString
	MAX-ACCESS	read-only
	STATUS	current
	DESCRIPTION
		"The backup APN."
	::= { sarianGPRS 28 }

gprsPhoneNumber		OBJECT-TYPE
	SYNTAX	DisplayString
	MAX-ACCESS	read-only
	STATUS	current
	DESCRIPTION
		"The called number."
	::= { sarianGPRS 29 }

gprsCurrentSIM		OBJECT-TYPE
	SYNTAX	INTEGER {
				unknown(0),
				SIM1(1),
				SIM2(2)
			}
	MAX-ACCESS	read-only
	STATUS	current
	DESCRIPTION
		"The current SIM."
	::= { sarianGPRS 30 }

gprsLTEBand		OBJECT-TYPE
	SYNTAX	DisplayString
	MAX-ACCESS	read-only
	STATUS	current
	DESCRIPTION
		"Band info."
	::= { sarianGPRS 31 }

--
-- Sarian System
--
cpuUtil		OBJECT-TYPE
	SYNTAX	Integer32 (0..100)
	MAX-ACCESS	read-only
	STATUS	current
	DESCRIPTION
		"The current CPU utilization."
	::= { sarianSystem 1 }

cpuMin		OBJECT-TYPE
	SYNTAX	Integer32 (0..100)
	MAX-ACCESS	read-only
	STATUS	current
	DESCRIPTION
		"The minimum CPU utilization recorded."
	::= { sarianSystem 2 }

cpuMax		OBJECT-TYPE
	SYNTAX	Integer32 (0..100)
	MAX-ACCESS	read-only
	STATUS	current
	DESCRIPTION
		"The maximum CPU utilization recorded."
	::= { sarianSystem 3 }

cpuAvg		OBJECT-TYPE
	SYNTAX	Integer32 (0..100)
	MAX-ACCESS	read-only
	STATUS	current
	DESCRIPTION
		"The average CPU utilization recorded."
	::= { sarianSystem 4 }

msgsFree	OBJECT-TYPE
	SYNTAX  Integer32
	MAX-ACCESS  read-only
	STATUS  current
	DESCRIPTION
		"The number of free messages."
	::= { sarianSystem 5 }

msgsMin		OBJECT-TYPE
	SYNTAX  Integer32
	MAX-ACCESS  read-only
	STATUS  current
	DESCRIPTION
		"The minimum number of free messages that has been 
		recorded."
	::= { sarianSystem 6 }

bufsFree	OBJECT-TYPE
	SYNTAX  Integer32
	MAX-ACCESS  read-only
	STATUS  current
	DESCRIPTION
		"The number of free buffers."
	::= { sarianSystem 7 }

bufsMin		OBJECT-TYPE
	SYNTAX  Integer32
	MAX-ACCESS  read-only
	STATUS  current
	DESCRIPTION
		"The minimum number of free buffers that has been 
		recorded."
	::= { sarianSystem 8 }

bigBufsFree		OBJECT-TYPE
	SYNTAX  Integer32
	MAX-ACCESS  read-only
	STATUS  current
	DESCRIPTION
		"The number of free big buffers."
	::= { sarianSystem 9 }

bigBufsMin		OBJECT-TYPE
	SYNTAX  Integer32
	MAX-ACCESS  read-only
	STATUS  current
	DESCRIPTION
		"The minimum number of free big buffers that has been 
		recorded."
	::= { sarianSystem 10 }

temperature		OBJECT-TYPE
	SYNTAX	Integer32
	MAX-ACCESS	read-only
	STATUS	current
	DESCRIPTION
		"The internal temperature of the device in Celsius."
	::= { sarianSystem 11 }

processorTemperature	OBJECT-TYPE
	SYNTAX	Integer32
	MAX-ACCESS	read-only
	STATUS	current
	DESCRIPTION
		"The temperature of the processor in Celsius."
	::= { sarianSystem 12 }

modemTemperature	OBJECT-TYPE
	SYNTAX	Integer32
	MAX-ACCESS	read-only
	STATUS	current
	DESCRIPTION
		"The temperature of the cellular modem in Celsius."
	::= { sarianSystem 13 }

model					OBJECT-TYPE
	SYNTAX  DisplayString
	MAX-ACCESS  read-only
	STATUS  current
	DESCRIPTION
		"The TransPort model."
	::= { sarianSystem 14 }

serialNumber			OBJECT-TYPE
	SYNTAX  DisplayString
	MAX-ACCESS  read-only
	STATUS  current
	DESCRIPTION
		"The serial number of the device."
	::= { sarianSystem 15 }

firmwareVersion			OBJECT-TYPE
	SYNTAX  DisplayString
	MAX-ACCESS  read-only
	STATUS  current
	DESCRIPTION
		"The firmware version currently running on the device."
	::= { sarianSystem 16 }
	
totalMemory				OBJECT-TYPE
	SYNTAX	Integer32
	MAX-ACCESS	read-only
	STATUS	current
	DESCRIPTION
		"The total amount of memory in KB available on the device."
	::= { sarianSystem 17 }

freeMemory				OBJECT-TYPE
	SYNTAX	Integer32
	MAX-ACCESS	read-only
	STATUS	current
	DESCRIPTION
		"The amount of free memory in KB available on the device."
	::= { sarianSystem 18 }

modemModel				OBJECT-TYPE
	SYNTAX  DisplayString
	MAX-ACCESS  read-only
	STATUS  current
	DESCRIPTION
		"The cellular modem model."
	::= { sarianSystem 19 }

modemFirmware			OBJECT-TYPE
	SYNTAX  DisplayString
	MAX-ACCESS  read-only
	STATUS  current
	DESCRIPTION
		"The cellular modem firmware version."
	::= { sarianSystem 20 }

--
-- Sarian Config
--
changesSincePowerUp		OBJECT-TYPE
	SYNTAX	Integer32
	MAX-ACCESS	read-only
	STATUS	current
	DESCRIPTION
		"The number of changes made to the configuration since
		the unit was powered up."
	::= { sarianConfig 1 }

unsavedChanges			OBJECT-TYPE
	SYNTAX	Integer32
	MAX-ACCESS	read-only
	STATUS	current
	DESCRIPTION
		"The number of unsaved configuration changes."
	::= { sarianConfig 2 }

lastSavedConfigUser		OBJECT-TYPE
	SYNTAX	DisplayString
	MAX-ACCESS	read-only
	STATUS	current
	DESCRIPTION
		"The user who last saved the configuration."
	::= { sarianConfig 3 }

lastSavedConfigTime		OBJECT-TYPE
	SYNTAX	DisplayString
	MAX-ACCESS	read-only
	STATUS	current
	DESCRIPTION
		"The time the configuration was last saved."
	::= { sarianConfig 4 }

lastSavedConfigNumber	OBJECT-TYPE
	SYNTAX	Integer32
	MAX-ACCESS	read-only
	STATUS	current
	DESCRIPTION
		"The number of changes that had been made when the 
		configuration was last saved."
	::= { sarianConfig 5 }

pwdChangesSincePowerUp	OBJECT-TYPE
	SYNTAX	Integer32
	MAX-ACCESS	read-only
	STATUS	current
	DESCRIPTION
		"The number of changes made to the password 
		configuration since the unit was powered up."
	::= { sarianConfig 6 }

unsavedPwdChanges		OBJECT-TYPE
	SYNTAX	Integer32
	MAX-ACCESS	read-only
	STATUS	current
	DESCRIPTION
		"The number of unsaved password configuration 
		changes."
	::= { sarianConfig 7 }

lastSavedPwdConfigUser	OBJECT-TYPE
	SYNTAX	DisplayString
	MAX-ACCESS	read-only
	STATUS	current
	DESCRIPTION
		"The user who last saved the password configuration."
	::= { sarianConfig 8 }

lastSavedPwdConfigTime	OBJECT-TYPE
	SYNTAX	DisplayString
	MAX-ACCESS	read-only
	STATUS	current
	DESCRIPTION
		"The time the password configuration was last saved."
	::= { sarianConfig 9 }

lastSavedPwdConfigNumber	OBJECT-TYPE
	SYNTAX	Integer32
	MAX-ACCESS	read-only
	STATUS	current
	DESCRIPTION
		"The number of changes that had been made when the 
		password configuration was last saved."
	::= { sarianConfig 10 }

--
-- Sarian CDMA
--
cdmaServiceMode	OBJECT-TYPE
	SYNTAX	INTEGER {
			unknown (1),
			cdma1xrtt (2),
			cdmaEvdoRev0 (3),
			cdmaEvdoRevA (4),
			cdmaEvdoEHRPD (5)
		}
	MAX-ACCESS	read-only
	STATUS	current
	DESCRIPTION
		"The CDMA service mode."
	::= { sarianCDMA 1 }

cdmaPilotPN	OBJECT-TYPE
	SYNTAX	Integer32
	MAX-ACCESS	read-only
	STATUS	current
	DESCRIPTION
		"The CDMA Pilot PN."
	::= { sarianCDMA 2 }

cdmaDRC		OBJECT-TYPE
	SYNTAX	DisplayString
	MAX-ACCESS	read-only
	STATUS	current
	DESCRIPTION
		"The CDMA DRC."
	::= { sarianCDMA 3 }

cdmaESN OBJECT-TYPE
	SYNTAX	DisplayString
	MAX-ACCESS	read-only
	STATUS	current
	DESCRIPTION
		"The CMDA Electronic Serial Number."
	::= { sarianCDMA 4 }

cdmaMEID OBJECT-TYPE
	SYNTAX	DisplayString
	MAX-ACCESS	read-only
	STATUS	current
	DESCRIPTION
		"The CMDA Mobile Equipment Manufacturer ID."
	::= { sarianCDMA 5 }

cdmaMDN OBJECT-TYPE
	SYNTAX	DisplayString
	MAX-ACCESS	read-only
	STATUS	current
	DESCRIPTION
		"The CMDA Mobile Directory Number."
	::= { sarianCDMA 6 }

cdmaMIN OBJECT-TYPE
	SYNTAX	DisplayString
	MAX-ACCESS	read-only
	STATUS	current
	DESCRIPTION
		"The CMDA Mobile Identification Number."
	::= { sarianCDMA 7 }

cdmaPRLVersion	OBJECT-TYPE
	SYNTAX	DisplayString
	MAX-ACCESS	read-only
	STATUS	current
	DESCRIPTION
		"The CMDA PRL version."
	::= { sarianCDMA 8 }

cdmaSignalStrength	OBJECT-TYPE
	SYNTAX	Integer32
	MAX-ACCESS	read-only
	STATUS	current
	DESCRIPTION
		"The CDMA signal strength."
	::= { sarianCDMA 9 }

evdoSignalStrength	OBJECT-TYPE
	SYNTAX	Integer32
	MAX-ACCESS	read-only
	STATUS	current
	DESCRIPTION
		"The EVDO signal strength."
	::= { sarianCDMA 10 }

cdmaEcio	OBJECT-TYPE
	SYNTAX	DisplayString
	MAX-ACCESS	read-only
	STATUS	current
	DESCRIPTION
		"The CDMA Ecio."
	::= { sarianCDMA 11 }

evdoEcio	OBJECT-TYPE
	SYNTAX	DisplayString
	MAX-ACCESS	read-only
	STATUS	current
	DESCRIPTION
		"The EVDO Ecio."
	::= { sarianCDMA 12 }


-- Conformance Information
sarianMonitorConformance	OBJECT IDENTIFIER ::= { sarianMonitor 100 }

sarianMonitorGroups			OBJECT IDENTIFIER ::= { sarianMonitorConformance 1 }
sarianMonitorCompliances	OBJECT IDENTIFIER ::= { sarianMonitorConformance 2 }

sarianMonitorCompliance MODULE-COMPLIANCE
	STATUS	current
	DESCRIPTION
			"Compliance statement for Sarian Monitor objects."

	MODULE
		GROUP			sarianPPPGroup
		DESCRIPTION
				"Compliance group for PPP objects"
				
		GROUP			sarianGPRSGroup
		DESCRIPTION
				"Compliance group for GPRS objects"
				
		GROUP			sarianSystemGroup
		DESCRIPTION
				"Compliance group for system objects"
				
		GROUP			sarianConfigGroup
		DESCRIPTION
				"Compliance group for configuration objects"
				
		GROUP			sarianCDMAGroup
		DESCRIPTION
				"Compliance group for CDMA objects"

	::= { sarianMonitorCompliances 1 }

sarianMonitorCompliance2 MODULE-COMPLIANCE
	STATUS	deprecated
	DESCRIPTION
			"Compliance statement for deprecated Sarian Monitor objects."

	MODULE
		GROUP			sarianGPRSCDMAGroup
		DESCRIPTION
				"Compliance group for deprecated CDMA objects"
				
	::= { sarianMonitorCompliances 2 }


sarianPPPGroup	OBJECT-GROUP
	OBJECTS { numPPPInterfaces, ifIndex, pppDLTotalData, pppDLWarn, pppDLStop,
				pppDLDayReset, pppDLLastReset, pppDLResetTotalData }
	STATUS	current
	DESCRIPTION
			"A collection of objects for monitoring PPP interfaces."
	::= { sarianMonitorGroups 1 }

sarianGPRSGroup OBJECT-GROUP
	OBJECTS { gprsSignalStrength, gprsRegistered, gprsAttached,
				gprsPPPIP, gprsAreaID, gprsCellID, gprsNetworkTechnology }
	STATUS	current
	DESCRIPTION
			"A collection of objects for monitoring GPRS connections."
	::= { sarianMonitorGroups 2 }

sarianGPRSCDMAGroup OBJECT-GROUP
	OBJECTS { gprsCdmaEcio, gprsCdmaPilotPN, gprsCdmaDRC, gprsCdmaESN, 
				gprsCdmaMEID, gprsCdmaMDN, gprsCdmaMIN, 
				gprsCdmaSignalStrength, gprsEvdoSignalStrength, 
				gprsEvdoEcio }
	STATUS	deprecated
	DESCRIPTION
			"A collection of objects for monitoring CDMA connections."
	::= { sarianMonitorGroups 3 }


sarianSystemGroup OBJECT-GROUP
	OBJECTS { cpuUtil, cpuMin, cpuMax, cpuAvg, msgsFree, msgsMin, 
				bufsFree, bufsMin, bigBufsFree, bigBufsMin, temperature }
	STATUS	current
	DESCRIPTION
			"A collection of objects for monitoring system information."
	::= { sarianMonitorGroups 4 }

sarianConfigGroup OBJECT-GROUP
	OBJECTS { changesSincePowerUp, unsavedChanges, lastSavedConfigUser, 
				lastSavedConfigTime, lastSavedConfigNumber, 
				pwdChangesSincePowerUp, unsavedPwdChanges, 
				lastSavedPwdConfigUser, lastSavedPwdConfigTime, 
				lastSavedPwdConfigNumber }
	STATUS	current
	DESCRIPTION
			"A collection of objects for monitoring configuration information."
	::= { sarianMonitorGroups 5 }

sarianCDMAGroup OBJECT-GROUP
	OBJECTS { cdmaServiceMode, cdmaPilotPN, cdmaDRC, cdmaESN, cdmaMEID, 
				cdmaMDN, cdmaMIN, cdmaPRLVersion, cdmaSignalStrength, 
				evdoSignalStrength, cdmaEcio, evdoEcio }
	STATUS	current
	DESCRIPTION
			"A collection of objects for monitoring CDMA connections."
	::= { sarianMonitorGroups 6 }

END
