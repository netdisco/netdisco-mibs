SARIAN-IPSEC-MIB DEFINITIONS ::= BEGIN
--
-- Copyright (c) 2014 Digi International Inc. All rights reserved.
--
-- Sarian IPsec MIB
--
-- Updates
--
--  1 Jun 2016 Created
--

IMPORTS
    enterprises                                 FROM RFC1155-SMI
    MODULE-IDENTITY, OBJECT-TYPE, Integer32,
    Unsigned32, Counter32, Counter64, IpAddress FROM SNMPv2-SMI
    DisplayString, MacAddress, TruthValue       FROM SNMPv2-TC;

sarianIpsecMIB MODULE-IDENTITY
	LAST-UPDATED "201606010000Z"	-- 1 Jun 2016
	ORGANIZATION
		"Digi International, Inc."
	CONTACT-INFO
		"Digi International Tech Support

		 Phone: 877 912 3444     (US and Canada)
		 		+1 952 912 3456  (Worldwide)
		 EMail: <Tech.Support@digi.com>"
	DESCRIPTION
		"The Sarian IPsec MIB for managing the IPsec SAs on the 
		 Digi TransPort product range."
	::= { sarian 10005 }


sarian           OBJECT IDENTIFIER ::= { enterprises 16378 }
sarian-ipsec     OBJECT IDENTIFIER ::= { sarian 10005 }

ipsec-sas 					OBJECT IDENTIFIER ::= { sarian-ipsec 1 }

ipsec-sas-v1     			OBJECT IDENTIFIER ::= { ipsec-sas 1 }

ipsec-sas-v2                OBJECT IDENTIFIER ::= { ipsec-sas 2 }

--
-- IPsec V1 SAs Table
--
IPsecV1InboundSATable   OBJECT-TYPE
    SYNTAX      SEQUENCE OF V1InboundSAEntry
    MAX-ACCESS  not-accessible
    STATUS      current
    DESCRIPTION
         "A list of entries containing information on all
         IPsec V1 inbound SAs."
    ::= { ipsec-sas-v1 1 }

IPsecV1InboundSAEntry   OBJECT-TYPE
    SYNTAX      V1InboundSAEntry
    MAX-ACCESS  not-accessible
    STATUS      current
    DESCRIPTION
         "An entry containing information for a particular
         inbound IPsec V1 SA."
    INDEX { ipsecV1InboundSaEroute }
    ::= { IPsecV1InboundSATable 1 }

IPsecV1OutboundSATable   OBJECT-TYPE
    SYNTAX      SEQUENCE OF V1OutboundSAEntry
    MAX-ACCESS  not-accessible
    STATUS      current
    DESCRIPTION
         "A list of entries containing information on all
         IPsec V1 outbound SAs."
    ::= { ipsec-sas-v1 2 }

IPsecV1OutboundSAEntry   OBJECT-TYPE
    SYNTAX      V1OutboundSAEntry
    MAX-ACCESS  not-accessible
    STATUS      current
    DESCRIPTION
         "An entry containing information for a particular
         outbound IPsec V1 SA."
    INDEX { ipsecV1OutboundSaEroute }
    ::= { IPsecV1OutboundSATable 1 }

V1InboundSAEntry ::=
        SEQUENCE {
                ipsecV1InboundSaSpi          Unsigned32,
                ipsecV1InboundSaEroute       Unsigned32,
                ipsecV1InboundSaPeerId       DisplayString,
				ipsecV1InboundSaPeerIp       IpAddress,
				ipsecV1InboundSaLocalIp      IpAddress,
				ipsecV1InboundSaLocalMask    IpAddress,
				ipsecV1InboundSaRemoteIp     IpAddress,
				ipsecV1InboundSaRemoteMask   IpAddress,
                ipsecV1InboundSaTtl          Unsigned32,
                ipsecV1InboundSaKiBRemaining Unsigned32
        }

V1OutboundSAEntry ::=
        SEQUENCE {
                ipsecV1OutboundSaSpi          Unsigned32,
                ipsecV1OutboundSaEroute       Unsigned32,
                ipsecV1OutboundSaPeerId       DisplayString,
				ipsecV1OutboundSaPeerIp       IpAddress,
				ipsecV1OutboundSaLocalIp      IpAddress,
				ipsecV1OutboundSaLocalMask    IpAddress,
				ipsecV1OutboundSaRemoteIp     IpAddress,
				ipsecV1OutboundSaRemoteMask   IpAddress,
                ipsecV1OutboundSaTtl          Unsigned32,
                ipsecV1OutboundSaKiBRemaining Unsigned32
        }

--
-- V1 inbound
--

ipsecV1InboundSaSpi OBJECT-TYPE
    SYNTAX      Unsigned32
    MAX-ACCESS  read-only
    STATUS      current
    DESCRIPTION
         "The SPI of the SA."
    ::= { IPsecV1InboundSAEntry 1 }

ipsecV1InboundSaEroute OBJECT-TYPE
    SYNTAX      Unsigned32
    MAX-ACCESS  read-only
    STATUS      current
    DESCRIPTION
         "The eroute associated with the SA."
    ::= { IPsecV1InboundSAEntry 2 }

ipsecV1InboundSaPeerId OBJECT-TYPE
    SYNTAX      DisplayString
    MAX-ACCESS  read-only
    STATUS      current
    DESCRIPTION
         "The peer ID for this SA."
    ::= { IPsecV1InboundSAEntry 3 }

ipsecV1InboundSaPeerIp OBJECT-TYPE
    SYNTAX      IpAddress
    MAX-ACCESS  read-only
    STATUS      current
    DESCRIPTION
         "The Peer IP address for this SA."
    ::= { IPsecV1InboundSAEntry 4 }

ipsecV1InboundSaLocalIp OBJECT-TYPE
    SYNTAX      IpAddress
    MAX-ACCESS  read-only
    STATUS      current
    DESCRIPTION
         "The local traffic selector network address for this SA."
    ::= { IPsecV1InboundSAEntry 5 }

ipsecV1InboundSaLocalMask OBJECT-TYPE
    SYNTAX      IpAddress
    MAX-ACCESS  read-only
    STATUS      current
    DESCRIPTION
         "The local traffic selector network mask for this SA."
    ::= { IPsecV1InboundSAEntry 6 }

ipsecV1InboundSaRemoteIp OBJECT-TYPE
    SYNTAX      IpAddress
    MAX-ACCESS  read-only
    STATUS      current
    DESCRIPTION
         "The remote traffic selector network address for this SA."
    ::= { IPsecV1InboundSAEntry 7 }

ipsecV1InboundSaRemoteMask OBJECT-TYPE
    SYNTAX      IpAddress
    MAX-ACCESS  read-only
    STATUS      current
    DESCRIPTION
         "The remote traffic selector network mask for this SA."
    ::= { IPsecV1InboundSAEntry 8 }

ipsecV1InboundSaTtl OBJECT-TYPE
    SYNTAX      Unsigned32
    MAX-ACCESS  read-only
    STATUS      current
    DESCRIPTION
         "The time to live in seconds for this SA."
    ::= { IPsecV1InboundSAEntry 9 }

ipsecV1InboundSaKiBRemaining OBJECT-TYPE
    SYNTAX      Unsigned32
    MAX-ACCESS  read-only
    STATUS      current
    DESCRIPTION
         "The number of Kibibytes remaining for this SA."
    ::= { IPsecV1InboundSAEntry 10 }

--
-- V1 outbound
--

ipsecV1OutboundSaSpi OBJECT-TYPE
    SYNTAX      Unsigned32
    MAX-ACCESS  read-only
    STATUS      current
    DESCRIPTION
         "The SPI of the SA."
    ::= { IPsecV1OutboundSAEntry 1 }

ipsecV1OutboundSaEroute OBJECT-TYPE
    SYNTAX      Unsigned32
    MAX-ACCESS  read-only
    STATUS      current
    DESCRIPTION
         "The eroute associated with the SA."
    ::= { IPsecV1OutboundSAEntry 2 }

ipsecV1OutboundSaPeerId OBJECT-TYPE
    SYNTAX      DisplayString
    MAX-ACCESS  read-only
    STATUS      current
    DESCRIPTION
         "The peer ID for this SA."
    ::= { IPsecV1OutboundSAEntry 3 }

ipsecV1OutboundSaPeerIp OBJECT-TYPE
    SYNTAX      IpAddress
    MAX-ACCESS  read-only
    STATUS      current
    DESCRIPTION
         "The Peer IP address for this SA."
    ::= { IPsecV1OutboundSAEntry 4 }

ipsecV1OutboundSaLocalIp OBJECT-TYPE
    SYNTAX      IpAddress
    MAX-ACCESS  read-only
    STATUS      current
    DESCRIPTION
         "The local traffic selector network address for this SA."
    ::= { IPsecV1OutboundSAEntry 5 }

ipsecV1OutboundSaLocalMask OBJECT-TYPE
    SYNTAX      IpAddress
    MAX-ACCESS  read-only
    STATUS      current
    DESCRIPTION
         "The local traffic selector network mask for this SA."
    ::= { IPsecV1OutboundSAEntry 6 }

ipsecV1OutboundSaRemoteIp OBJECT-TYPE
    SYNTAX      IpAddress
    MAX-ACCESS  read-only
    STATUS      current
    DESCRIPTION
         "The remote traffic selector network address for this SA."
    ::= { IPsecV1OutboundSAEntry 7 }

ipsecV1OutboundSaRemoteMask OBJECT-TYPE
    SYNTAX      IpAddress
    MAX-ACCESS  read-only
    STATUS      current
    DESCRIPTION
         "The remote traffic selector network mask for this SA."
    ::= { IPsecV1OutboundSAEntry 8 }

ipsecV1OutboundSaTtl OBJECT-TYPE
    SYNTAX      Unsigned32
    MAX-ACCESS  read-only
    STATUS      current
    DESCRIPTION
         "The time to live in seconds for this SA."
    ::= { IPsecV1OutboundSAEntry 9 }

ipsecV1OutboundSaKiBRemaining OBJECT-TYPE
    SYNTAX      Unsigned32
    MAX-ACCESS  read-only
    STATUS      current
    DESCRIPTION
         "The number of Kibibytes remaining for this SA."
    ::= { IPsecV1OutboundSAEntry 10 }

--
-- IPsec V2 SAs Table
--
IPsecV2InboundSATable   OBJECT-TYPE
    SYNTAX      SEQUENCE OF V2InboundSAEntry
    MAX-ACCESS  not-accessible
    STATUS      current
    DESCRIPTION
         "A list of entries containing information on all
         IPsec V2 inbound SAs."
    ::= { ipsec-sas-v2 1 }

IPsecV2InboundSAEntry   OBJECT-TYPE
    SYNTAX      V2InboundSAEntry
    MAX-ACCESS  not-accessible
    STATUS      current
    DESCRIPTION
         "An entry containing information for a particular
         inbound IPsec V2 SA."
    INDEX { ipsecV2InboundSaEroute }
    ::= { IPsecV2InboundSATable 1 }

IPsecV2OutboundSATable   OBJECT-TYPE
    SYNTAX      SEQUENCE OF V2OutboundSAEntry
    MAX-ACCESS  not-accessible
    STATUS      current
    DESCRIPTION
         "A list of entries containing information on all
         IPsec V2 inbound SAs."
    ::= { ipsec-sas-v2 2 }

IPsecV2OutboundSAEntry   OBJECT-TYPE
    SYNTAX      V2OutboundSAEntry
    MAX-ACCESS  not-accessible
    STATUS      current
    DESCRIPTION
         "An entry containing information for a particular
         outbound IPsec V2 SA."
    INDEX { ipsecV2OutboundSaEroute }
    ::= { IPsecV2OutboundSATable 1 }

V2InboundSAEntry ::=
        SEQUENCE {
                ipsecV2InboundSaSpi           Unsigned32,
                ipsecV2InboundSaEroute        Unsigned32,
                ipsecV2InboundSaPeerId        DisplayString,
				ipsecV2InboundSaPeerIp        IpAddress,
				ipsecV2InboundSaFirstLocalIp  IpAddress,
				ipsecV2InboundSaLastLocalIp   IpAddress,
				ipsecV2InboundSaFirstRemoteIp IpAddress,
				ipsecV2InboundSaLastRemoteIp  IpAddress,
                ipsecV2InboundSaTtl           Unsigned32,
                ipsecV2InboundSaKiBRemaining  Unsigned32
        }

V2OutboundSAEntry ::=
        SEQUENCE {
                ipsecV2OutboundSaSpi           Unsigned32,
                ipsecV2OutboundSaEroute        Unsigned32,
                ipsecV2OutboundSaPeerId        DisplayString,
				ipsecV2OutboundSaPeerIp        IpAddress,
				ipsecV2OutboundSaFirstLocalIp  IpAddress,
				ipsecV2OutboundSaLastLocalIp   IpAddress,
				ipsecV2OutboundSaFirstRemoteIp IpAddress,
				ipsecV2OutboundSaLastRemoteIp  IpAddress,
                ipsecV2OutboundSaTtl           Unsigned32,
                ipsecV2OutboundSaKiBRemaining  Unsigned32
        }

--
-- V2 inbound
--

ipsecV2InboundSaSpi OBJECT-TYPE
    SYNTAX      Unsigned32
    MAX-ACCESS  read-only
    STATUS      current
    DESCRIPTION
         "The SPI of the SA."
    ::= { IPsecV2InboundSAEntry 1 }

ipsecV2InboundSaEroute OBJECT-TYPE
    SYNTAX      Unsigned32
    MAX-ACCESS  read-only
    STATUS      current
    DESCRIPTION
         "The eroute associated with the SA."
    ::= { IPsecV2InboundSAEntry 2 }

ipsecV2InboundSaPeerId OBJECT-TYPE
    SYNTAX      DisplayString
    MAX-ACCESS  read-only
    STATUS      current
    DESCRIPTION
         "The peer ID for this SA."
    ::= { IPsecV2InboundSAEntry 3 }

ipsecV2InboundSaPeerIp OBJECT-TYPE
    SYNTAX      IpAddress
    MAX-ACCESS  read-only
    STATUS      current
    DESCRIPTION
         "The Peer IP address for this SA."
    ::= { IPsecV2InboundSAEntry 4 }

ipsecV2InboundSaFirstLocalIp OBJECT-TYPE
    SYNTAX      IpAddress
    MAX-ACCESS  read-only
    STATUS      current
    DESCRIPTION
         "The local traffic selector first network address for this SA."
    ::= { IPsecV2InboundSAEntry 5 }

ipsecV2InboundSaLastLocalIp OBJECT-TYPE
    SYNTAX      IpAddress
    MAX-ACCESS  read-only
    STATUS      current
    DESCRIPTION
         "The local traffic selector last network address for this SA."
    ::= { IPsecV2InboundSAEntry 6 }

ipsecV2InboundSaFirstRemoteIp OBJECT-TYPE
    SYNTAX      IpAddress
    MAX-ACCESS  read-only
    STATUS      current
    DESCRIPTION
         "The remote traffic selector first network address for this SA."
    ::= { IPsecV2InboundSAEntry 7 }

ipsecV2InboundSaLastRemote OBJECT-TYPE
    SYNTAX      IpAddress
    MAX-ACCESS  read-only
    STATUS      current
    DESCRIPTION
         "The remote traffic selector last network address for this SA."
    ::= { IPsecV2InboundSAEntry 8 }

ipsecV2InboundSaTtl OBJECT-TYPE
    SYNTAX      Unsigned32
    MAX-ACCESS  read-only
    STATUS      current
    DESCRIPTION
         "The time to live in seconds for this SA."
    ::= { IPsecV2InboundSAEntry 9 }

ipsecV2InboundSaKiBRemaining OBJECT-TYPE
    SYNTAX      Unsigned32
    MAX-ACCESS  read-only
    STATUS      current
    DESCRIPTION
         "The number of Kibibytes remaining for this SA."
    ::= { IPsecV2InboundSAEntry 10 }

--
-- V2 Outbound
--

ipsecV2OutboundSaSpi OBJECT-TYPE
    SYNTAX      Unsigned32
    MAX-ACCESS  read-only
    STATUS      current
    DESCRIPTION
         "The SPI of the SA."
    ::= { IPsecV2OutboundSAEntry 1 }

ipsecV2OutboundSaEroute OBJECT-TYPE
    SYNTAX      Unsigned32
    MAX-ACCESS  read-only
    STATUS      current
    DESCRIPTION
         "The eroute associated with the SA."
    ::= { IPsecV2OutboundSAEntry 2 }

ipsecV2OutboundSaPeerId OBJECT-TYPE
    SYNTAX      DisplayString
    MAX-ACCESS  read-only
    STATUS      current
    DESCRIPTION
         "The peer ID for this SA."
    ::= { IPsecV2OutboundSAEntry 3 }

ipsecV2OutboundSaPeerIp OBJECT-TYPE
    SYNTAX      IpAddress
    MAX-ACCESS  read-only
    STATUS      current
    DESCRIPTION
         "The Peer IP address for this SA."
    ::= { IPsecV2OutboundSAEntry 4 }

ipsecV2OutboundSaFirstLocalIp OBJECT-TYPE
    SYNTAX      IpAddress
    MAX-ACCESS  read-only
    STATUS      current
    DESCRIPTION
         "The local traffic selector first network address for this SA."
    ::= { IPsecV2OutboundSAEntry 5 }

ipsecV2OutboundSaLastLocalIp OBJECT-TYPE
    SYNTAX      IpAddress
    MAX-ACCESS  read-only
    STATUS      current
    DESCRIPTION
         "The local traffic selector last network address for this SA."
    ::= { IPsecV2OutboundSAEntry 6 }

ipsecV2OutboundSaRemoteIp OBJECT-TYPE
    SYNTAX      IpAddress
    MAX-ACCESS  read-only
    STATUS      current
    DESCRIPTION
         "The remote traffic selector first network address for this SA."
    ::= { IPsecV2OutboundSAEntry 7 }

ipsecV2OutboundSaRemoteMask OBJECT-TYPE
    SYNTAX      IpAddress
    MAX-ACCESS  read-only
    STATUS      current
    DESCRIPTION
         "The remote traffic selector last network address for this SA."
    ::= { IPsecV2OutboundSAEntry 8 }

ipsecV2OutboundSaTtl OBJECT-TYPE
    SYNTAX      Unsigned32
    MAX-ACCESS  read-only
    STATUS      current
    DESCRIPTION
         "The time to live in seconds for this SA."
    ::= { IPsecV2OutboundSAEntry 9 }

ipsecV2OutboundSaKiBRemaining OBJECT-TYPE
    SYNTAX      Unsigned32
    MAX-ACCESS  read-only
    STATUS      current
    DESCRIPTION
         "The number of Kibibytes remaining for this SA."
    ::= { IPsecV2OutboundSAEntry 10 }

END
