-- ################################################################################

ETMONSERVICEABILITYTRAP-MIB DEFINITIONS ::= BEGIN

    IMPORTS
        MODULE-IDENTITY      FROM SNMPv2-SMI
        OBJECT-TYPE          FROM SNMPv2-SMI
        NOTIFICATION-TYPE    FROM SNMPv2-SMI
        extremeV2Traps       FROM EXTREME-BASE-MIB
        sysDescr             FROM RFC1213-MIB
        sysUpTime            FROM RFC1213-MIB
        DisplayString        FROM RFC1213-MIB;

    --  Organization & Product branches

    etmonServiceabilityTrap MODULE-IDENTITY
        LAST-UPDATED "202001021400Z"  -- Thu Jan 02 14:00 UTC 2020
        ORGANIZATION "Extreme Networks, Inc."
        CONTACT-INFO "support@extremenetworks.com"
        DESCRIPTION  "Extreme Serviceability TRAP MIB"
        ::= { extremeV2Traps 15}

    etmonServiceabilityTrapPrefix   OBJECT IDENTIFIER
        ::= { etmonServiceabilityTrap 0}

    noMoreMemory    NOTIFICATION-TYPE
        OBJECTS {
            sysUpTime,
            sysDescr
        }
        STATUS      current
        DESCRIPTION
            "Memory full, No more momory. System memory is depleted."
        ::= {etmonServiceabilityTrapPrefix 1 }

    asyncQGrowing       NOTIFICATION-TYPE
        OBJECTS {
            sysUpTime,
            sysDescr
        }
        STATUS      current
        DESCRIPTION
            "async queue is growing. Logged messages will provide more
            information related to growing async queue.
            MIB have limitation to provide real-time information."
        ::= {etmonServiceabilityTrapPrefix 2 }
END
