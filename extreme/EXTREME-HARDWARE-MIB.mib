-- ################################################################################

EXTREME-HARDWARE-MIB DEFINITIONS ::= BEGIN

    IMPORTS
    MODULE-IDENTITY FROM SNMPv2-SMI
    OBJECT-IDENTITY FROM SNMPv2-SMI
    extremenetworks   FROM EXTREME-BASE-MIB;

    extremeHardware MODULE-IDENTITY
        LAST-UPDATED "202001072243Z"  -- Tue Jan 07 22:43:00 UTC 2020

        ORGANIZATION "Extreme Networks, Inc."
        CONTACT-INFO "www.extremenetworks.com"
        DESCRIPTION  "Extreme hardware OIDs.  These OIDs are used to identify
                      Extreme hardware entities in the entityMIB.  Specifically,
                      these OIDs are used for the entPysicalVendorType column
                      in the entPhysicalTable."

        REVISION    "202001072243Z"  -- Tue Jan 07 22:43:00 UTC 2020
        DESCRIPTION "Add the following OIDs:
                     extremeV3008p2x, extremeV3008t2x, 
                     extremeV300ht8p2x, extremeV300ht8t2x."

        REVISION    "201911202014Z"  -- Wed Nov 20 20:14:00 UTC 2019
        DESCRIPTION "Add X695-48Y-8C hardware OID"

        REVISION    "201909042120Z"  -- Wed Sep 4 21:20:00 UTC 2019
        DESCRIPTION "Add X465-24XE, X465-24S and X465i-48W hardware OIDs"

        REVISION     "201908011714Z"  --  Thurs Aug 01 17:14 UTC 2019
        DESCRIPTION  "Initial list of Extreme hardware OIDs"

    ::= { extremenetworks 5 }

    extremeG8x OBJECT-IDENTITY
        STATUS      current
    --  Name        "G8X"
    --  Date        "201807111626Z"  - Tues July 11 16:26 UTC 2018
        DESCRIPTION "Extreme G8X"
    ::= { extremeHardware 1 }

    extremeMsmG8x OBJECT-IDENTITY
        STATUS      current
    --  Name        "MSM-G8X"
    --  Date        "201807111626Z"  - Tues July 11 16:26 UTC 2018
        DESCRIPTION "Extreme MSM-G8X"
    ::= { extremeHardware 2 }

    extremeG48t OBJECT-IDENTITY
        STATUS      current
    --  Name        "G48T"
    --  Date        "201807111626Z"  - Tues July 11 16:26 UTC 2018
        DESCRIPTION "Extreme G48T"
    ::= { extremeHardware 3 }

    extremeG48p OBJECT-IDENTITY
        STATUS      current
    --  Name        "G48P"
    --  Date        "201807111626Z"  - Tues July 11 16:26 UTC 2018
        DESCRIPTION "Extreme G48P"
    ::= { extremeHardware 4 }

    extremeG24x OBJECT-IDENTITY
        STATUS      current
    --  Name        "G24X"
    --  Date        "201807111626Z"  - Tues July 11 16:26 UTC 2018
        DESCRIPTION "Extreme G24X"
    ::= { extremeHardware 5 }

    extreme10g4x OBJECT-IDENTITY
        STATUS      current
    --  Name        "10G4X"
    --  Date        "201807111626Z"  - Tues July 11 16:26 UTC 2018
        DESCRIPTION "Extreme 10G4X"
    ::= { extremeHardware 6 }

    extremeG48te OBJECT-IDENTITY
        STATUS      current
    --  Name        "G48Te"
    --  Date        "201807111626Z"  - Tues July 11 16:26 UTC 2018
        DESCRIPTION "Extreme G48Te"
    ::= { extremeHardware 7 }

    extremeG48pe OBJECT-IDENTITY
        STATUS      current
    --  Name        "G48Pe"
    --  Date        "201807111626Z"  - Tues July 11 16:26 UTC 2018
        DESCRIPTION "Extreme G48Pe"
    ::= { extremeHardware 8 }

    extremeG48ta OBJECT-IDENTITY
        STATUS      current
    --  Name        "G48Ta"
    --  Date        "201807111626Z"  - Tues July 11 16:26 UTC 2018
        DESCRIPTION "Extreme G48Ta"
    ::= { extremeHardware 9 }

    extremeG48pa OBJECT-IDENTITY
        STATUS      current
    --  Name        "G48Pa"
    --  Date        "201807111626Z"  - Tues July 11 16:26 UTC 2018
        DESCRIPTION "Extreme G48Pa"
    ::= { extremeHardware 10 }

    extremeG48xa OBJECT-IDENTITY
        STATUS      current
    --  Name        "G48Xa"
    --  Date        "201807111626Z"  - Tues July 11 16:26 UTC 2018
        DESCRIPTION "Extreme G48Xa"
    ::= { extremeHardware 11 }

    extremeMsm48 OBJECT-IDENTITY
        STATUS      current
    --  Name        "MSM-48"
    --  Date        "201807111626Z"  - Tues July 11 16:26 UTC 2018
        DESCRIPTION "Extreme MSM-48"
    ::= { extremeHardware 12 }

    extreme10g4ca OBJECT-IDENTITY
        STATUS      current
    --  Name        "10G4Ca"
    --  Date        "201807111626Z"  - Tues July 11 16:26 UTC 2018
        DESCRIPTION "Extreme 10G4Ca"
    ::= { extremeHardware 13 }

    extreme10g4xa OBJECT-IDENTITY
        STATUS      current
    --  Name        "10G4Xa"
    --  Date        "201807111626Z"  - Tues July 11 16:26 UTC 2018
        DESCRIPTION "Extreme 10G4Xa"
    ::= { extremeHardware 14 }

    extremeG48tc OBJECT-IDENTITY
        STATUS      current
    --  Name        "G48Tc"
    --  Date        "201807111626Z"  - Tues July 11 16:26 UTC 2018
        DESCRIPTION "Extreme G48Tc"
    ::= { extremeHardware 15 }

    extremeG48te2 OBJECT-IDENTITY
        STATUS      current
    --  Name        "G48Te2"
    --  Date        "201807111626Z"  - Tues July 11 16:26 UTC 2018
        DESCRIPTION "Extreme G48Te2"
    ::= { extremeHardware 16 }

    extremeG48tcPoe OBJECT-IDENTITY
        STATUS      current
    --  Name        "G48Tc(PoE)"
    --  Date        "201807111626Z"  - Tues July 11 16:26 UTC 2018
        DESCRIPTION "Extreme G48Tc(PoE)"
    ::= { extremeHardware 17 }

    extremeG48te2Poe OBJECT-IDENTITY
        STATUS      current
    --  Name        "G48Te2(PoE)"
    --  Date        "201807111626Z"  - Tues July 11 16:26 UTC 2018
        DESCRIPTION "Extreme G48Te2(PoE)"
    ::= { extremeHardware 18 }

    extremeG48xc OBJECT-IDENTITY
        STATUS      current
    --  Name        "G48Xc"
    --  Date        "201807111626Z"  - Tues July 11 16:26 UTC 2018
        DESCRIPTION "Extreme G48Xc"
    ::= { extremeHardware 19 }

    extremeG24xc OBJECT-IDENTITY
        STATUS      current
    --  Name        "G24Xc"
    --  Date        "201807111626Z"  - Tues July 11 16:26 UTC 2018
        DESCRIPTION "Extreme G24Xc"
    ::= { extremeHardware 20 }

    extreme10g8xc OBJECT-IDENTITY
        STATUS      current
    --  Name        "10G8Xc"
    --  Date        "201807111626Z"  - Tues July 11 16:26 UTC 2018
        DESCRIPTION "Extreme 10G8Xc"
    ::= { extremeHardware 21 }

    extreme10g4xc OBJECT-IDENTITY
        STATUS      current
    --  Name        "10G4Xc"
    --  Date        "201807111626Z"  - Tues July 11 16:26 UTC 2018
        DESCRIPTION "Extreme 10G4Xc"
    ::= { extremeHardware 22 }

    extremeMsm48c OBJECT-IDENTITY
        STATUS      current
    --  Name        "MSM-48c"
    --  Date        "201807111626Z"  - Tues July 11 16:26 UTC 2018
        DESCRIPTION "Extreme MSM-48c"
    ::= { extremeHardware 23 }

    extremeG8xc OBJECT-IDENTITY
        STATUS      current
    --  Name        "G8Xc"
    --  Date        "201807111626Z"  - Tues July 11 16:26 UTC 2018
        DESCRIPTION "Extreme G8Xc"
    ::= { extremeHardware 24 }

    extreme10g1xc OBJECT-IDENTITY
        STATUS      current
    --  Name        "10G1Xc"
    --  Date        "201807111626Z"  - Tues July 11 16:26 UTC 2018
        DESCRIPTION "Extreme 10G1Xc"
    ::= { extremeHardware 25 }

    extreme8900Msm128 OBJECT-IDENTITY
        STATUS      current
    --  Name        "8900-MSM128"
    --  Date        "201807111626Z"  - Tues July 11 16:26 UTC 2018
        DESCRIPTION "Extreme 8900-MSM128"
    ::= { extremeHardware 26 }

    extreme890010g24xC OBJECT-IDENTITY
        STATUS      current
    --  Name        "8900-10G24X-c"
    --  Date        "201807111626Z"  - Tues July 11 16:26 UTC 2018
        DESCRIPTION "Extreme 8900-10G24X-c"
    ::= { extremeHardware 27 }

    extreme890010g8xXl OBJECT-IDENTITY
        STATUS      current
    --  Name        "8900-10G8X-xl"
    --  Date        "201807111626Z"  - Tues July 11 16:26 UTC 2018
        DESCRIPTION "Extreme 8900-10G8X-xl"
    ::= { extremeHardware 28 }

    extreme8900G48tXl OBJECT-IDENTITY
        STATUS      current
    --  Name        "8900-G48T-xl"
    --  Date        "201807111626Z"  - Tues July 11 16:26 UTC 2018
        DESCRIPTION "Extreme 8900-G48T-xl"
    ::= { extremeHardware 29 }

    extreme8900G48xXl OBJECT-IDENTITY
        STATUS      current
    --  Name        "8900-G48X-xl"
    --  Date        "201807111626Z"  - Tues July 11 16:26 UTC 2018
        DESCRIPTION "Extreme 8900-G48X-xl"
    ::= { extremeHardware 30 }

    extreme8900G96tC OBJECT-IDENTITY
        STATUS      current
    --  Name        "8900-G96T-c"
    --  Date        "201807111626Z"  - Tues July 11 16:26 UTC 2018
        DESCRIPTION "Extreme 8900-G96T-c"
    ::= { extremeHardware 31 }

    extreme8900G48tXlP OBJECT-IDENTITY
        STATUS      current
    --  Name        "8900-G48T-xl(P)"
    --  Date        "201807111626Z"  - Tues July 11 16:26 UTC 2018
        DESCRIPTION "Extreme 8900-G48T-xl(P)"
    ::= { extremeHardware 32 }

    extreme8500Msm24 OBJECT-IDENTITY
        STATUS      current
    --  Name        "8500-MSM24"
    --  Date        "201807111626Z"  - Tues July 11 16:26 UTC 2018
        DESCRIPTION "Extreme 8500-MSM24"
    ::= { extremeHardware 33 }

    extreme8500G24xE OBJECT-IDENTITY
        STATUS      current
    --  Name        "8500-G24X-e"
    --  Date        "201807111626Z"  - Tues July 11 16:26 UTC 2018
        DESCRIPTION "Extreme 8500-G24X-e"
    ::= { extremeHardware 34 }

    extreme8500G48tE OBJECT-IDENTITY
        STATUS      current
    --  Name        "8500-G48T-e"
    --  Date        "201807111626Z"  - Tues July 11 16:26 UTC 2018
        DESCRIPTION "Extreme 8500-G48T-e"
    ::= { extremeHardware 35 }

    extreme8500G48tEP OBJECT-IDENTITY
        STATUS      current
    --  Name        "8500-G48T-e(P)"
    --  Date        "201807111626Z"  - Tues July 11 16:26 UTC 2018
        DESCRIPTION "Extreme 8500-G48T-e(P)"
    ::= { extremeHardware 36 }

    extreme10g2xc OBJECT-IDENTITY
        STATUS      current
    --  Name        "10G2Xc"
    --  Date        "201807111626Z"  - Tues July 11 16:26 UTC 2018
        DESCRIPTION "Extreme 10G2Xc"
    ::= { extremeHardware 37 }

    extreme890040g6xXm OBJECT-IDENTITY
        STATUS      current
    --  Name        "8900-40G6X-xm"
    --  Date        "201807111626Z"  - Tues July 11 16:26 UTC 2018
        DESCRIPTION "Extreme 8900-40G6X-xm"
    ::= { extremeHardware 38 }

    extreme8900Msm96 OBJECT-IDENTITY
        STATUS      current
    --  Name        "8900-MSM96"
    --  Date        "201807111626Z"  - Tues July 11 16:26 UTC 2018
        DESCRIPTION "Extreme 8900-MSM96"
    ::= { extremeHardware 39 }

    extremeBdxMm1 OBJECT-IDENTITY
        STATUS      current
    --  Name        "BDX-MM1"
    --  Date        "201807111626Z"  - Tues July 11 16:26 UTC 2018
        DESCRIPTION "Extreme BDX-MM1"
    ::= { extremeHardware 40 }

    extremeBdxa10g48x OBJECT-IDENTITY
        STATUS      current
    --  Name        "BDXA-10G48X"
    --  Date        "201807111626Z"  - Tues July 11 16:26 UTC 2018
        DESCRIPTION "Extreme BDXA-10G48X"
    ::= { extremeHardware 41 }

    extremeBdxa10g48x0 OBJECT-IDENTITY
        STATUS      current
    --  Name        "BDXA-10G48X-0"
    --  Date        "201807111626Z"  - Tues July 11 16:26 UTC 2018
        DESCRIPTION "Extreme BDXA-10G48X-0"
    ::= { extremeHardware 42 }

    extremeBdxa10g24x OBJECT-IDENTITY
        STATUS      current
    --  Name        "BDXA-10G24X"
    --  Date        "201807111626Z"  - Tues July 11 16:26 UTC 2018
        DESCRIPTION "Extreme BDXA-10G24X"
    ::= { extremeHardware 43 }

    extremeBdxa40g24x OBJECT-IDENTITY
        STATUS      current
    --  Name        "BDXA-40G24X"
    --  Date        "201807111626Z"  - Tues July 11 16:26 UTC 2018
        DESCRIPTION "Extreme BDXA-40G24X"
    ::= { extremeHardware 44 }

    extremeBdxa40g12x OBJECT-IDENTITY
        STATUS      current
    --  Name        "BDXA-40G12X"
    --  Date        "201807111626Z"  - Tues July 11 16:26 UTC 2018
        DESCRIPTION "Extreme BDXA-40G12X"
    ::= { extremeHardware 45 }

    extremeBdxaFm20t OBJECT-IDENTITY
        STATUS      current
    --  Name        "BDXA-FM20T"
    --  Date        "201807111626Z"  - Tues July 11 16:26 UTC 2018
        DESCRIPTION "Extreme BDXA-FM20T"
    ::= { extremeHardware 46 }

    extremeBdxaFm10t OBJECT-IDENTITY
        STATUS      current
    --  Name        "BDXA-FM10T"
    --  Date        "201807111626Z"  - Tues July 11 16:26 UTC 2018
        DESCRIPTION "Extreme BDXA-FM10T"
    ::= { extremeHardware 47 }

    extremeBdxa10g48t OBJECT-IDENTITY
        STATUS      current
    --  Name        "BDXA-10G48T"
    --  Date        "201807111626Z"  - Tues July 11 16:26 UTC 2018
        DESCRIPTION "Extreme BDXA-10G48T"
    ::= { extremeHardware 48 }

    extremeBdxb40g12xXl OBJECT-IDENTITY
        STATUS      current
    --  Name        "BDXB-40G12X-XL"
    --  Date        "201807111626Z"  - Tues July 11 16:26 UTC 2018
        DESCRIPTION "Extreme BDXB-40G12X-XL"
    ::= { extremeHardware 49 }

    extremeBdxb100g4xXl OBJECT-IDENTITY
        STATUS      current
    --  Name        "BDXB-100G4X-XL"
    --  Date        "201807111626Z"  - Tues July 11 16:26 UTC 2018
        DESCRIPTION "Extreme BDXB-100G4X-XL"
    ::= { extremeHardware 50 }

    extremeBdxb100g4x OBJECT-IDENTITY
        STATUS      current
    --  Name        "BDXB-100G4X"
    --  Date        "201807111626Z"  - Tues July 11 16:26 UTC 2018
        DESCRIPTION "Extreme BDXB-100G4X"
    ::= { extremeHardware 51 }

    extremeBdxaG48t OBJECT-IDENTITY
        STATUS      current
    --  Name        "BDXA-G48T"
    --  Date        "201807111626Z"  - Tues July 11 16:26 UTC 2018
        DESCRIPTION "Extreme BDXA-G48T"
    ::= { extremeHardware 52 }

    extremeBdxaG48x OBJECT-IDENTITY
        STATUS      current
    --  Name        "BDXA-G48X"
    --  Date        "201807111626Z"  - Tues July 11 16:26 UTC 2018
        DESCRIPTION "Extreme BDXA-G48X"
    ::= { extremeHardware 53 }

    extremeBdxaG48x0 OBJECT-IDENTITY
        STATUS      current
    --  Name        "BDXA-G48X-0"
    --  Date        "201807111626Z"  - Tues July 11 16:26 UTC 2018
        DESCRIPTION "Extreme BDXA-G48X-0"
    ::= { extremeHardware 54 }

    extremeXcm OBJECT-IDENTITY
        STATUS      current
    --  Name        "XCM"
    --  Date        "201807111626Z"  - Tues July 11 16:26 UTC 2018
        DESCRIPTION "Extreme XCM"
    ::= { extremeHardware 55 }

    extremeXcm88s1 OBJECT-IDENTITY
        STATUS      current
    --  Name        "XCM88S1"
    --  Date        "201807111626Z"  - Tues July 11 16:26 UTC 2018
        DESCRIPTION "Extreme XCM88S1"
    ::= { extremeHardware 56 }

    extremeXcm8848t OBJECT-IDENTITY
        STATUS      current
    --  Name        "XCM8848T"
    --  Date        "201807111626Z"  - Tues July 11 16:26 UTC 2018
        DESCRIPTION "Extreme XCM8848T"
    ::= { extremeHardware 57 }

    extremeXcm8848tP OBJECT-IDENTITY
        STATUS      current
    --  Name        "XCM8848T(P)"
    --  Date        "201807111626Z"  - Tues July 11 16:26 UTC 2018
        DESCRIPTION "Extreme XCM8848T(P)"
    ::= { extremeHardware 58 }

    extremeXcm8824f OBJECT-IDENTITY
        STATUS      current
    --  Name        "XCM8824F"
    --  Date        "201807111626Z"  - Tues July 11 16:26 UTC 2018
        DESCRIPTION "Extreme XCM8824F"
    ::= { extremeHardware 59 }

    extremeXcm8808x OBJECT-IDENTITY
        STATUS      current
    --  Name        "XCM8808X"
    --  Date        "201807111626Z"  - Tues July 11 16:26 UTC 2018
        DESCRIPTION "Extreme XCM8808X"
    ::= { extremeHardware 60 }

    extremeXcm888f OBJECT-IDENTITY
        STATUS      current
    --  Name        "XCM888F"
    --  Date        "201807111626Z"  - Tues July 11 16:26 UTC 2018
        DESCRIPTION "Extreme XCM888F"
    ::= { extremeHardware 61 }

    extremeX77032q OBJECT-IDENTITY
        STATUS      current
    --  Name        "X770-32q"
    --  Date        "201807111626Z"  - Tues July 11 16:26 UTC 2018
        DESCRIPTION "Extreme Summit X770-32q: 32 QSFP+"
    ::= { extremeHardware 62 }

    extremeX670g248x4q OBJECT-IDENTITY
        STATUS      current
    --  Name        "X670G2-48x-4q"
    --  Date        "201807111626Z"  - Tues July 11 16:26 UTC 2018
        DESCRIPTION "Extreme Summit X670-G2-48x-4q: 48 SFP+, 4 QSFP+"
    ::= { extremeHardware 63 }

    extremeX670g272x OBJECT-IDENTITY
        STATUS      current
    --  Name        "X670G2-72x"
    --  Date        "201807111626Z"  - Tues July 11 16:26 UTC 2018
        DESCRIPTION "Extreme Summit X670-G2-72x: 72 SFP+"
    ::= { extremeHardware 64 }

    extremeX460g224t10g4 OBJECT-IDENTITY
        STATUS      current
    --  Name        "X460G2-24t-10G4"
    --  Date        "201807111626Z"  - Tues July 11 16:26 UTC 2018
        DESCRIPTION "Extreme Summit X460-G2-24t-10GE4: 24 BaseT, 8 SFP (4 Combo), 4 SFP+, 1 VIM slot, 1 Clock slot"
    ::= { extremeHardware 65 }

    extremeX460g224p10g4 OBJECT-IDENTITY
        STATUS      current
    --  Name        "X460G2-24p-10G4"
    --  Date        "201807111626Z"  - Tues July 11 16:26 UTC 2018
        DESCRIPTION "Extreme Summit X460-G2-24p-10GE4: 24 BaseT (PoE+), 8 SFP (4 Combo), 4 SFP+, 1 VIM slot, 1 Clock slot"
    ::= { extremeHardware 66 }

    extremeX460g224x10g4 OBJECT-IDENTITY
        STATUS      current
    --  Name        "X460G2-24x-10G4"
    --  Date        "201807111626Z"  - Tues July 11 16:26 UTC 2018
        DESCRIPTION "Extreme Summit X460-G2-24x-10GE4: 24 SFP, 8 BaseT (4 Combo), 4 SFP+, 1 VIM slot, 1 Clock slot"
    ::= { extremeHardware 67 }

    extremeX460g248t10g4 OBJECT-IDENTITY
        STATUS      current
    --  Name        "X460G2-48t-10G4"
    --  Date        "201807111626Z"  - Tues July 11 16:26 UTC 2018
        DESCRIPTION "Extreme Summit X460-G2-48t-10GE4: 48 BaseT, 4 SFP+, 1 VIM slot, 1 Clock slot"
    ::= { extremeHardware 68 }

    extremeX460g248p10g4 OBJECT-IDENTITY
        STATUS      current
    --  Name        "X460G2-48p-10G4"
    --  Date        "201807111626Z"  - Tues July 11 16:26 UTC 2018
        DESCRIPTION "Extreme Summit X460-G2-48p-10GE4:  48 BaseT (PoE+), 4 SFP+, 1 VIM slot, 1 Clock slot"
    ::= { extremeHardware 69 }

    extremeX460g224p24hp OBJECT-IDENTITY
        STATUS      current
    --  Name        "X460G2-24p-24hp"
    --  Date        "201807111626Z"  - Tues July 11 16:26 UTC 2018
        DESCRIPTION "Extreme Summit X460-G2-24p-24hp-10GE4-Base:  24 BaseT(PoE+), 24 BaseT(PoE+) Half Duplex , 4 SFP+, 1 VIM slot, 1 Clock slot"
    ::= { extremeHardware 70 }

    extremeX460g224t24ht OBJECT-IDENTITY
        STATUS      current
    --  Name        "X460G2-24t-24ht"
    --  Date        "201807111626Z"  - Tues July 11 16:26 UTC 2018
        DESCRIPTION "Extreme Summit X460-G2-24t-24ht-10GE4-Base: 24 BaseT, 24 BaseT Half Duplex, 4 SFP+, 1 VIM slot, 1 Clock slot"
    ::= { extremeHardware 71 }

    extremeX460g248x10g4 OBJECT-IDENTITY
        STATUS      current
    --  Name        "X460G2-48x-10G4"
    --  Date        "201807111626Z"  - Tues July 11 16:26 UTC 2018
        DESCRIPTION "Extreme Summit X460-G2-48x-10GE4: 48 SFP, 4 SFP+, 1 VIM slot, 1 Clock slot"
    ::= { extremeHardware 72 }

    extremeX460g224tG4 OBJECT-IDENTITY
        STATUS      current
    --  Name        "X460G2-24t-G4"
    --  Date        "201807111626Z"  - Tues July 11 16:26 UTC 2018
        DESCRIPTION "Extreme Summit X460-G2-24t-GE4: 24 BaseT, 8 SFP (4 Combo), 4 SFP, 1 VIM slot, 1 Clock slot"
    ::= { extremeHardware 73 }

    extremeX460g224pG4 OBJECT-IDENTITY
        STATUS      current
    --  Name        "X460G2-24p-G4"
    --  Date        "201807111626Z"  - Tues July 11 16:26 UTC 2018
        DESCRIPTION "Extreme Summit X460-G2-24p-GE4: 24 BaseT (PoE+), 8 SFP (4 Combo), 4 SFP, 1 VIM slot, 1 Clock slot"
    ::= { extremeHardware 74 }

    extremeX460g248tG4 OBJECT-IDENTITY
        STATUS      current
    --  Name        "X460G2-48t-G4"
    --  Date        "201807111626Z"  - Tues July 11 16:26 UTC 2018
        DESCRIPTION "Extreme Summit X460-G2-48t-GE4: 48 BaseT, 4 SFP, 1 VIM slot, 1 Clock slot"
    ::= { extremeHardware 75 }

    extremeX460g248pG4 OBJECT-IDENTITY
        STATUS      current
    --  Name        "X460G2-48p-G4"
    --  Date        "201807111626Z"  - Tues July 11 16:26 UTC 2018
        DESCRIPTION "Extreme Summit X460-G2-48p-GE4:  48 BaseT (PoE+), 4 SFP, 1 VIM slot, 1 Clock slot"
    ::= { extremeHardware 76 }

    extremeX460g216mp32p OBJECT-IDENTITY
        STATUS      current
    --  Name        "X460G2-16mp-32p"
    --  Date        "201807111626Z"  - Tues July 11 16:26 UTC 2018
        DESCRIPTION "Extreme Summit X460-G2-16mp-32p-10GE4: 16 100Mb/1.0/2.5GbE (PoE+), 32 10/100/1000BASE-T (PoE+), 4 1000/10GBaseX SFP+, 1 VIM slot, 1 Clock slot"
    ::= { extremeHardware 77 }

    extremeX450g224t10g4 OBJECT-IDENTITY
        STATUS      current
    --  Name        "X450G2-24t-10G4"
    --  Date        "201807111626Z"  - Tues July 11 16:26 UTC 2018
        DESCRIPTION "Extreme Summit X450-G2-24t-10GE4: 24 BaseT, 4 SFP+, 2 HG[21] (Stack only)"
    ::= { extremeHardware 78 }

    extremeX450g224p10g4 OBJECT-IDENTITY
        STATUS      current
    --  Name        "X450G2-24p-10G4"
    --  Date        "201807111626Z"  - Tues July 11 16:26 UTC 2018
        DESCRIPTION "Extreme Summit X450-G2-24p-10GE4: 24 BaseT (PoE+), 4 SFP+, 2 HG[21] (Stack only)"
    ::= { extremeHardware 79 }

    extremeX450g248t10g4 OBJECT-IDENTITY
        STATUS      current
    --  Name        "X450G2-48t-10G4"
    --  Date        "201807111626Z"  - Tues July 11 16:26 UTC 2018
        DESCRIPTION "Extreme Summit X450-G2-48t-10GE4: 48 BaseT, 4 SFP+, 2 HG[21] (Stack only)"
    ::= { extremeHardware 80 }

    extremeX450g248p10g4 OBJECT-IDENTITY
        STATUS      current
    --  Name        "X450G2-48p-10G4"
    --  Date        "201807111626Z"  - Tues July 11 16:26 UTC 2018
        DESCRIPTION "Extreme Summit X450-G2-48p-10GE4: 48 BaseT (PoE+), 4 SFP+, 2 HG[21] (Stack only)"
    ::= { extremeHardware 81 }

    extremeX450g224tG4 OBJECT-IDENTITY
        STATUS      current
    --  Name        "X450G2-24t-G4"
    --  Date        "201807111626Z"  - Tues July 11 16:26 UTC 2018
        DESCRIPTION "Extreme Summit X450-G2-24t-GE4: 24 BaseT, 4 SFP, 2 HG[21] (Stack only)"
    ::= { extremeHardware 82 }

    extremeX450g224pG4 OBJECT-IDENTITY
        STATUS      current
    --  Name        "X450G2-24p-G4"
    --  Date        "201807111626Z"  - Tues July 11 16:26 UTC 2018
        DESCRIPTION "Extreme Summit X450-G2-24p-GE4: 24 BaseT (PoE+), 4 SFP, 2 HG[21] (Stack only)"
    ::= { extremeHardware 83 }

    extremeX450g248tG4 OBJECT-IDENTITY
        STATUS      current
    --  Name        "X450G2-48t-G4"
    --  Date        "201807111626Z"  - Tues July 11 16:26 UTC 2018
        DESCRIPTION "Extreme Summit X450-G2-48t-GE4: 48 BaseT, 4 SFP, 2 HG[21] (Stack only)"
    ::= { extremeHardware 84 }

    extremeX450g248pG4 OBJECT-IDENTITY
        STATUS      current
    --  Name        "X450G2-48p-G4"
    --  Date        "201807111626Z"  - Tues July 11 16:26 UTC 2018
        DESCRIPTION "Extreme Summit X450-G2-48p-GE4: 48 BaseT (PoE+), 4 SFP, 2 HG[21] (Stack only)"
    ::= { extremeHardware 85 }

    extremeX440g248p10g4 OBJECT-IDENTITY
        STATUS      current
    --  Name        "X440G2-48p-10G4"
    --  Date        "201807111626Z"  - Tues July 11 16:26 UTC 2018
        DESCRIPTION "Extreme Summit X440-G2-48p-10GE4: 48 BaseT (PoE+), 4 SFP (Combo), 4 SFP+ (2 10GBase-T combo), 1 Fixed AC PSU, 1 RPS port"
    ::= { extremeHardware 86 }

    extremeX440g248t10g4 OBJECT-IDENTITY
        STATUS      current
    --  Name        "X440G2-48t-10G4"
    --  Date        "201807111626Z"  - Tues July 11 16:26 UTC 2018
        DESCRIPTION "Extreme Summit X440-G2-48t-10GE4: 48 BaseT, 4 SFP (Combo), 4 SFP+ (2 10GBase-T combo), 1 Fixed AC PSU, 1 RPS port"
    ::= { extremeHardware 87 }

    extremeX440g248td10g OBJECT-IDENTITY
        STATUS      current
    --  Name        "X440G2-48td-10G"
    --  Date        "201807111626Z"  - Tues July 11 16:26 UTC 2018
        DESCRIPTION "Extreme Summit X440-G2-48t-10GE4-DC: 48 BaseT, 4 SFP (Combo), 4 SFP+ (2 10GBase-T combo), 1 Fixed DC PSU, 1 RPS port"
    ::= { extremeHardware 88 }

    extremeX440g224p10g4 OBJECT-IDENTITY
        STATUS      current
    --  Name        "X440G2-24p-10G4"
    --  Date        "201807111626Z"  - Tues July 11 16:26 UTC 2018
        DESCRIPTION "Extreme Summit X440-G2-24p-10GE4: 24 BaseT (PoE+), 4 SFP (Combo), 4 SFP+, 1 Fixed AC PSU, 1 RPS port"
    ::= { extremeHardware 89 }

    extremeX440g224t10g4 OBJECT-IDENTITY
        STATUS      current
    --  Name        "X440G2-24t-10G4"
    --  Date        "201807111626Z"  - Tues July 11 16:26 UTC 2018
        DESCRIPTION "Extreme Summit X440-G2-24t-10GE4: 24 BaseT, 4 SFP (Combo), 4 SFP+, 1 Fixed AC PSU, 1 RPS port"
    ::= { extremeHardware 90 }

    extremeX440g224td10g OBJECT-IDENTITY
        STATUS      current
    --  Name        "X440G2-24td-10G"
    --  Date        "201807111626Z"  - Tues July 11 16:26 UTC 2018
        DESCRIPTION "Extreme Summit X440-G2-24t-10GE4-DC: 24 BaseT, 4 SFP (Combo), 4 SFP+, 1 Fixed DC PSU, 1 RPS port"
    ::= { extremeHardware 91 }

    extremeX440g224x10g4 OBJECT-IDENTITY
        STATUS      current
    --  Name        "X440G2-24x-10G4"
    --  Date        "201807111626Z"  - Tues July 11 16:26 UTC 2018
        DESCRIPTION "Extreme Summit X440-G2-24x-10GE4: 24 SFP, 4 BaseT (Combo), 4 SFP+, 1 Fixed AC PSU, 1 RPS port"
    ::= { extremeHardware 92 }

    extremeX440g212p10g4 OBJECT-IDENTITY
        STATUS      current
    --  Name        "X440G2-12p-10G4"
    --  Date        "201807111626Z"  - Tues July 11 16:26 UTC 2018
        DESCRIPTION "Extreme Summit X440-G2-12p-10GE4: 12 BaseT (PoE+), 4 SFP+, 1 Fixed AC PSU, 1 RPS port"
    ::= { extremeHardware 93 }

    extremeX440g212t10g4 OBJECT-IDENTITY
        STATUS      current
    --  Name        "X440G2-12t-10G4"
    --  Date        "201807111626Z"  - Tues July 11 16:26 UTC 2018
        DESCRIPTION "Extreme Summit X440-G2-12t-10GE4: 12 BaseT, 4 SFP+, 1 Fixed AC PSU, 1 RPS port"
    ::= { extremeHardware 94 }

    extremeX440g212t8fxg4 OBJECT-IDENTITY
        STATUS      current
    --  Name        "X440G2-12t8fxG4"
    --  Date        "201807111626Z"  - Tues July 11 16:26 UTC 2018
        DESCRIPTION "Extreme Summit X440-G2-12t8fx-GE4: 12 BaseT, 8 100Base-FX LC, 4 SFP, 1 Fixed AC PSU, 1 RPS port"
    ::= { extremeHardware 95 }

    extremeX440g224tG4 OBJECT-IDENTITY
        STATUS      current
    --  Name        "X440G2-24t-G4"
    --  Date        "201807111626Z"  - Tues July 11 16:26 UTC 2018
        DESCRIPTION "Extreme Summit X440-G2-24t-GE4: 24 BaseT, 4 SFP, 1 Fixed AC PSU, 1 RPS port"
    ::= { extremeHardware 96 }

    extremeX440g224fxG4 OBJECT-IDENTITY
        STATUS      current
    --  Name        "X440G2-24fx-G4"
    --  Date        "201807111626Z"  - Tues July 11 16:26 UTC 2018
        DESCRIPTION "Extreme Summit X440-G2-24fx-GE4: 24 100Base-FX LC, 4 SFP, 1 Fixed AC PSU, 1 RPS port"
    ::= { extremeHardware 97 }

    extremeX62016t OBJECT-IDENTITY
        STATUS      current
    --  Name        "X620-16t"
    --  Date        "201807111626Z"  - Tues July 11 16:26 UTC 2018
        DESCRIPTION "Extreme Summit X620-16T: 12 1G/2.5G/5G/10GBaseT, 4 10GBaseT, 4 SFP+ (combo)"
    ::= { extremeHardware 98 }

    extremeX62016p OBJECT-IDENTITY
        STATUS      current
    --  Name        "X620-16p"
    --  Date        "201807111626Z"  - Tues July 11 16:26 UTC 2018
        DESCRIPTION "Extreme Summit X620-16P: 12 MGBaseT, 4 with POE+, 4 with POE++, 4 10GBaseT with POE+, 4 SFP+ (combo)"
    ::= { extremeHardware 99 }

    extremeX62016x OBJECT-IDENTITY
        STATUS      current
    --  Name        "X620-16x"
    --  Date        "201807111626Z"  - Tues July 11 16:26 UTC 2018
        DESCRIPTION "Extreme Summit X620-16X: 16 SFP+"
    ::= { extremeHardware 100 }

    extremeX62010x OBJECT-IDENTITY
        STATUS      current
    --  Name        "X620-10x"
    --  Date        "201807111626Z"  - Tues July 11 16:26 UTC 2018
        DESCRIPTION "Extreme Summit X620-16X: 10 SFP+, 1 Fixed AC PSU, 1 RPS port"
    ::= { extremeHardware 101 }

    extremeX6208t2x OBJECT-IDENTITY
        STATUS      current
    --  Name        "X620-8t-2x"
    --  Date        "201807111626Z"  - Tues July 11 16:26 UTC 2018
        DESCRIPTION "Extreme Summit X620-8T-2X: 8 MGBaseT, 2 SFP+, 1 Fixed AC PSU, 1 RPS port"
    ::= { extremeHardware 102 }

    extremeX87032c OBJECT-IDENTITY
        STATUS      current
    --  Name        "X870-32c"
    --  Date        "201807111626Z"  - Tues July 11 16:26 UTC 2018
        DESCRIPTION "Extreme Summit X870-32C: 32 QSFP+ (100Gb)"
    ::= { extremeHardware 103 }

    extremeX87096x8c OBJECT-IDENTITY
        STATUS      current
    --  Name        "X870-96x-8c"
    --  Date        "201807111626Z"  - Tues July 11 16:26 UTC 2018
        DESCRIPTION "Extreme Summit X870-96X-8C: 24 QSFP+ (4x10Gb), 8 QSFP+ (100Gb)"
    ::= { extremeHardware 104 }

    extremeBpeG24t OBJECT-IDENTITY
        STATUS      current
    --  Name        "BPE-G24t"
    --  Date        "201807111626Z"  - Tues July 11 16:26 UTC 2018
        DESCRIPTION "Extreme BPE-G24T: Bridge Port Extender, "
    ::= { extremeHardware 105 }

    extremePe OBJECT-IDENTITY
        STATUS      current
    --  Name        "PE"
    --  Date        "201807111626Z"  - Tues July 11 16:26 UTC 2018
        DESCRIPTION "Extreme PE"
    ::= { extremeHardware 106 }

    extremeV40024t10ge2 OBJECT-IDENTITY
        STATUS      current
    --  Name        "V400-24t-10GE2"
    --  Date        "201807111626Z"  - Tues July 11 16:26 UTC 2018
        DESCRIPTION "Extreme V400-24t-10GE2: V400 Series 24 10/100/1000BASE-T, 2 1000/10GBaseX unpopulated SFP+ ports, fixed power supply and fan"
    ::= { extremeHardware 107 }

    extremeV40024p10ge2 OBJECT-IDENTITY
        STATUS      current
    --  Name        "V400-24p-10GE2"
    --  Date        "201807111626Z"  - Tues July 11 16:26 UTC 2018
        DESCRIPTION "Extreme V400-24p-10GE2: V400 Series 24 10/100/1000BASE-T PoE+, 2 1000/10GBaseX unpopulated SFP+ ports, fixed power supply and fans, and optional redundant power supply"
    ::= { extremeHardware 108 }

    extremeV40048t10ge4 OBJECT-IDENTITY
        STATUS      current
    --  Name        "V400-48t-10GE4"
    --  Date        "201807111626Z"  - Tues July 11 16:26 UTC 2018
        DESCRIPTION "Extreme V400-48t-10GE4: V400 Series 48 10/100/1000BASE-T, 4 1000/10GBaseX unpopulated SFP+ ports, fixed power supply and fan"
    ::= { extremeHardware 109 }

    extremeV40048p10ge4 OBJECT-IDENTITY
        STATUS      current
    --  Name        "V400-48p-10GE4"
    --  Date        "201807111626Z"  - Tues July 11 16:26 UTC 2018
        DESCRIPTION "Extreme V400-48p-10GE4: V400 Series 48 10/100/1000BASE-T PoE+, 4 1000/10GBaseX unpopulated SFP+ ports, fixed power supply, fans, and optional redundant power supply"
    ::= { extremeHardware 110 }

    extremeX69048t2q4c OBJECT-IDENTITY
        STATUS      current
    --  Name        "X690-48t-2q-4c"
    --  Date        "201807111626Z"  - Tues July 11 16:26 UTC 2018
        DESCRIPTION "Extreme Summit X690-48T-2Q-4C: 48 10GBASE-T, 2 10Gb/40Gb QSFP+, 4 10Gb/25Gb/40Gb/50Gb/100Gb QSFP28"
    ::= { extremeHardware 111 }

    extremeX69048x2q4c OBJECT-IDENTITY
        STATUS      current
    --  Name        "X690-48x-2q-4c"
    --  Date        "201807111626Z"  - Tues July 11 16:26 UTC 2018
        DESCRIPTION "Extreme Summit X690-48X-2Q-4C: 48 1/10Gb SFP+, 2 10Gb/40Gb QSFP+, 4 10Gb/25Gb/40Gb/50Gb/100Gb QSFP28"
    ::= { extremeHardware 112 }

    extremeX59024t1q2c OBJECT-IDENTITY
        STATUS      current
    --  Name        "X590-24t-1q-2c"
    --  Date        "201807111626Z"  - Tues July 11 16:26 UTC 2018
        DESCRIPTION "Extreme Summit X590-24T-1Q-2C: 24 10GBASE-T, 1 10Gb/40Gb QSFP+, 2 10Gb/25Gb/40Gb/50Gb/100Gb QSFP28"
    ::= { extremeHardware 113 }

    extremeX59024x1q2c OBJECT-IDENTITY
        STATUS      current
    --  Name        "X590-24x-1q-2c"
    --  Date        "201807111626Z"  - Tues July 11 16:26 UTC 2018
        DESCRIPTION "Extreme Summit X590-24X-1Q-2C: 24 1/10Gb SFP+, 1 10Gb/40Gb QSFP+, 2 10Gb/25Gb/40Gb/50Gb/100Gb QSFP28"
    ::= { extremeHardware 114 }

    extremeStack OBJECT-IDENTITY
        STATUS      current
    --  Name        "Stack"
    --  Date        "201807111626Z"  - Tues July 11 16:26 UTC 2018
        DESCRIPTION "Extreme Summit Stack"
    ::= { extremeHardware 115 }

    extremeX46548t OBJECT-IDENTITY
        STATUS    current
    --  Name      "X465-48T"
    --  Date      "201907102021Z"  - Wed Jul 10 20:21:09 UTC 2019
        DESCRIPTION
        "X465 with 48 10/100/1000Mb FDX/HDX MACSEC capable ports, 1 VIM slot"
    ::= { extremeHardware 116 }

    extremeX46548p OBJECT-IDENTITY
        STATUS    current
    --  Name      "X465-48P"
    --  Date      "201907102021Z"  - Wed Jul 10 20:21:09 UTC 2019
        DESCRIPTION
        "X465 with 48 10/100/1000Mb FDX/HDX MACSEC capable ports, 802.3at PoE (30W), 1 VIM slot"
    ::= { extremeHardware 117 }

    extremeX46548w OBJECT-IDENTITY
        STATUS    current
    --  Name      "X465-48W"
    --  Date      "201907102021Z"  - Wed Jul 10 20:21:09 UTC 2019
        DESCRIPTION
        "X465 with 48 10/100/1000Mb FDX/HDX MACSEC capable ports, 802.3bt Type3/Type4 PoE (90W), 1 VIM slot"
    ::= { extremeHardware 118 }

    extremeX46524mu OBJECT-IDENTITY
    STATUS    current
    --  Name      "X465-24MU"
    --  Date      "201907102021Z"  - Wed Jul 10 20:21:09 UTC 2019
        DESCRIPTION
        "X465 with 24 100Mb/1/2.5/5Gb ports, 802.3bt Type3 PoE (60W), 1 VIM slot"
    ::= { extremeHardware 119 }

    extremeX46524mu24w OBJECT-IDENTITY
    STATUS    current
    --  Name      "X465-24MU-24W"
    --  Date      "201907102021Z"  - Wed Jul 10 20:21:09 UTC 2019
        DESCRIPTION
        "X465 with 24 100Mb/1/2.5/5Gb ports, 802.3bt Type3 PoE (60W) and 24 10/100/1000Mb FDX/HDX ports with MACSEC, 802.1bt Type3/Type4 PoE (90W), 1 VIM slot"
    ::= { extremeHardware 120 }

    extremeX46524w OBJECT-IDENTITY
    STATUS    current
    --  Name      "X465-24W"
    --  Date      "201907102021Z"  - Wed Jul 10 20:21:09 UTC 2019
        DESCRIPTION
        "X465 with 24 10/100/1000Mb FDX/HDX MACSEC capable ports, 802.3bt PoE Type3/Type4 (90W), 1 VIM slot"
    ::= { extremeHardware 121 }

    extremeV3008p2tW OBJECT-IDENTITY
        STATUS      current
    --  Name        "V300-8P-2T-W"
    --  Date        "201908011714Z"  - Thurs Aug 01 17:14 UTC 2019
        DESCRIPTION "Extreme V300-8P-2T-W: V300 Series 8 10/100/1000BASE-T PoE+, 2 1000BaseT uplink ports, powered by PoE, and fanless"
    ::= { extremeHardware 122 }

    extremeX43524p4s OBJECT-IDENTITY
        STATUS      current
    --  Name        "X435-24P-4S"
    --  Date        "201908051031Z"  - Mon Aug  5 10:31:29 UTC 2019
        DESCRIPTION "X435 with 24 10/100/1000Mb FDX/HDX capable ports, 802.3at PoE (30W), 2 1/2.5G SFP ports"
    ::= { extremeHardware 123 }

    extremeX43524t4s OBJECT-IDENTITY
        STATUS      current
    --  Name        "X435-24T-4S"
    --  Date        "201908051031Z"  - Mon Aug  5 10:31:29 UTC 2019
        DESCRIPTION "X435 with 24 10/100/1000Mb FDX/HDX capable ports, 2 1/2.5G SFP ports"
    ::= { extremeHardware 124 }

    extremeX4358p4s OBJECT-IDENTITY
        STATUS      current
    --  Name        "X435-8P-4S"
    --  Date        "201908051031Z"  - Mon Aug  5 10:31:29 UTC 2019
        DESCRIPTION "X435 with 8 10/100/1000Mb FDX/HDX capable ports, 802.3at PoE (30W), 2 1/2.5G SFP ports"
    ::= { extremeHardware 125 }

    extremeX4358t4s OBJECT-IDENTITY
        STATUS      current
    --  Name        "X435-8T-4S"
    --  Date        "201908051031Z"  - Mon Aug  5 10:31:29 UTC 2019
        DESCRIPTION "X435 with 8 10/100/1000Mb FDX/HDX capable ports, 2 1/2.5G SFP ports"
    ::= { extremeHardware 126 }

    extremeX4358p2tW OBJECT-IDENTITY
        STATUS      current
    --  Name        "X435-8P-2T-W"
    --  Date        "201908051031Z"  - Mon Aug  5 10:31:29 UTC 2019
        DESCRIPTION "X435 with 8 10/100/1000Mb FDX/HDX capable ports, 802.3at PoE (30W), 2 10/100/1000Mb FDX/HDX, 802.3bt PoE (90W) powered ports"
    ::= { extremeHardware 127 }

    extremeX46524xe OBJECT-IDENTITY
    STATUS    current
    --  Name      "X465-24XE"
    --  Date      "201909042120Z"  - Wed Sep 4 21:20:00 UTC 2019
        DESCRIPTION
        "X465 with 24 1/10GbE SFP+ MACSEC capable ports, 1 VIM slot"
    ::= { extremeHardware 128 }

    extremeX46524s OBJECT-IDENTITY
    STATUS    current
    --  Name      "X465-24S"
    --  Date      "201909042120Z"  - Wed Sep 4 21:20:00 UTC 2019
        DESCRIPTION
        "X465-24s: X465 with 24 1GbE SFP ports, 1 VIM slot"
    ::= { extremeHardware 129 }

    extremeX465i48w OBJECT-IDENTITY
    STATUS    current
    --  Name      "X465i-48W"
    --  Date      "201909042120Z"  - Wed Sep 4 21:20:00 UTC 2019
        DESCRIPTION
        "X465 with 48 10/100/1000Mb FDX/HDX MACSEC capable ports, 802.3bt Type3/Type4 PoE (90W), 1 VIM slot"
    ::= { extremeHardware 130 }

    extremeX69548y8c OBJECT-IDENTITY
    STATUS    current
    --  Name      "X695-48Y-8C"
    --  Date      "201911202014Z"  - Wed Nov 20 20:14:00 UTC 2019
        DESCRIPTION
        "X695-48Y-8C: 48 1Gb/10Gb/25Gb SFP28, 8 40Gb/100Gb QSFP28"
    ::= { extremeHardware 131 }

    extremeV3008p2x OBJECT-IDENTITY
        STATUS      current
    --  Name        "V300-8P-2X"
    --  Date        "202001072243Z"  - Tues Jan 07 22:43 UTC 2020
        DESCRIPTION "Extreme V300-8P-2X: V300 Series 8 10/100/1000BASE-T PoE+, 2 1/10GbE SFP+ uplink ports, and fanless"
    ::= { extremeHardware 132 }

    extremeV3008t2x OBJECT-IDENTITY
        STATUS      current
    --  Name        "V300-8T-2X"
    --  Date        "202001072243Z"  - Tues Jan 07 22:43 UTC 2020
        DESCRIPTION "Extreme V300-8T-2X: V300 Series 8 10/100/1000BASE-T, 2 1/10GbE SFP+ uplink ports, and fanless"
    ::= { extremeHardware 133 }

    extremeV300ht8p2x OBJECT-IDENTITY
        STATUS      current
    --  Name        "V300HT-8P-2X"
    --  Date        "202001072243Z"  - Tues Jan 07 22:43 UTC 2020
        DESCRIPTION "Extreme V300HT-8P-2X: V300 Series 8 10/100/1000BASE-T PoE+, 2 1/10GbE SFP+ uplink ports, high temp, and fanless"
    ::= { extremeHardware 134 }

    extremeV300ht8t2x OBJECT-IDENTITY
        STATUS      current
    --  Name        "V300HT-8T-2X"
    --  Date        "202001072243Z"  - Tues Jan 07 22:43 UTC 2020
        DESCRIPTION "Extreme V300HT-8T-2X: V300 Series 8 10/100/1000BASE-T, 2 1/10GbE SFP+ uplink ports, high temp, and fanless"
    ::= { extremeHardware 135 }

END
