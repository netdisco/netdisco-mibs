-- **************************************************************** 
-- *  Moxa General (System Management) - Modbus TCP PRIVATE MIB 
-- * 
-- *  Copyright (c) 2019 by Moxa Inc. 
-- *  All rights reserved. 
-- ***************************************************************** 
MOXA-MODBUS-TCP-MIB DEFINITIONS ::= BEGIN 
    IMPORTS 
        MODULE-IDENTITY, OBJECT-TYPE, Integer32 
        enterprises
            FROM SNMPv2-SMI 
        TEXTUAL-CONVENTION, TruthValue 
            FROM SNMPv2-TC; 

    mxModbusTcp MODULE-IDENTITY 
        LAST-UPDATED "202203080000Z"
        ORGANIZATION "Moxa Inc." 
        CONTACT-INFO 
                "
                Postal: Moxa Inc.
                13F., No. 3, Sec. 4, New Taipei Blvd.
                Xinzhuang Dist., New Taipei City 242032, Taiwan, R.O.C.


                Tel: +866-2-89191230
                Web: http://www.moxa.com/
                "
        DESCRIPTION
                "This MIB module defines settings used for Modbus TCP" 

        REVISION    "202203080000Z"
        DESCRIPTION    "Update CONTACT-INFO"

        REVISION    "202101190000Z" 
        DESCRIPTION    "Initial Revision" 
        ::= { systemManagement 9 }  

        moxa               OBJECT IDENTIFIER ::= { enterprises 8691 } 
        general            OBJECT IDENTIFIER ::= { moxa 602 }         
        systemManagement   OBJECT IDENTIFIER ::= { general 1 }      

-- ------------------------------------------------------------- 
-- groups in the MOXA-MODBUS-TCP-MIB MIB 
-- -------------------------------------------------------------  

    -- mbustcpNotification OBJECT IDENTIFIER ::= { mxModbusTcp 0 } 
    mbustcpConfiguration OBJECT IDENTIFIER ::= { mxModbusTcp 1 } 
    -- mbustcpStatus OBJECT IDENTIFIER ::= { mxModbusTcp 2 } 
    -- mbustcpExtensions OBJECT IDENTIFIER ::= { mxModbusTcp 3 } 

-- ------------------------------------------------------------- 
-- configuration group 
-- ------------------------------------------------------------- 

    mbustcpEnable OBJECT-TYPE 
        SYNTAX      TruthValue 
        MAX-ACCESS  read-write 
        STATUS      current 
        DESCRIPTION 
                "Enable/Disable Modbus Tcp Server" 
        ::= { mbustcpConfiguration 1 } 
END
