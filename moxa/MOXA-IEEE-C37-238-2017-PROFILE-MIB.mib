-- ****************************************************************
-- *  Moxa General (Time) - PTP PRIVATE MIB
-- *
-- *  Copyright (c) 2021 by Moxa Inc.
-- *  All rights reserved.
-- *****************************************************************

MOXA-IEEE-C37-238-2017-PROFILE-MIB DEFINITIONS ::= BEGIN
    IMPORTS
        MODULE-IDENTITY, NOTIFICATION-TYPE, OBJECT-TYPE, OBJECT-IDENTITY, Gauge32, Unsigned32, Counter32, Counter64, mib-2, Integer32
            FROM SNMPv2-SMI
        TEXTUAL-CONVENTION, DateAndTime, DisplayString, TruthValue, AutonomousType
            FROM SNMPv2-TC
        OBJECT-GROUP, MODULE-COMPLIANCE
            FROM SNMPv2-CONF
        time
            FROM MOXA-GENERAL-MIB
        InterfaceIndexOrZero
            FROM IF-MIB
        PtpClockDomainType, PtpClockIdentity, PtpClockInstanceType, PtpClockIntervalBase2, PtpClockMechanismType, PtpClockPortNumber, PtpClockPortTransportTypeAddress, PtpClockProfileType, PtpClockQualityAccuracyType, PtpClockQualityClassType, PtpClockRoleType, PtpClockStateType, PtpClockTimeInterval, PtpClockTimeSourceType, PtpClockTxModeType, PtpClockType
            FROM PTPBASE-MIB;

    mxIeeeC37238Profile MODULE-IDENTITY
        LAST-UPDATED "202210190000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa IEEE C37.238 2017 Profile"

        REVISION    "202312010000Z"
        DESCRIPTION
            "
            Modified objects:
				ieeeC37238ConfigClockDefaultDSMaximumStepsRemoved
            "

        REVISION    "202210190000Z"
        DESCRIPTION 
            "
            Modified objects:
                ieeeC37238StatClockPortRunningState
            "

        REVISION    "202111030000Z"
        DESCRIPTION "Initial Revision"

        ::= { time 6 }

-- -------------------------------------------------------------
-- groups in the IEEE-C37-238-2017-PROFILE-MIB MIB
-- -------------------------------------------------------------
    -- ieeeC37238Notification       OBJECT IDENTIFIER ::= { mxIeeeC37238Profile 0 }
    ieeeC37238Configuration         OBJECT IDENTIFIER ::= { mxIeeeC37238Profile 1 }
    ieeeC37238Status                OBJECT IDENTIFIER ::= { mxIeeeC37238Profile 2 }
    -- ieeeC37238Extensions         OBJECT IDENTIFIER ::= { mxIeeeC37238Profile 3 }

-- -------------------------------------------------------------
-- configuration group
-- -------------------------------------------------------------
-----------------------
-- IEEE C37.238 2017 -- 
-----------------------
    ieeeC37238ConfigClock  OBJECT IDENTIFIER
        ::= { ieeeC37238Configuration 1 }

    ieeeC37238ConfigClockDefaultDSTable OBJECT-TYPE
        SYNTAX          SEQUENCE OF IeeeC37238ConfigClockDefaultDSEntry
        MAX-ACCESS      not-accessible
        STATUS          current
        DESCRIPTION
                "Table of information about the PTP clock defaultDS for
                 all domains."
        ::= { ieeeC37238ConfigClock 1 }

    ieeeC37238ConfigClockDefaultDSEntry OBJECT-TYPE
        SYNTAX          IeeeC37238ConfigClockDefaultDSEntry
        MAX-ACCESS      not-accessible
        STATUS          current
        DESCRIPTION
                "A table entry that contains information about a single
                 PTP clock defaultDS for a domain."
        INDEX  { ieeeC37238ConfigClockDefaultDSInstanceIndex }
        ::= { ieeeC37238ConfigClockDefaultDSTable 1 }

    IeeeC37238ConfigClockDefaultDSEntry ::= 
        SEQUENCE {
            ieeeC37238ConfigClockDefaultDSInstanceIndex       PtpClockInstanceType,
            ieeeC37238ConfigClockDefaultDSClockType           PtpClockType,
            ieeeC37238ConfigClockDefaultDSDomainNumber        PtpClockDomainType,
            ieeeC37238ConfigClockDefaultDSTwoStepFlag         TruthValue,
            ieeeC37238ConfigClockDefaultDSClockIdentity       PtpClockIdentity,
            ieeeC37238ConfigClockDefaultDSPriority1           Unsigned32,
            ieeeC37238ConfigClockDefaultDSPriority2           Unsigned32,
            ieeeC37238ConfigClockDefaultDSQualityClass        PtpClockQualityClassType,
            ieeeC37238ConfigClockDefaultDSQualityAccuracy     PtpClockQualityAccuracyType,
            ieeeC37238ConfigClockDefaultDSMaximumStepsRemoved Unsigned32,
            ieeeC37238ConfigClockDefaultDSAccuracyAlert       Unsigned32,
            ieeeC37238ConfigClockDefaultDSGrandmasterId       Unsigned32
        }

    ieeeC37238ConfigClockDefaultDSInstanceIndex OBJECT-TYPE
        SYNTAX          PtpClockInstanceType
        MAX-ACCESS      not-accessible
        STATUS          current
        DESCRIPTION
                "This object specifies the instance of the clock for this clock
                 type in the given domain."
        ::= { ieeeC37238ConfigClockDefaultDSEntry 1 }

    ieeeC37238ConfigClockDefaultDSClockType OBJECT-TYPE
        SYNTAX          PtpClockType
        MAX-ACCESS      read-write
        STATUS          current
        DESCRIPTION
                "This object specifies the clock type as defined in the
                 textual convention description."
        ::= { ieeeC37238ConfigClockDefaultDSEntry 2 }

    ieeeC37238ConfigClockDefaultDSDomainNumber OBJECT-TYPE
        SYNTAX          PtpClockDomainType (0..127|254)
        MAX-ACCESS      read-write
        STATUS          current
        DESCRIPTION
                "This object specifies the domain number used to create a
                 logical group of PTP devices."
        ::= { ieeeC37238ConfigClockDefaultDSEntry 3 }

    ieeeC37238ConfigClockDefaultDSTwoStepFlag OBJECT-TYPE
        SYNTAX          TruthValue
        MAX-ACCESS      read-write
        STATUS          current
        DESCRIPTION
                "This object specifies whether the two-step process is used."
        ::= { ieeeC37238ConfigClockDefaultDSEntry 4 }

    ieeeC37238ConfigClockDefaultDSClockIdentity OBJECT-TYPE
        SYNTAX          PtpClockIdentity
        MAX-ACCESS      read-only
        STATUS          current
        DESCRIPTION
                "This object specifies the defaultDS clockIdentity member."
        ::= { ieeeC37238ConfigClockDefaultDSEntry 5 }

    ieeeC37238ConfigClockDefaultDSPriority1 OBJECT-TYPE
        SYNTAX          Unsigned32 (0..255)
        MAX-ACCESS      read-write
        STATUS          current
        DESCRIPTION
                "This object specifies the defaultDS priority1 member."
        ::= { ieeeC37238ConfigClockDefaultDSEntry 6 }

    ieeeC37238ConfigClockDefaultDSPriority2 OBJECT-TYPE
        SYNTAX          Unsigned32 (0..255)
        MAX-ACCESS      read-write
        STATUS          current
        DESCRIPTION
                "This object specifies the defaultDS priority2 member."
        ::= { ieeeC37238ConfigClockDefaultDSEntry 7 }

    ieeeC37238ConfigClockDefaultDSQualityClass OBJECT-TYPE
        SYNTAX          PtpClockQualityClassType
        MAX-ACCESS      read-only
        STATUS          current
        DESCRIPTION
                "This object specifies the defaultDS Quality Class."
        ::= { ieeeC37238ConfigClockDefaultDSEntry 8 }

    ieeeC37238ConfigClockDefaultDSQualityAccuracy OBJECT-TYPE
        SYNTAX          PtpClockQualityAccuracyType
        MAX-ACCESS      read-only
        STATUS          current
        DESCRIPTION
                "This object specifies the defaultDS Quality Accuracy."
        ::= { ieeeC37238ConfigClockDefaultDSEntry 9 }

    ieeeC37238ConfigClockDefaultDSMaximumStepsRemoved OBJECT-TYPE
        SYNTAX          Unsigned32 (2..255)
        MAX-ACCESS      read-write
        STATUS          current
        DESCRIPTION
                "This object specifies the defaultDS Maximum Steps Removed."
        ::= { ieeeC37238ConfigClockDefaultDSEntry 10 }

    ieeeC37238ConfigClockDefaultDSAccuracyAlert OBJECT-TYPE
        SYNTAX          Unsigned32 (50..250000000)
        MAX-ACCESS      read-write
        STATUS          current
        DESCRIPTION
                "This object specifies the defaultDS Accuracy Alert."
        ::= { ieeeC37238ConfigClockDefaultDSEntry 11 }

    ieeeC37238ConfigClockDefaultDSGrandmasterId OBJECT-TYPE
        SYNTAX          Unsigned32 (0..65535)
        MAX-ACCESS      read-write
        STATUS          current
        DESCRIPTION
                "This object specifies the defaultDS Accuracy Alert."
        ::= { ieeeC37238ConfigClockDefaultDSEntry 12 }

    ieeeC37238ConfigClockPortDSTable OBJECT-TYPE
        SYNTAX          SEQUENCE OF IeeeC37238ConfigClockPortDSEntry
        MAX-ACCESS      not-accessible
        STATUS          current
        DESCRIPTION
                "Table of information about the clock's portDS for a
                 particular domain."
        ::= { ieeeC37238ConfigClock 2 }

    ieeeC37238ConfigClockPortDSEntry OBJECT-TYPE
        SYNTAX          IeeeC37238ConfigClockPortDSEntry
        MAX-ACCESS      not-accessible
        STATUS          current
        DESCRIPTION
                "A table entry that contains portDS information for
                 a single clock port."
        INDEX { ieeeC37238ConfigClockPortDSPortNumberIndex }
        ::= { ieeeC37238ConfigClockPortDSTable 1 }

    IeeeC37238ConfigClockPortDSEntry ::= 
        SEQUENCE {
            ieeeC37238ConfigClockPortDSPortNumberIndex      PtpClockPortNumber,
            ieeeC37238ConfigClockPortDSPortIdentity         OCTET STRING,
            ieeeC37238ConfigClockPortDSlogAnnouncementInterval PtpClockIntervalBase2,
            ieeeC37238ConfigClockPortDSAnnounceRctTimeout   Integer32,
            ieeeC37238ConfigClockPortDSlogSyncInterval      PtpClockIntervalBase2,
            ieeeC37238ConfigClockPortDSMinDelayReqInterval  Integer32,
            ieeeC37238ConfigClockPortDSPeerDelayReqInterval Integer32,
            ieeeC37238ConfigClockPortDSDelayMech            PtpClockMechanismType,
            ieeeC37238ConfigClockPortDSEnabled              TruthValue 
        }

    ieeeC37238ConfigClockPortDSPortNumberIndex OBJECT-TYPE
        SYNTAX          PtpClockPortNumber
        MAX-ACCESS      not-accessible
        STATUS          current
        DESCRIPTION
                "This object specifies the PTP portNumber associated with this
                 PTP port."
        ::= { ieeeC37238ConfigClockPortDSEntry 1 }

    ieeeC37238ConfigClockPortDSPortIdentity OBJECT-TYPE
        SYNTAX          OCTET STRING(SIZE(1..256))
        MAX-ACCESS      read-only
        STATUS          current
        DESCRIPTION
                "This object specifies the PTP clock port Identity."
        ::= { ieeeC37238ConfigClockPortDSEntry 2 }

    ieeeC37238ConfigClockPortDSlogAnnouncementInterval OBJECT-TYPE
        SYNTAX          PtpClockIntervalBase2
        UNITS           "Time Interval"
        MAX-ACCESS      read-only
        STATUS          current
        DESCRIPTION
                "This object specifies the Announce message transmission
                 interval associated with this clock port."
        ::= { ieeeC37238ConfigClockPortDSEntry 3 }

    ieeeC37238ConfigClockPortDSAnnounceRctTimeout OBJECT-TYPE
        SYNTAX          Integer32
        MAX-ACCESS      read-only
        STATUS          current
        DESCRIPTION
                "This object specifies the Announce receipt timeout associated
                 with this clock port."
        ::= { ieeeC37238ConfigClockPortDSEntry 4 }

    ieeeC37238ConfigClockPortDSlogSyncInterval OBJECT-TYPE
        SYNTAX          PtpClockIntervalBase2
        UNITS           "Time Interval"
        MAX-ACCESS      read-only
        STATUS          current
        DESCRIPTION
                "This object specifies the Sync message transmission interval."
        ::= { ieeeC37238ConfigClockPortDSEntry 5 }

    ieeeC37238ConfigClockPortDSMinDelayReqInterval OBJECT-TYPE
        SYNTAX          Integer32
        MAX-ACCESS      read-only
        STATUS          current
        DESCRIPTION
                "This object specifies the Delay_Req message transmission
                 interval."
        ::= { ieeeC37238ConfigClockPortDSEntry 6 }

    ieeeC37238ConfigClockPortDSPeerDelayReqInterval OBJECT-TYPE
        SYNTAX          Integer32
        MAX-ACCESS      read-only
        STATUS          current
        DESCRIPTION
                "This object specifies the Pdelay_Req message transmission
                 interval."
        ::= { ieeeC37238ConfigClockPortDSEntry 7 }

    ieeeC37238ConfigClockPortDSDelayMech OBJECT-TYPE
        SYNTAX          PtpClockMechanismType
        MAX-ACCESS      read-only
        STATUS          current
        DESCRIPTION
                "This object specifies the delay mechanism used.  If the clock
                 is an end-to-end clock, the value is e2e; if the
                 clock is a peer to-peer clock, the value is p2p."
        ::= { ieeeC37238ConfigClockPortDSEntry 8 }

    ieeeC37238ConfigClockPortDSEnabled OBJECT-TYPE
        SYNTAX          TruthValue
        MAX-ACCESS      read-write
        STATUS          current
        DESCRIPTION
                "True if port is enabled."
        DEFVAL { false }
        ::= { ieeeC37238ConfigClockPortDSEntry 9 }

    ieeeC37238ConfigTransportType OBJECT-TYPE
        SYNTAX  INTEGER {
                    udpipv4 (1),
                    udpipv6 (2),
                    ieee8023 (3),
                    devicenet (4),
                    controlnet (5),
                    profitnet (6),
                    ieee8021 (7),
                    unknown (65534)
                }
        MAX-ACCESS read-only
        STATUS     current 
        DESCRIPTION
                "This denotes the type of the interface. PTP port bears a seperate 
                 meaning than the one that are normally defined in interface mibs.
                 PTP can run over physical interfaces, VLAN identifiers or IVR
                 interfaces. Hence this object needs to be configured before making
                 this particular row as ACTIVE.
                 Only values UDP/IPv4, UDP/IPv6, IEEE802.3 are supported. IEEE8021 
                 corresponds to layer 2 Vlan."
        ::= { ieeeC37238ConfigClock 3 }

-- -------------------------------------------------------------
-- status group
-- -------------------------------------------------------------
-----------------------
-- IEEE C37.238 2017 -- 
-----------------------

    ieeeC37238StatClock  OBJECT IDENTIFIER
        ::= { ieeeC37238Status 1 }

    ieeeC37238StatClockCurrentDSTable OBJECT-TYPE
        SYNTAX          SEQUENCE OF IeeeC37238StatClockCurrentDSEntry
        MAX-ACCESS      not-accessible
        STATUS          current
        DESCRIPTION
                "Table of information about the PTP clock currentDS for
                 all domains."
        ::= { ieeeC37238StatClock 1 }

    ieeeC37238StatClockCurrentDSEntry OBJECT-TYPE
        SYNTAX          IeeeC37238StatClockCurrentDSEntry
        MAX-ACCESS      not-accessible
        STATUS          current
        DESCRIPTION
                "A table entry that contains information about a single
                 PTP clock currentDS for a domain."
        REFERENCE
                "Section 8.2.2 ('currentDS data set member
                 specifications') of [IEEE-1588-2008]"
        INDEX { ieeeC37238StatClockCurrentDSInstanceIndex }
        ::= { ieeeC37238StatClockCurrentDSTable 1 }

    IeeeC37238StatClockCurrentDSEntry ::=
        SEQUENCE {
            ieeeC37238StatClockCurrentDSInstanceIndex    PtpClockInstanceType,
            ieeeC37238StatClockCurrentDSStepsRemoved     Unsigned32,
            ieeeC37238StatClockCurrentDSOffsetFromMaster PtpClockTimeInterval,
            ieeeC37238StatClockCurrentDSMeanPathDelay    PtpClockTimeInterval,
            ieeeC37238StatClockCurrentDSSyncStatus       Unsigned32,
            ieeeC37238StatClockCurrentDSSlavePort        Integer32,
            ieeeC37238StatClockCurrentDSClockTime        DisplayString
        }

    ieeeC37238StatClockCurrentDSInstanceIndex OBJECT-TYPE
        SYNTAX          PtpClockInstanceType
        MAX-ACCESS      not-accessible
        STATUS          current
        DESCRIPTION
                "This object specifies the instance of the clock for this clock
                 type in the given domain."
        ::= { ieeeC37238StatClockCurrentDSEntry 1 }

    ieeeC37238StatClockCurrentDSStepsRemoved OBJECT-TYPE
        SYNTAX          Unsigned32
        UNITS           "Steps"
        MAX-ACCESS      read-only
        STATUS          current
        DESCRIPTION
                "The current clock dataset stepsRemoved value.

                 This object specifies the distance measured by the number of
                 boundary clocks between the local clock and the foreign master
                 as indicated in the stepsRemoved field of Announce messages."
        REFERENCE
                "Section 8.2.2.2 ('stepsRemoved') of [IEEE-1588-2008]"
        ::= { ieeeC37238StatClockCurrentDSEntry 2 }

    ieeeC37238StatClockCurrentDSOffsetFromMaster OBJECT-TYPE
        SYNTAX          PtpClockTimeInterval
        UNITS           "Time Interval"
        MAX-ACCESS      read-only
        STATUS          current
        DESCRIPTION
                "This object specifies the current clock dataset ClockOffset
                 value.  The value of the computation of the offset in time
                 between a slave and a master clock."
        REFERENCE
                "Section 8.2.2.3 ('currentDS.offsetFromMaster')
                 of [IEEE-1588-2008]"
        ::= { ieeeC37238StatClockCurrentDSEntry 3 }

    ieeeC37238StatClockCurrentDSMeanPathDelay OBJECT-TYPE
        SYNTAX          PtpClockTimeInterval
        UNITS           "Time Interval"
        MAX-ACCESS      read-only
        STATUS          current
        DESCRIPTION
                "This object specifies the current clock dataset
                 MeanPathDelay value.

                 The mean path delay between a pair of ports as measured by the
                 delay request-response mechanism."
        REFERENCE
                "Section 8.2.2.4 ('currentDS.meanPathDelay')
                 of [IEEE-1588-2008]"
        ::= { ieeeC37238StatClockCurrentDSEntry 4 }


    ieeeC37238StatClockCurrentDSSyncStatus OBJECT-TYPE
        SYNTAX          Unsigned32
        MAX-ACCESS      read-only
        STATUS          current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 1 }
        ::= { ieeeC37238StatClockCurrentDSEntry 5 }

    ieeeC37238StatClockCurrentDSSlavePort OBJECT-TYPE
        SYNTAX          Integer32(1..255)
        MAX-ACCESS      read-only
        STATUS          current
        DESCRIPTION
                "Indicate the port which is in the SLAVE state."
        ::= { ieeeC37238StatClockCurrentDSEntry 6 }

    ieeeC37238StatClockCurrentDSClockTime OBJECT-TYPE
        SYNTAX          DisplayString
        MAX-ACCESS      read-only
        STATUS          current
        DESCRIPTION
                "Indicate the PTP Clock Time."
        ::= { ieeeC37238StatClockCurrentDSEntry 7 }

    ieeeC37238StatClockParentDSTable OBJECT-TYPE
        SYNTAX          SEQUENCE OF IeeeC37238StatClockParentDSEntry
        MAX-ACCESS      not-accessible
        STATUS          current
        DESCRIPTION
                "Table of information about the PTP clock parentDS for
                 all domains."
        ::= { ieeeC37238StatClock 2 }

    ieeeC37238StatClockParentDSEntry OBJECT-TYPE
        SYNTAX          IeeeC37238StatClockParentDSEntry
        MAX-ACCESS      not-accessible
        STATUS          current
        DESCRIPTION
                "A table entry that contains information about a single
                 PTP clock parentDS for a domain."
        REFERENCE
                "Section 8.2.3 ('parentDS data set member specifications') of
                 [IEEE-1588-2008]"
        INDEX { ieeeC37238StatClockParentDSInstanceIndex }
        ::= { ieeeC37238StatClockParentDSTable 1 }

    IeeeC37238StatClockParentDSEntry ::=
        SEQUENCE {
            ieeeC37238StatClockParentDSInstanceIndex          PtpClockInstanceType,
            ieeeC37238StatClockParentDSParentPortIdentity     OCTET STRING,
            ieeeC37238StatClockParentDSGMClockIdentity        PtpClockIdentity,
            ieeeC37238StatClockParentDSGMClockPriority1       Unsigned32,
            ieeeC37238StatClockParentDSGMClockPriority2       Unsigned32,
            ieeeC37238StatClockParentDSGMClockQualityClass    PtpClockQualityClassType,
            ieeeC37238StatClockParentDSGMClockQualityAccuracy PtpClockQualityAccuracyType,
            ieeeC37238StatClockParentDSParentPortNumber       PtpClockPortNumber
        }

    ieeeC37238StatClockParentDSInstanceIndex OBJECT-TYPE
        SYNTAX          PtpClockInstanceType
        MAX-ACCESS      not-accessible
        STATUS          current
        DESCRIPTION
                "This object specifies the instance of the clock for this clock
                 type in the given domain."
        ::= { ieeeC37238StatClockParentDSEntry 1 }

    ieeeC37238StatClockParentDSParentPortIdentity OBJECT-TYPE
        SYNTAX          OCTET STRING(SIZE(1..256))
        MAX-ACCESS      read-only
        STATUS          current
        DESCRIPTION
                "This object specifies the value of portIdentity of the port on
                 the master that issues the Sync messages used in synchronizing
                 this clock."
        REFERENCE
                "Section 8.2.3.2 ('parentDS.parentPortIdentity') of
                 [IEEE-1588-2008]"
        ::= { ieeeC37238StatClockParentDSEntry 2 }

    ieeeC37238StatClockParentDSGMClockIdentity OBJECT-TYPE
        SYNTAX          PtpClockIdentity
        MAX-ACCESS      read-only
        STATUS          current
        DESCRIPTION
                "This object specifies the parentDS grandmaster clock
                 identity."
        REFERENCE
                "Section 8.2.3.6 ('parentDS.grandmasterIdentity') of
                 [IEEE-1588-2008]"
        ::= { ieeeC37238StatClockParentDSEntry 3 }

    ieeeC37238StatClockParentDSGMClockPriority1 OBJECT-TYPE
        SYNTAX          Unsigned32
        MAX-ACCESS      read-only
        STATUS          current
        DESCRIPTION
                "This object specifies the parentDS grandmaster clock
                 priority1."
        REFERENCE
                "Section 8.2.3.8 ('parentDS.grandmasterPriority1') of
                 [IEEE-1588-2008]"
        ::= { ieeeC37238StatClockParentDSEntry 4 }

    ieeeC37238StatClockParentDSGMClockPriority2 OBJECT-TYPE
        SYNTAX          Unsigned32
        MAX-ACCESS      read-only
        STATUS          current
        DESCRIPTION
                "This object specifies the parentDS grandmaster clock
                 priority2."
        REFERENCE
                "Section 8.2.3.9 ('parentDS.grandmasterPriority2') of
                 [IEEE-1588-2008]"
        ::= { ieeeC37238StatClockParentDSEntry 5 }

    ieeeC37238StatClockParentDSGMClockQualityClass OBJECT-TYPE
        SYNTAX          PtpClockQualityClassType
        MAX-ACCESS      read-only
        STATUS          current
        DESCRIPTION
                "This object specifies the parentDS grandmaster clock
                 quality class."
        REFERENCE
                "Section 8.2.3.7 ('parentDS.grandmasterClockQuality') of
                 [IEEE-1588-2008]"
        ::= { ieeeC37238StatClockParentDSEntry 6 }

    ieeeC37238StatClockParentDSGMClockQualityAccuracy OBJECT-TYPE
        SYNTAX          PtpClockQualityAccuracyType
        MAX-ACCESS      read-only
        STATUS          current
        DESCRIPTION
                "This object specifies the parentDS grandmaster clock
                 quality accuracy."
        REFERENCE
                "Section 8.2.3.7 ('parentDS.grandmasterClockQuality') of
                 [IEEE-1588-2008]"
        ::= { ieeeC37238StatClockParentDSEntry 7 }

    ieeeC37238StatClockParentDSParentPortNumber OBJECT-TYPE
        SYNTAX          PtpClockPortNumber
        MAX-ACCESS      read-only
        STATUS          current
        DESCRIPTION
                "This object specifies the parentDS PTP portNumber"
        ::= { ieeeC37238StatClockParentDSEntry 8 }

    ieeeC37238StatClockPortRunningTable OBJECT-TYPE
        SYNTAX          SEQUENCE OF IeeeC37238StatClockPortRunningEntry
        MAX-ACCESS      not-accessible
        STATUS          current
        DESCRIPTION
                "Table of information about the clock ports running datasets for
                 a particular domain."
        ::= { ieeeC37238StatClock 3 }

    ieeeC37238StatClockPortRunningEntry OBJECT-TYPE
        SYNTAX          IeeeC37238StatClockPortRunningEntry
        MAX-ACCESS      not-accessible
        STATUS          current
        DESCRIPTION
                "A table entry that contains running dataset information
                 about a single clock port."
        INDEX { ieeeC37238StatClockPortRunningPortNumberIndex }
        ::= { ieeeC37238StatClockPortRunningTable 1 }

    IeeeC37238StatClockPortRunningEntry ::=
        SEQUENCE {
            ieeeC37238StatClockPortRunningPortNumberIndex    PtpClockPortNumber,
            ieeeC37238StatClockPortRunningState              INTEGER,
            ieeeC37238StatClockPortRunningPeerMeanPathDelay  PtpClockTimeInterval
        }

    ieeeC37238StatClockPortRunningPortNumberIndex OBJECT-TYPE
        SYNTAX          PtpClockPortNumber
        MAX-ACCESS      not-accessible
        STATUS          current
        DESCRIPTION
                "This object specifies the PTP portNumber associated with this
                 clock port."
        ::= { ieeeC37238StatClockPortRunningEntry 1 }

    ieeeC37238StatClockPortRunningState OBJECT-TYPE
        SYNTAX          INTEGER  {
                            initializing(1),
                            faulty(2),
                            disabled(3),
                            listening(4),
                            preMaster(5),
                            master(6),
                            passive(7),
                            uncalibrated(8),
                            slave(9),
                            TransmittingSynchronized(10),
                            ReceivingSynchronized (11)
                        }
        MAX-ACCESS      read-only
        STATUS          current
        DESCRIPTION
                "This object specifies the port state returned by PTP engine:

                initializing
                faulty
                disabled
                listening
                preMaster
                master
                passive
                uncalibrated
                slave
                TransmittingSynchronized
                ReceivingSynchronized       "
        ::= { ieeeC37238StatClockPortRunningEntry 2 }

    ieeeC37238StatClockPortRunningPeerMeanPathDelay OBJECT-TYPE
        SYNTAX          PtpClockTimeInterval
        UNITS           "Time Interval"
        MAX-ACCESS      read-only
        STATUS          current
        DESCRIPTION
                "This object specifies the peer meanPathDelay."
        ::= { ieeeC37238StatClockPortRunningEntry 3 }

END
