-- ****************************************************************
-- *  Moxa General (Network Configuration) - DHCP SERVER PRIVATE MIB
-- *
-- *  Copyright (c) 2019 by Moxa Inc.
-- *  All rights reserved.
-- *****************************************************************

MOXA-DHCP-SERVER-MIB DEFINITIONS ::= BEGIN
    IMPORTS
        MODULE-IDENTITY, NOTIFICATION-TYPE, OBJECT-TYPE, IpAddress, Unsigned32,
        enterprises
            FROM SNMPv2-SMI
        TEXTUAL-CONVENTION, DateAndTime, MacAddress, DisplayString, TruthValue, RowStatus
            FROM SNMPv2-TC;

    mxDhcpSrv MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa DHCP server"

        REVISION    "202202170000Z"
        DESCRIPTION "update CONTACT-INFO"

        REVISION    "201906300000Z"
        DESCRIPTION "Initial Revision"

        ::= { networkConfiguration 2 }

    moxa                 OBJECT IDENTIFIER ::= { enterprises 8691 }
    general              OBJECT IDENTIFIER ::= { moxa 602 }
    networkConfiguration OBJECT IDENTIFIER ::= { general 2 }

-- -------------------------------------------------------------
-- groups in the MOXA-DHCP-SERVER-MIB MIB
-- -------------------------------------------------------------

    -- dsNotification  OBJECT IDENTIFIER ::= { mxDhcpSrv 0 }
    dsConfiguration OBJECT IDENTIFIER ::= { mxDhcpSrv 1 }
    dsStatus        OBJECT IDENTIFIER ::= { mxDhcpSrv 2 }
    -- dsExtensions     OBJECT IDENTIFIER ::= { mxDhcpSrv 3 }

-- -------------------------------------------------------------
-- configuration group
-- -------------------------------------------------------------

-- -------------------------------------------------------------
-- General
-- -------------------------------------------------------------

    dsConfigMode OBJECT-TYPE
        SYNTAX      INTEGER {
                        disable                     (1),
                        dhcpAndMacBasedIpAssignment (2),
                        portBasedIpAssignment       (3)
                    }
        MAX-ACCESS  read-write
        STATUS      current
        DESCRIPTION
            "Configure DHCP server operation mode"
        ::= { dsConfiguration 1 }

-- -------------------------------------------------------------
-- DHCP
-- -------------------------------------------------------------

    dsConfigDhcpTable OBJECT-TYPE
        SYNTAX SEQUENCE OF DsConfigDhcpEntry
        MAX-ACCESS not-accessible
        STATUS current
        DESCRIPTION
            "Table of the DHCP pools configuration."
        ::= { dsConfiguration 2 }

    dsConfigDhcpEntry OBJECT-TYPE
      SYNTAX DsConfigDhcpEntry
      MAX-ACCESS not-accessible
      STATUS current
      DESCRIPTION
          "An entry for a DHCP pool configuration."
      INDEX { dsConfigDhcpIndex }
      ::= { dsConfigDhcpTable 1 }

    DsConfigDhcpEntry ::=
        SEQUENCE {
            dsConfigDhcpIndex     Unsigned32,
            dsConfigDhcpEnable    TruthValue,
            dsConfigDhcpStartIp   IpAddress,
            dsConfigDhcpEndIp     IpAddress,
            dsConfigDhcpNetmask   IpAddress,
            dsConfigDhcpLeaseTime Unsigned32,
            dsConfigDhcpGateway   IpAddress,
            dsConfigDhcpNtp       IpAddress,
            dsConfigDhcpDns1      IpAddress,
            dsConfigDhcpDns2      IpAddress,
            dsConfigDhcpRowStatus RowStatus
        }

    dsConfigDhcpIndex OBJECT-TYPE
        SYNTAX      Unsigned32
        MAX-ACCESS  not-accessible
        STATUS      current
        DESCRIPTION
            "Index of a DHCP pool configuration."
         ::= { dsConfigDhcpEntry 1 }

    dsConfigDhcpEnable OBJECT-TYPE
        SYNTAX      TruthValue
        MAX-ACCESS  read-create
        STATUS      current
        DESCRIPTION
            "Enables or disables the DHCP pool."
         ::= { dsConfigDhcpEntry 2 }

    dsConfigDhcpStartIp OBJECT-TYPE
        SYNTAX      IpAddress
        MAX-ACCESS  read-create
        STATUS      current
        DESCRIPTION
            "Start IP address for the DHCP pool."
         ::= { dsConfigDhcpEntry 3 }

    dsConfigDhcpEndIp OBJECT-TYPE
        SYNTAX      IpAddress
        MAX-ACCESS  read-create
        STATUS      current
        DESCRIPTION
            "End IP address for the DHCP pool."
         ::= { dsConfigDhcpEntry 4 }

    dsConfigDhcpNetmask OBJECT-TYPE
        SYNTAX      IpAddress
        MAX-ACCESS  read-create
        STATUS      current
        DESCRIPTION
            "Subnet mask for the DHCP pool."
         ::= { dsConfigDhcpEntry 5 }

    dsConfigDhcpLeaseTime OBJECT-TYPE
        SYNTAX      Unsigned32 (10..604800)
        MAX-ACCESS  read-create
        STATUS      current
        DESCRIPTION
            "Lease time (10-604800 seconds) for the DHCP pool."
         ::= { dsConfigDhcpEntry 6 }

    dsConfigDhcpGateway OBJECT-TYPE
        SYNTAX      IpAddress
        MAX-ACCESS  read-create
        STATUS      current
        DESCRIPTION
            "Default gateway IP address for the DHCP pool."
         ::= { dsConfigDhcpEntry 7 }

    dsConfigDhcpNtp OBJECT-TYPE
        SYNTAX      IpAddress
        MAX-ACCESS  read-create
        STATUS      current
        DESCRIPTION
            "NTP server IP address for the DHCP pool."
         ::= { dsConfigDhcpEntry 8 }

    dsConfigDhcpDns1 OBJECT-TYPE
        SYNTAX      IpAddress
        MAX-ACCESS  read-create
        STATUS      current
        DESCRIPTION
            "First DNS server IP address for the DHCP pool."
         ::= { dsConfigDhcpEntry 9 }

    dsConfigDhcpDns2 OBJECT-TYPE
        SYNTAX      IpAddress
        MAX-ACCESS  read-create
        STATUS      current
        DESCRIPTION
            "Second DNS server IP address for the DHCP pool."
         ::= { dsConfigDhcpEntry 10 }

    dsConfigDhcpRowStatus OBJECT-TYPE
        SYNTAX      RowStatus
        MAX-ACCESS  read-create
        STATUS      current
        DESCRIPTION
            "The status column used for creating, modifying, and deleting entries of the DHCP pool."
        ::= { dsConfigDhcpEntry 11 }

-- -------------------------------------------------------------
-- MAC-based IP Assignment
-- -------------------------------------------------------------

    dsConfigMacBasedIpTable OBJECT-TYPE
        SYNTAX SEQUENCE OF DsConfigMacBasedIpEntry
        MAX-ACCESS not-accessible
        STATUS current
        DESCRIPTION
            "Table of the MAC-based IP assignment configuration."
        ::= { dsConfiguration 3 }

    dsConfigMacBasedIpEntry OBJECT-TYPE
      SYNTAX DsConfigMacBasedIpEntry
      MAX-ACCESS not-accessible
      STATUS current
      DESCRIPTION
          "An entry for a MAC-based IP assignment configuration."
      INDEX { dsConfigMacBasedIpIndex }
      ::= { dsConfigMacBasedIpTable 1 }

    DsConfigMacBasedIpEntry ::=
        SEQUENCE {
            dsConfigMacBasedIpIndex     Unsigned32,
            dsConfigMacBasedIpEnable    TruthValue,
            dsConfigMacBasedIpHostName  DisplayString,
            dsConfigMacBasedIpMacAddr   MacAddress,
            dsConfigMacBasedIpIpAddr    IpAddress,
            dsConfigMacBasedIpNetmask   IpAddress,
            dsConfigMacBasedIpLeaseTime Unsigned32,
            dsConfigMacBasedIpGateway   IpAddress,
            dsConfigMacBasedIpNtp       IpAddress,
            dsConfigMacBasedIpDns1      IpAddress,
            dsConfigMacBasedIpDns2      IpAddress,
            dsConfigMacBasedIpRowStatus RowStatus
        }

    dsConfigMacBasedIpIndex OBJECT-TYPE
        SYNTAX      Unsigned32
        MAX-ACCESS  not-accessible
        STATUS      current
        DESCRIPTION
            "Index of a MAC-based IP assignment configuration."
         ::= { dsConfigMacBasedIpEntry 1 }

    dsConfigMacBasedIpEnable OBJECT-TYPE
        SYNTAX      TruthValue
        MAX-ACCESS  read-create
        STATUS      current
        DESCRIPTION
            "Enables or disables the MAC-based IP assignment."
         ::= { dsConfigMacBasedIpEntry 2 }

    dsConfigMacBasedIpHostName OBJECT-TYPE
        SYNTAX      DisplayString
        MAX-ACCESS  read-create
        STATUS      current
        DESCRIPTION
            "DHCP option 12 host name for the MAC-based IP assignment."
         ::= { dsConfigMacBasedIpEntry 3 }

    dsConfigMacBasedIpMacAddr OBJECT-TYPE
        SYNTAX      MacAddress
        MAX-ACCESS  read-create
        STATUS      current
        DESCRIPTION
            "MAC address for the MAC-based IP assignment."
         ::= { dsConfigMacBasedIpEntry 4 }

    dsConfigMacBasedIpIpAddr OBJECT-TYPE
        SYNTAX      IpAddress
        MAX-ACCESS  read-create
        STATUS      current
        DESCRIPTION
            "IP address for the MAC-based IP assignment."
         ::= { dsConfigMacBasedIpEntry 5 }

    dsConfigMacBasedIpNetmask OBJECT-TYPE
        SYNTAX      IpAddress
        MAX-ACCESS  read-create
        STATUS      current
        DESCRIPTION
            "Subnet mask for the MAC-based IP assignment."
         ::= { dsConfigMacBasedIpEntry 6 }

    dsConfigMacBasedIpLeaseTime OBJECT-TYPE
        SYNTAX      Unsigned32 (10..604800)
        MAX-ACCESS  read-create
        STATUS      current
        DESCRIPTION
            "Lease time (10-604800 seconds) for the MAC-based IP assignment."
         ::= { dsConfigMacBasedIpEntry 7 }

    dsConfigMacBasedIpGateway OBJECT-TYPE
        SYNTAX      IpAddress
        MAX-ACCESS  read-create
        STATUS      current
        DESCRIPTION
            "Default gateway IP address for the MAC-based IP assignment."
         ::= { dsConfigMacBasedIpEntry 8 }

    dsConfigMacBasedIpNtp OBJECT-TYPE
        SYNTAX      IpAddress
        MAX-ACCESS  read-create
        STATUS      current
        DESCRIPTION
            "NTP server IP address for the MAC-based IP assignment."
         ::= { dsConfigMacBasedIpEntry 9 }

    dsConfigMacBasedIpDns1 OBJECT-TYPE
        SYNTAX      IpAddress
        MAX-ACCESS  read-create
        STATUS      current
        DESCRIPTION
            "First DNS server IP address for the MAC-based IP assignment."
         ::= { dsConfigMacBasedIpEntry 10 }

    dsConfigMacBasedIpDns2 OBJECT-TYPE
        SYNTAX      IpAddress
        MAX-ACCESS  read-create
        STATUS      current
        DESCRIPTION
            "Second DNS server IP address for the MAC-based IP assignment."
         ::= { dsConfigMacBasedIpEntry 11 }

    dsConfigMacBasedIpRowStatus OBJECT-TYPE
        SYNTAX      RowStatus
        MAX-ACCESS  read-create
        STATUS      current
        DESCRIPTION
            "The status column used for creating, modifying, and deleting entries of the MAC-based IP assignment."
        ::= { dsConfigMacBasedIpEntry 12 }

-- -------------------------------------------------------------
-- Port-based IP Assignment
-- -------------------------------------------------------------

    dsConfigPortBasedIpTable OBJECT-TYPE
        SYNTAX SEQUENCE OF DsConfigPortBasedIpEntry
        MAX-ACCESS not-accessible
        STATUS current
        DESCRIPTION
            "Table of the Port-based IP assignment configuration."
        ::= { dsConfiguration 4 }

    dsConfigPortBasedIpEntry OBJECT-TYPE
      SYNTAX DsConfigPortBasedIpEntry
      MAX-ACCESS not-accessible
      STATUS current
      DESCRIPTION
          "An entry for a Port-based IP assignment configuration."
      INDEX { dsConfigPortBasedIpIndex }
      ::= { dsConfigPortBasedIpTable 1 }

    DsConfigPortBasedIpEntry ::=
        SEQUENCE {
            dsConfigPortBasedIpIndex     Unsigned32,
            dsConfigPortBasedIpEnable    TruthValue,
            dsConfigPortBasedIpPortNum   Unsigned32,
            dsConfigPortBasedIpIpAddr    IpAddress,
            dsConfigPortBasedIpNetmask   IpAddress,
            dsConfigPortBasedIpLeaseTime Unsigned32,
            dsConfigPortBasedIpGateway   IpAddress,
            dsConfigPortBasedIpNtp       IpAddress,
            dsConfigPortBasedIpDns1      IpAddress,
            dsConfigPortBasedIpDns2      IpAddress,
            dsConfigPortBasedIpRowStatus RowStatus
        }

    dsConfigPortBasedIpIndex OBJECT-TYPE
        SYNTAX      Unsigned32
        MAX-ACCESS  not-accessible
        STATUS      current
        DESCRIPTION
            "Index of a Port-based IP assignment configuration."
         ::= { dsConfigPortBasedIpEntry 1 }

    dsConfigPortBasedIpEnable OBJECT-TYPE
        SYNTAX      TruthValue
        MAX-ACCESS  read-create
        STATUS      current
        DESCRIPTION
            "Enables or disables the Port-based IP assignment."
         ::= { dsConfigPortBasedIpEntry 2 }

    dsConfigPortBasedIpPortNum OBJECT-TYPE
        SYNTAX      Unsigned32
        MAX-ACCESS  read-create
        STATUS      current
        DESCRIPTION
            "The port number for the Port-based IP assignment."
         ::= { dsConfigPortBasedIpEntry 3 }

    dsConfigPortBasedIpIpAddr OBJECT-TYPE
        SYNTAX      IpAddress
        MAX-ACCESS  read-create
        STATUS      current
        DESCRIPTION
            "IP address for the Port-based IP assignment."
         ::= { dsConfigPortBasedIpEntry 4 }

    dsConfigPortBasedIpNetmask OBJECT-TYPE
        SYNTAX      IpAddress
        MAX-ACCESS  read-create
        STATUS      current
        DESCRIPTION
            "Subnet mask for the Port-based IP assignment."
         ::= { dsConfigPortBasedIpEntry 5 }

    dsConfigPortBasedIpLeaseTime OBJECT-TYPE
        SYNTAX      Unsigned32 (10..604800)
        MAX-ACCESS  read-create
        STATUS      current
        DESCRIPTION
            "Lease time (10-604800 seconds) for the Port-based IP assignment."
         ::= { dsConfigPortBasedIpEntry 6 }

    dsConfigPortBasedIpGateway OBJECT-TYPE
        SYNTAX      IpAddress
        MAX-ACCESS  read-create
        STATUS      current
        DESCRIPTION
            "Default gateway IP address for the Port-based IP assignment."
         ::= { dsConfigPortBasedIpEntry 7 }

    dsConfigPortBasedIpNtp OBJECT-TYPE
        SYNTAX      IpAddress
        MAX-ACCESS  read-create
        STATUS      current
        DESCRIPTION
            "NTP server IP address for the Port-based IP assignment."
         ::= { dsConfigPortBasedIpEntry 8 }

    dsConfigPortBasedIpDns1 OBJECT-TYPE
        SYNTAX      IpAddress
        MAX-ACCESS  read-create
        STATUS      current
        DESCRIPTION
            "First DNS server IP address for the Port-based IP assignment."
         ::= { dsConfigPortBasedIpEntry 9 }

    dsConfigPortBasedIpDns2 OBJECT-TYPE
        SYNTAX      IpAddress
        MAX-ACCESS  read-create
        STATUS      current
        DESCRIPTION
            "Second DNS server IP address for the Port-based IP assignment."
         ::= { dsConfigPortBasedIpEntry 10 }

    dsConfigPortBasedIpRowStatus OBJECT-TYPE
        SYNTAX      RowStatus
        MAX-ACCESS  read-create
        STATUS      current
        DESCRIPTION
            "The status column used for creating, modifying, and deleting entries of the Port-based IP assignment."
        ::= { dsConfigPortBasedIpEntry 11 }

-- -------------------------------------------------------------
-- Status group
-- -------------------------------------------------------------

-- -------------------------------------------------------------
-- Lease table
-- -------------------------------------------------------------

    dsStatLeaseTable OBJECT-TYPE
        SYNTAX SEQUENCE OF DsStatLeaseEntry
        MAX-ACCESS not-accessible
        STATUS current
        DESCRIPTION
            "Table of the DHCP server leases."
        ::= { dsStatus 1 }

    dsStatLeaseEntry OBJECT-TYPE
      SYNTAX DsStatLeaseEntry
      MAX-ACCESS not-accessible
      STATUS current
      DESCRIPTION
          "An entry for a lease."
      INDEX { dsStatLeaseIndex }
      ::= { dsStatLeaseTable 1 }

    DsStatLeaseEntry ::=
        SEQUENCE {
            dsStatLeaseIndex    Unsigned32,
            dsStatLeaseHostName DisplayString,
            dsStatLeaseIpAddr   IpAddress,
            dsStatLeaseMacAddr  MacAddress,
            dsStatLeaseTimeLeft DisplayString
        }

    dsStatLeaseIndex OBJECT-TYPE
        SYNTAX      Unsigned32
        MAX-ACCESS  not-accessible
        STATUS      current
        DESCRIPTION
            "Index of a lease entry."
         ::= { dsStatLeaseEntry 1 }

    dsStatLeaseHostName OBJECT-TYPE
        SYNTAX      DisplayString
        MAX-ACCESS  read-only
        STATUS      current
        DESCRIPTION
            "DHCP option 12 host name for the lease."
         ::= { dsStatLeaseEntry 2 }

    dsStatLeaseIpAddr OBJECT-TYPE
        SYNTAX      DisplayString
        MAX-ACCESS  read-only
        STATUS      current
        DESCRIPTION
            "IP address for the lease."
         ::= { dsStatLeaseEntry 3 }

    dsStatLeaseMacAddr OBJECT-TYPE
        SYNTAX      DisplayString
        MAX-ACCESS  read-only
        STATUS      current
        DESCRIPTION
            "MAC address for the lease."
         ::= { dsStatLeaseEntry 4 }

    dsStatLeaseTimeLeft OBJECT-TYPE
        SYNTAX      DisplayString
        MAX-ACCESS  read-only
        STATUS      current
        DESCRIPTION
            "Time left for the lease."
         ::= { dsStatLeaseEntry 5 }

END
