-- ****************************************************************
-- *  Moxa General (Events) - General Event (GENE) PRIVATE MIB
-- *
-- *  Copyright (c) 2019 by Moxa Inc.
-- *  All rights reserved.
-- *****************************************************************

MOXA-GENERAL-EVENT-MIB DEFINITIONS ::= BEGIN
    IMPORTS
        MODULE-IDENTITY, NOTIFICATION-TYPE,
        enterprises, OBJECT-TYPE, IpAddress, Unsigned32
            FROM SNMPv2-SMI
        TEXTUAL-CONVENTION, DateAndTime, MacAddress, DisplayString, TruthValue, RowStatus
            FROM SNMPv2-TC
        eventNotification
            FROM MOXA-GENERAL-MIB;

    mxGeneralEvent MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa event notification general event"

        REVISION    "202202170000Z"
        DESCRIPTION "update CONTACT-INFO"

        REVISION    "202109290000Z"
        DESCRIPTION
            "Add OIDs:
                 geneConfigColdStartRelayEnable
                 geneConfigWarmStartRelayEnable
                 geneConfigConfigChangedRelayEnable
                 geneConfigConfigImportedRelayEnable
                 geneConfigLogCapacityThresholdRelayEnable
                 geneConfigLoginSuccessRelayEnable
                 geneConfigLoginFailRelayEnable
                 geneConfigLoginLockoutRelayEnable
                 geneConfigAccountSettingChangedRelayEnable
                 geneConfigPasswordChangedRelayEnable
                 geneConfigSslCertificationChangedRelayEnable
                 geneConfigPowerOnRelayEnable
                 geneConfigPowerOffRelayEnable
                 geneConfigDiOnRelayEnable
                 geneConfigDiOffRelayEnable"

        REVISION    "202105100000Z"
        DESCRIPTION "correct the name of Dying Gasp's OID"

        REVISION    "201906300000Z"
        DESCRIPTION "Initial Revision"

        ::= { mxEvents 1 }

    moxa                 OBJECT IDENTIFIER ::= { enterprises 8691 }
    general              OBJECT IDENTIFIER ::= { moxa 602 }
    eventNotification    OBJECT IDENTIFIER ::= { general 7 }
    mxEvents             OBJECT IDENTIFIER ::= { eventNotification 1 }

-- -------------------------------------------------------------
-- groups in the MOXA-GENERAL-EVENT-MIB MIB
-- -------------------------------------------------------------

  geneNotification      OBJECT IDENTIFIER ::= { mxGeneralEvent 0 }
  geneConfiguration     OBJECT IDENTIFIER ::= { mxGeneralEvent 1 }
  geneStatus            OBJECT IDENTIFIER ::= { mxGeneralEvent 2 }
  -- geneExtensions        OBJECT IDENTIFIER ::= { mxGeneralEvent 3 }

-- -------------------------------------------------------------
-- configuration group
-- -------------------------------------------------------------
-- Cold Start

    geneConfigColdStart OBJECT IDENTIFIER ::= { geneConfiguration 1 }

    geneConfigColdStartEnable OBJECT-TYPE
        SYNTAX TruthValue
        MAX-ACCESS read-write
        STATUS current
        DESCRIPTION
            "This enables or disables the event Cold Start in the event notification.
            A value of 'true' (1) indicates that notifications are
            allowed to notify the user while the system cold started.
            A value of 'false'(2) indicates that notifications are not
            allowed to notify the user while the system cold started."
        ::= { geneConfigColdStart 1 }

    geneConfigColdStartAction OBJECT IDENTIFIER ::= { geneConfigColdStart 2 }

    geneConfigColdStartTrapEnable OBJECT-TYPE
        SYNTAX TruthValue
        MAX-ACCESS read-write
        STATUS current
        DESCRIPTION
            "This enables or disables the notification action trap in the event Cold Start.
            A value of 'true' (1) indicates that the notification action trap is
            allowed to notify the user while the system cold started.
            A value of 'false'(2) indicates that the notification action trap is not
            allowed to notify the user while the system cold started."
        ::= { geneConfigColdStartAction 1 }

    geneConfigColdStartEmailEnable OBJECT-TYPE
        SYNTAX TruthValue
        MAX-ACCESS read-write
        STATUS current
        DESCRIPTION
            "This enables or disables the notification action email in the event Cold Start.
            A value of 'true' (1) indicates that the notification action email is
            allowed to notify the user while the system cold started.
            A value of 'false'(2) indicates that the notification action email is not
            allowed to notify the user while the system cold started."
        ::= { geneConfigColdStartAction 2 }

    geneConfigColdStartMgmtRelayEnable OBJECT-TYPE
        SYNTAX TruthValue
        MAX-ACCESS read-write
        STATUS current
        DESCRIPTION
            "This enables or disables the notification action MGMT relay in the event Cold Start.
            A value of 'true' (1) indicates that the notification action MGMT relay is
            allowed to notify the user while the system cold started.
            A value of 'false'(2) indicates that the notification action MGMT relay is not
            allowed to notify the user while the system cold started."
        ::= { geneConfigColdStartAction 3 }

    geneConfigColdStartPwr1RelayEnable OBJECT-TYPE
        SYNTAX TruthValue
        MAX-ACCESS read-write
        STATUS current
        DESCRIPTION
            "This enables or disables the notification action PWR1 relay in the event Cold Start.
            A value of 'true' (1) indicates that the notification action PWR1 relay is
            allowed to notify the user while the system cold started.
            A value of 'false'(2) indicates that the notification action PWR1 relay is not
            allowed to notify the user while the system cold started."
        ::= { geneConfigColdStartAction 4 }

    geneConfigColdStartPwr2RelayEnable OBJECT-TYPE
        SYNTAX TruthValue
        MAX-ACCESS read-write
        STATUS current
        DESCRIPTION
            "This enables or disables the notification action PWR2 relay in the event Cold Start.
            A value of 'true' (1) indicates that the notification action PWR2 relay is
            allowed to notify the user while the system cold started.
            A value of 'false'(2) indicates that the notification action PWR2 relay is not
            allowed to notify the user while the system cold started."
        ::= { geneConfigColdStartAction 5 }

    geneConfigColdStartRelayEnable OBJECT-TYPE
        SYNTAX TruthValue
        MAX-ACCESS read-write
        STATUS current
        DESCRIPTION
            "This enables or disables the notification action relay in the event Cold Start. 
            A value of 'true' (1) indicates that the notification action relay is  allowed to notify the user while the system cold started.
            A value of 'false'(2) indicates that the notification action relay is not allowed to notify the user while the system cold started."
        ::= { geneConfigColdStartAction 6 }

-- Warm Start

    geneConfigWarmStart OBJECT IDENTIFIER ::= { geneConfiguration 2 }

    geneConfigWarmStartEnable OBJECT-TYPE
        SYNTAX TruthValue
        MAX-ACCESS read-write
        STATUS current
        DESCRIPTION
            "This enables or disables the event Warm Start in the event notification.
            A value of 'true' (1) indicates that notifications are
            allowed to notify the user while the system warm started.
            A value of 'false'(2) indicates that notifications are not
            allowed to notify the user while the system warm started."
        ::= { geneConfigWarmStart 1 }

    geneConfigWarmStartAction OBJECT IDENTIFIER ::= { geneConfigWarmStart 2 }

    geneConfigWarmStartTrapEnable OBJECT-TYPE
        SYNTAX TruthValue
        MAX-ACCESS read-write
        STATUS current
        DESCRIPTION
            "This enables or disables the notification action trap in the event Warm Start.
            A value of 'true' (1) indicates that the notification action trap is
            allowed to notify the user while the system warm started.
            A value of 'false'(2) indicates that the notification action trap is not
            allowed to notify the user while the system warm started."
        ::= { geneConfigWarmStartAction 1 }

    geneConfigWarmStartEmailEnable OBJECT-TYPE
        SYNTAX TruthValue
        MAX-ACCESS read-write
        STATUS current
        DESCRIPTION
            "This enables or disables the notification action email in the event Warm Start.
            A value of 'true' (1) indicates that the notification action email is
            allowed to notify the user while the system warm started.
            A value of 'false'(2) indicates that the notification action email is not
            allowed to notify the user while the system warm started."
        ::= { geneConfigWarmStartAction 2 }

    geneConfigWarmStartMgmtRelayEnable OBJECT-TYPE
        SYNTAX TruthValue
        MAX-ACCESS read-write
        STATUS current
        DESCRIPTION
            "This enables or disables the notification action MGMT relay in the event Warm Start.
            A value of 'true' (1) indicates that the notification action MGMT relay is
            allowed to notify the user while the system warm started.
            A value of 'false'(2) indicates that the notification action MGMT relay is not
            allowed to notify the user while the system warm started"
        ::= { geneConfigWarmStartAction 3 }

    geneConfigWarmStartPwr1RelayEnable OBJECT-TYPE
        SYNTAX TruthValue
        MAX-ACCESS read-write
        STATUS current
        DESCRIPTION
            "This enables or disables the notification action PWR1 relay in the event Warm Start.
            A value of 'true' (1) indicates that the notification action PWR1 relay is
            allowed to notify the user while the system warm started.
            A value of 'false'(2) indicates that the notification action PWR1 relay is not
            allowed to notify the user while the system warm started"
        ::= { geneConfigWarmStartAction 4 }

    geneConfigWarmStartPwr2RelayEnable OBJECT-TYPE
        SYNTAX TruthValue
        MAX-ACCESS read-write
        STATUS current
        DESCRIPTION
            "This enables or disables the notification action PWR2 relay in the event Warm Start.
            A value of 'true' (1) indicates that the notification action PWR2 relay is
            allowed to notify the user while the system warm started.
            A value of 'false'(2) indicates that the notification action PWR2 relay is not
            allowed to notify the user while the system warm started."
        ::= { geneConfigWarmStartAction 5 }

    geneConfigWarmStartRelayEnable OBJECT-TYPE
        SYNTAX TruthValue
        MAX-ACCESS read-write
        STATUS current
        DESCRIPTION 
            "This enables or disables the notification action relay in the event Warm Start. 
            A value of 'true' (1) indicates that the notification action relay is allowed to notify the user while the system warm started.
            A value of 'false'(2) indicates that the notification action relay is not allowed to notify the user while the system warm started."
        ::= { geneConfigWarmStartAction 6 }

-- Configuration Changed

    geneConfigConfigChanged OBJECT IDENTIFIER ::= { geneConfiguration 3 }

    geneConfigConfigChangedEnable OBJECT-TYPE
        SYNTAX TruthValue
        MAX-ACCESS read-write
        STATUS current
        DESCRIPTION
            "This enables or disables the event Configuration Changed in the event notification.
            A value of 'true' (1) indicates that notifications are
            allowed to notify the user while the system configuration changed.
            A value of 'false'(2) indicates that notifications are not
            allowed to notify the user while the system configuration changed."
        ::= { geneConfigConfigChanged 1 }

    geneConfigConfigChangedAction OBJECT IDENTIFIER ::= { geneConfigConfigChanged 2 }

    geneConfigConfigChangedTrapEnable OBJECT-TYPE
        SYNTAX TruthValue
        MAX-ACCESS read-write
        STATUS current
        DESCRIPTION
            "This enables or disables the notification action trap in the event Configuration Changed.
            A value of 'true' (1) indicates that the notification action trap is
            allowed to notify the user while the system configuration changed.
            A value of 'false'(2) indicates that the notification action trap is not
            allowed to notify the user while the system configuration changed."
        ::= { geneConfigConfigChangedAction 1 }

    geneConfigConfigChangedEmailEnable OBJECT-TYPE
        SYNTAX TruthValue
        MAX-ACCESS read-write
        STATUS current
        DESCRIPTION
            "This enables or disables the notification action email in the event Configuration Changed.
            A value of 'true' (1) indicates that the notification action email is
            allowed to notify the user while the system configuration changed.
            A value of 'false'(2) indicates that the notification action email is not
            allowed to notify the user while the system configuration changed."
        ::= { geneConfigConfigChangedAction 2 }

    geneConfigConfigChangedMgmtRelayEnable OBJECT-TYPE
        SYNTAX TruthValue
        MAX-ACCESS read-write
        STATUS current
        DESCRIPTION
            "This enables or disables the notification action MGMT relay in the event Configuration Changed.
            A value of 'true' (1) indicates that the notification action MGMT relay is
            allowed to notify the user while the system configuration changed.
            A value of 'false'(2) indicates that the notification action MGMT relay is not
            allowed to notify the user while the system configuration changed."
        ::= { geneConfigConfigChangedAction 3 }


    geneConfigConfigChangedPwr1RelayEnable OBJECT-TYPE
        SYNTAX TruthValue
        MAX-ACCESS read-write
        STATUS current
        DESCRIPTION
            "This enables or disables the notification action PWR1 relay in the event Configuration Changed.
            A value of 'true' (1) indicates that the notification action PWR1 relay is
            allowed to notify the user while the system configuration changed.
            A value of 'false'(2) indicates that the notification action PWR1 relay is not
            allowed to notify the user while the system configuration changed."
        ::= { geneConfigConfigChangedAction 4 }

    geneConfigConfigChangedPwr2RelayEnable OBJECT-TYPE
        SYNTAX TruthValue
        MAX-ACCESS read-write
        STATUS current
        DESCRIPTION
            "This enables or disables the notification action PWR2 relay in the event Configuration Changed.
            A value of 'true' (1) indicates that the notification action PWR2 relay is
            allowed to notify the user while the system configuration changed.
            A value of 'false'(2) indicates that the notification action PWR2 relay is not
            allowed to notify the user while the system configuration changed."
        ::= { geneConfigConfigChangedAction 5 }

    geneConfigConfigChangedRelayEnable OBJECT-TYPE
        SYNTAX TruthValue
        MAX-ACCESS read-write
        STATUS current
        DESCRIPTION 
            "This enables or disables the notification action relay in the event Configuration Changed. 
            A value of 'true' (1) indicates that the notification action relay is allowed to notify the user while the system configuration changed.
            A value of 'false'(2) indicates that the notification action relay is not allowed to notify the user while the system configuration changed."
        ::= { geneConfigConfigChangedAction 6 }

-- Configuration Imported

    geneConfigConfigImported OBJECT IDENTIFIER ::= { geneConfiguration 4 }

    geneConfigConfigImportedEnable OBJECT-TYPE
        SYNTAX TruthValue
        MAX-ACCESS read-write
        STATUS current
        DESCRIPTION
            "This enables or disables the event Configuration Imported in the event notification.
            A value of 'true' (1) indicates that notifications are
            allowed to notify the user while the system configuration imported.
            A value of 'false'(2) indicates that notifications are not
            allowed to notify the user while the system configuration imported."
        ::= { geneConfigConfigImported 1 }

    geneConfigConfigImportedAction OBJECT IDENTIFIER ::= { geneConfigConfigImported 2 }

    geneConfigConfigImportedTrapEnable OBJECT-TYPE
        SYNTAX TruthValue
        MAX-ACCESS read-write
        STATUS current
        DESCRIPTION
            "This enables or disables the notification action trap in the event Configuration Imported.
            A value of 'true' (1) indicates that the notification action trap is
            allowed to notify the user while the system configuration imported.
            A value of 'false'(2) indicates that the notification action trap is not
            allowed to notify the user while the system configuration imported."
        ::= { geneConfigConfigImportedAction 1 }

    geneConfigConfigImportedEmailEnable OBJECT-TYPE
        SYNTAX TruthValue
        MAX-ACCESS read-write
        STATUS current
        DESCRIPTION
            "This enables or disables the notification action email in the event Configuration Imported.
            A value of 'true' (1) indicates that the notification action email is
            allowed to notify the user while the system configuration imported.
            A value of 'false'(2) indicates that the notification action email is not
            allowed to notify the user while the system configuration imported."
        ::= { geneConfigConfigImportedAction 2 }

    geneConfigConfigImportedMgmtRelayEnable OBJECT-TYPE
        SYNTAX TruthValue
        MAX-ACCESS read-write
        STATUS current
        DESCRIPTION
            "This enables or disables the notification action MGMT relay in the event Configuration Imported.
            A value of 'true' (1) indicates that the notification action MGMT relay is
            allowed to notify the user while the system configuration imported.
            A value of 'false'(2) indicates that the notification action MGMT relay is not
            allowed to notify the user while the system configuration imported."
        ::= { geneConfigConfigImportedAction 3 }

    geneConfigConfigImportedPwr1RelayEnable OBJECT-TYPE
        SYNTAX TruthValue
        MAX-ACCESS read-write
        STATUS current
        DESCRIPTION
            "This enables or disables the notification action PWR1 relay in the event Configuration Imported.
            A value of 'true' (1) indicates that the notification action PWR1 relay is
            allowed to notify the user while the system configuration imported.
            A value of 'false'(2) indicates that the notification action PWR1 relay is not
            allowed to notify the user while the system configuration imported."
        ::= { geneConfigConfigImportedAction 4 }

    geneConfigConfigImportedPwr2RelayEnable OBJECT-TYPE
        SYNTAX TruthValue
        MAX-ACCESS read-write
        STATUS current
        DESCRIPTION
            "This enables or disables the notification action PWR2 relay in the event Configuration Imported.
            A value of 'true' (1) indicates that the notification action PWR2 relay is
            allowed to notify the user while the system configuration imported.
            A value of 'false'(2) indicates that the notification action PWR2 relay is not
            allowed to notify the user while the system configuration imported."
        ::= { geneConfigConfigImportedAction 5 }

    geneConfigConfigImportedRelayEnable OBJECT-TYPE
        SYNTAX TruthValue
        MAX-ACCESS read-write
        STATUS current
        DESCRIPTION 
            "This enables or disables the notification action relay in the event Configuration Imported. 
            A value of 'true' (1) indicates that the notification action relay is allowed to notify the user while the system configuration imported.
            A value of 'false'(2) indicates that the notification action relay is not allowed to notify the user while the system configuration imported."
        ::= { geneConfigConfigImportedAction 6 }

-- Log Capacity Threshold

    geneConfigLogCapacityThreshold OBJECT IDENTIFIER ::= { geneConfiguration 5 }

    geneConfigLogCapacityThresholdEnable OBJECT-TYPE
        SYNTAX TruthValue
        MAX-ACCESS read-write
        STATUS current
        DESCRIPTION
            "This enables or disables the event Log Capacity Threshold in the event notification.
            A value of 'true' (1) indicates that notifications are
            allowed to notify the user while the system reach log capacity threshold.
            A value of 'false'(2) indicates that notifications are not
            allowed to notify the user while the system reach log capacity threshold."
        ::= { geneConfigLogCapacityThreshold 1 }

    geneConfigLogCapacityThresholdAction OBJECT IDENTIFIER ::= { geneConfigLogCapacityThreshold 2 }

    geneConfigLogCapacityThresholdTrapEnable OBJECT-TYPE
        SYNTAX TruthValue
        MAX-ACCESS read-write
        STATUS current
        DESCRIPTION
            "This enables or disables the notification action trap in the event Log Capacity Threshold.
            A value of 'true' (1) indicates that the notification action trap is
            allowed to notify the user while the system reach log capacity threshold.
            A value of 'false'(2) indicates that the notification action trap is not
            allowed to notify the user while the system reach log capacity threshold."
        ::= { geneConfigLogCapacityThresholdAction 1 }

    geneConfigLogCapacityThresholdEmailEnable OBJECT-TYPE
        SYNTAX TruthValue
        MAX-ACCESS read-write
        STATUS current
        DESCRIPTION
            "This enables or disables the notification action email in the event Log Capacity Threshold.
            A value of 'true' (1) indicates that the notification action email is
            allowed to notify the user while the system reach log capacity threshold.
            A value of 'false'(2) indicates that the notification action email is not
            allowed to notify the user while the system reach log capacity threshold."
        ::= { geneConfigLogCapacityThresholdAction 2 }

    geneConfigLogCapacityThresholdMgmtRelayEnable OBJECT-TYPE
        SYNTAX TruthValue
        MAX-ACCESS read-write
        STATUS current
        DESCRIPTION
            "This enables or disables the notification action MGMT relay in the event Log Capacity Threshold.
            A value of 'true' (1) indicates that the notification action MGMT relay is
            allowed to notify the user while the system reach log capacity threshold.
            A value of 'false'(2) indicates that the notification action MGMT relay is not
            allowed to notify the user while the system reach log capacity threshold."
        ::= { geneConfigLogCapacityThresholdAction 3 }

    geneConfigLogCapacityThresholdPwr1RelayEnable OBJECT-TYPE
        SYNTAX TruthValue
        MAX-ACCESS read-write
        STATUS current
        DESCRIPTION
            "This enables or disables the notification action PWR1 relay in the event Log Capacity Threshold.
            A value of 'true' (1) indicates that the notification action PWR1 relay is
            allowed to notify the user while the system reach log capacity threshold.
            A value of 'false'(2) indicates that the notification action PWR1 relay is not
            allowed to notify the user while the system reach log capacity threshold."
        ::= { geneConfigLogCapacityThresholdAction 4 }

    geneConfigLogCapacityThresholdPwr2RelayEnable OBJECT-TYPE
        SYNTAX TruthValue
        MAX-ACCESS read-write
        STATUS current
        DESCRIPTION
            "This enables or disables the notification action PWR2 relay in the event Log Capacity Threshold.
            A value of 'true' (1) indicates that the notification action PWR2 relay is
            allowed to notify the user while the system reach log capacity threshold.
            A value of 'false'(2) indicates that the notification action PWR2 relay is not
            allowed to notify the user while the system reach log capacity threshold."
        ::= { geneConfigLogCapacityThresholdAction 5 }

    geneConfigLogCapacityThresholdRelayEnable OBJECT-TYPE
        SYNTAX TruthValue
        MAX-ACCESS read-write
        STATUS current
        DESCRIPTION 
            "This enables or disables the notification action relay in the event Log Capacity Threshold. 
            A value of 'true' (1) indicates that the notification action relay is allowed to notify the user while the system reach log capacity threshold.
            A value of 'false'(2) indicates that the notification action relay is not allowed to notify the user while the system reach log capacity threshold."
        ::= { geneConfigLogCapacityThresholdAction 6 }

-- Login Success

    geneConfigLoginSuccess OBJECT IDENTIFIER ::= { geneConfiguration 6 }

    geneConfigLoginSuccessEnable OBJECT-TYPE
        SYNTAX TruthValue
        MAX-ACCESS read-write
        STATUS current
        DESCRIPTION
            "This enables or disables the event Login Success in the event notification.
            A value of 'true' (1) indicates that notifications are
            allowed to notify the user while there is user login success in the device.
            A value of 'false'(2) indicates that notifications are not
            allowed to notify the user while there is user login success in the device."
        ::= { geneConfigLoginSuccess 1 }

    geneConfigLoginSuccessAction OBJECT IDENTIFIER ::= { geneConfigLoginSuccess 2 }

    geneConfigLoginSuccessTrapEnable OBJECT-TYPE
        SYNTAX TruthValue
        MAX-ACCESS read-write
        STATUS current
        DESCRIPTION
            "This enables or disables the notification action trap in the event Login Success.
            A value of 'true' (1) indicates that the notification action trap is
            allowed to notify the user while there is user login success in the device.
            A value of 'false'(2) indicates that the notification action trap is not
            allowed to notify the user while there is user login success in the device."
        ::= { geneConfigLoginSuccessAction 1 }

    geneConfigLoginSuccessEmailEnable OBJECT-TYPE
        SYNTAX TruthValue
        MAX-ACCESS read-write
        STATUS current
        DESCRIPTION
            "This enables or disables the notification action email in the event Login Success.
            A value of 'true' (1) indicates that the notification action email is
            allowed to notify the user while there is user login success in the device.
            A value of 'false'(2) indicates that the notification action email is not
            allowed to notify the user while there is user login success in the device."
        ::= { geneConfigLoginSuccessAction 2 }

    geneConfigLoginSuccessMgmtRelayEnable OBJECT-TYPE
        SYNTAX TruthValue
        MAX-ACCESS read-write
        STATUS current
        DESCRIPTION
            "This enables or disables the notification action MGMT relay in the event Login Success.
            A value of 'true' (1) indicates that the notification action MGMT relay is
            allowed to notify the user while there is user login success in the device.
            A value of 'false'(2) indicates that the notification action MGMT relay is not
            allowed to notify the user while there is user login success in the device."
        ::= { geneConfigLoginSuccessAction 3 }

    geneConfigLoginSuccessPwr1RelayEnable OBJECT-TYPE
        SYNTAX TruthValue
        MAX-ACCESS read-write
        STATUS current
        DESCRIPTION
            "This enables or disables the notification action PWR1 relay in the event Login Success.
            A value of 'true' (1) indicates that the notification action PWR1 relay is
            allowed to notify the user while there is user login success in the device.
            A value of 'false'(2) indicates that the notification action PWR1 relay is not
            allowed to notify the user while there is user login success in the device."
        ::= { geneConfigLoginSuccessAction 4 }

    geneConfigLoginSuccessPwr2RelayEnable OBJECT-TYPE
        SYNTAX TruthValue
        MAX-ACCESS read-write
        STATUS current
        DESCRIPTION
            "This enables or disables the notification action PWR2 relay in the event Login Success.
            A value of 'true' (1) indicates that the notification action PWR2 relay is
            allowed to notify the user while there is user login success in the device.
            A value of 'false'(2) indicates that the notification action PWR2 relay is not
            allowed to notify the user while there is user login success in the device."
        ::= { geneConfigLoginSuccessAction 5 }

    geneConfigLoginSuccessRelayEnable OBJECT-TYPE
        SYNTAX TruthValue
        MAX-ACCESS read-write
        STATUS current
        DESCRIPTION 
            "This enables or disables the notification action relay in the event Login Success. 
            A value of 'true' (1) indicates that the notification action relay is allowed to notify the user while there is user login success in the device.
            A value of 'false'(2) indicates that the notification action relay is not allowed to notify the user while there is user login success in the device."
        ::= { geneConfigLoginSuccessAction 6 }

-- Login Fail

    geneConfigLoginFail OBJECT IDENTIFIER ::= { geneConfiguration 7 }

    geneConfigLoginFailEnable OBJECT-TYPE
        SYNTAX TruthValue
        MAX-ACCESS read-write
        STATUS current
        DESCRIPTION
            "This enables or disables the event Login Fail in the event notification.
            A value of 'true' (1) indicates that notifications are
            allowed to notify the user while there is user login fail in the device.
            A value of 'false'(2) indicates that notifications are not
            allowed to notify the user while there is user login fail in the device."
        ::= { geneConfigLoginFail 1 }

    geneConfigLoginFailAction OBJECT IDENTIFIER ::= { geneConfigLoginFail 2 }

    geneConfigLoginFailTrapEnable OBJECT-TYPE
        SYNTAX TruthValue
        MAX-ACCESS read-write
        STATUS current
        DESCRIPTION
            "This enables or disables the notification action trap in the event Login Fail.
            A value of 'true' (1) indicates that the notification action trap is
            allowed to notify the user while there is user login fail in the device.
            A value of 'false'(2) indicates that the notification action trap is not
            allowed to notify the user while there is user login fail in the device."
        ::= { geneConfigLoginFailAction 1 }

    geneConfigLoginFailEmailEnable OBJECT-TYPE
        SYNTAX TruthValue
        MAX-ACCESS read-write
        STATUS current
        DESCRIPTION
            "This enables or disables the notification action email in the event Login Fail.
            A value of 'true' (1) indicates that the notification action email is
            allowed to notify the user while there is user login fail in the device.
            A value of 'false'(2) indicates that the notification action email is not
            allowed to notify the user while there is user login fail in the device."
        ::= { geneConfigLoginFailAction 2 }

    geneConfigLoginFailMgmtRelayEnable OBJECT-TYPE
        SYNTAX TruthValue
        MAX-ACCESS read-write
        STATUS current
        DESCRIPTION
            "This enables or disables the notification action MGMT relay in the event Login Fail.
            A value of 'true' (1) indicates that the notification action MGMT relay is
            allowed to notify the user while there is user login fail in the device.
            A value of 'false'(2) indicates that the notification action MGMT relay is not
            allowed to notify the user while there is user login fail in the device."
        ::= { geneConfigLoginFailAction 3 }

    geneConfigLoginFailPwr1RelayEnable OBJECT-TYPE
        SYNTAX TruthValue
        MAX-ACCESS read-write
        STATUS current
        DESCRIPTION
            "This enables or disables the notification action PWR1 relay in the event Login Fail.
            A value of 'true' (1) indicates that the notification action PWR1 relay is
            allowed to notify the user while there is user login fail in the device.
            A value of 'false'(2) indicates that the notification action PWR1 relay is not
            allowed to notify the user while there is user login fail in the device."
        ::= { geneConfigLoginFailAction 4 }

    geneConfigLoginFailPwr2RelayEnable OBJECT-TYPE
        SYNTAX TruthValue
        MAX-ACCESS read-write
        STATUS current
        DESCRIPTION
            "This enables or disables the notification action PWR2 relay in the event Login Fail.
            A value of 'true' (1) indicates that the notification action PWR2 relay is
            allowed to notify the user while there is user login fail in the device.
            A value of 'false'(2) indicates that the notification action PWR2 relay is not
            allowed to notify the user while there is user login fail in the device."
        ::= { geneConfigLoginFailAction 5 }

    geneConfigLoginFailRelayEnable OBJECT-TYPE
        SYNTAX TruthValue
        MAX-ACCESS read-write
        STATUS current
        DESCRIPTION 
            "This enables or disables the notification action relay in the event Login Fail. 
            A value of 'true' (1) indicates that the notification action relay is allowed to notify the user while there is user login fail in the device.
            A value of 'false'(2) indicates that the notification action relay is not allowed to notify the user while there is user login fail in the device."
        ::= { geneConfigLoginFailAction 6 }

-- Login Lockout

    geneConfigLoginLockout OBJECT IDENTIFIER ::= { geneConfiguration 8 }

    geneConfigLoginLockoutEnable OBJECT-TYPE
        SYNTAX TruthValue
        MAX-ACCESS read-write
        STATUS current
        DESCRIPTION
            "This enables or disables the event Login Lockout in the event notification.
            A value of 'true' (1) indicates that notifications are
            allowed to notify the user while the login failed reach the lockout threshold.
            A value of 'false'(2) indicates that notifications are not
            allowed to notify the user while the login failed reach the lockout threshold."
        ::= { geneConfigLoginLockout 1 }

    geneConfigLoginLockoutAction OBJECT IDENTIFIER ::= { geneConfigLoginLockout 2 }

    geneConfigLoginLockoutTrapEnable OBJECT-TYPE
        SYNTAX TruthValue
        MAX-ACCESS read-write
        STATUS current
        DESCRIPTION
            "This enables or disables the notification action trap in the event Login Lockout.
            A value of 'true' (1) indicates that the notification action trap is
            allowed to notify the user while the login failed reach the lockout threshold.
            A value of 'false'(2) indicates that the notification action trap is not
            allowed to notify the user while the login failed reach the lockout threshold."
        ::= { geneConfigLoginLockoutAction 1 }

    geneConfigLoginLockoutEmailEnable OBJECT-TYPE
        SYNTAX TruthValue
        MAX-ACCESS read-write
        STATUS current
        DESCRIPTION
            "This enables or disables the notification action email in the event Login Lockout.
            A value of 'true' (1) indicates that the notification action email is
            allowed to notify the user while the login failed reach the lockout threshold.
            A value of 'false'(2) indicates that the notification action email is not
            allowed to notify the user while the login failed reach the lockout threshold."
        ::= { geneConfigLoginLockoutAction 2 }

    geneConfigLoginLockoutMgmtRelayEnable OBJECT-TYPE
        SYNTAX TruthValue
        MAX-ACCESS read-write
        STATUS current
        DESCRIPTION
            "This enables or disables the notification action MGMT relay in the event Login Lockout.
            A value of 'true' (1) indicates that the notification action MGMT relay is
            allowed to notify the user while the login failed reach the lockout threshold.
            A value of 'false'(2) indicates that the notification action MGMT relay is not
            allowed to notify the user while the login failed reach the lockout threshold."
        ::= { geneConfigLoginLockoutAction 3 }

    geneConfigLoginLockoutPwr1RelayEnable OBJECT-TYPE
        SYNTAX TruthValue
        MAX-ACCESS read-write
        STATUS current
        DESCRIPTION
            "This enables or disables the notification action PWR1 relay in the event Login Lockout.
            A value of 'true' (1) indicates that the notification action PWR1 relay is
            allowed to notify the user while the login failed reach the lockout threshold.
            A value of 'false'(2) indicates that the notification action PWR1 relay is not
            allowed to notify the user while the login failed reach the lockout threshold."
        ::= { geneConfigLoginLockoutAction 4 }

    geneConfigLoginLockoutPwr2RelayEnable OBJECT-TYPE
        SYNTAX TruthValue
        MAX-ACCESS read-write
        STATUS current
        DESCRIPTION
            "This enables or disables the notification action PWR2 relay in the event Login Lockout.
            A value of 'true' (1) indicates that the notification action PWR2 relay is
            allowed to notify the user while the login failed reach the lockout threshold.
            A value of 'false'(2) indicates that the notification action PWR2 relay is not
            allowed to notify the user while the login failed reach the lockout threshold."
        ::= { geneConfigLoginLockoutAction 5 }

    geneConfigLoginLockoutRelayEnable OBJECT-TYPE
        SYNTAX TruthValue
        MAX-ACCESS read-write
        STATUS current
        DESCRIPTION 
            "This enables or disables the notification action relay in the event Login Lockout. 
            A value of 'true' (1) indicates that the notification action relay is allowed to notify the user while the login failed reach the lockout threshold.
            A value of 'false'(2) indicates that the notification action relay is not allowed to notify the user while the login failed reach the lockout threshold."
        ::= { geneConfigLoginLockoutAction 6 }

-- Account Setting Changed

    geneConfigAccountSettingChanged OBJECT IDENTIFIER ::= { geneConfiguration 9 }

    geneConfigAccountSettingChangedEnable OBJECT-TYPE
        SYNTAX TruthValue
        MAX-ACCESS read-write
        STATUS current
        DESCRIPTION
            "This enables or disables the event Account Setting Changed in the event notification.
            A value of 'true' (1) indicates that notifications are
            allowed to notify the user while the system account setting changed.
            A value of 'false'(2) indicates that notifications are not
            allowed to notify the user while the system account setting changed."
        ::= { geneConfigAccountSettingChanged 1 }

    geneConfigAccountSettingChangedAction OBJECT IDENTIFIER ::= { geneConfigAccountSettingChanged 2 }

    geneConfigAccountSettingChangedTrapEnable OBJECT-TYPE
        SYNTAX TruthValue
        MAX-ACCESS read-write
        STATUS current
        DESCRIPTION
            "This enables or disables the notification action trap in the event Account Setting Changed.
            A value of 'true' (1) indicates that the notification action trap is
            allowed to notify the user while the system account setting changed.
            A value of 'false'(2) indicates that the notification action trap is not
            allowed to notify the user while the system account setting changed."
        ::= { geneConfigAccountSettingChangedAction 1 }

    geneConfigAccountSettingChangedEmailEnable OBJECT-TYPE
        SYNTAX TruthValue
        MAX-ACCESS read-write
        STATUS current
        DESCRIPTION
            "This enables or disables the notification action email in the event Account Setting Changed.
            A value of 'true' (1) indicates that the notification action email is
            allowed to notify the user while the system account setting changed.
            A value of 'false'(2) indicates that the notification action email is not
            allowed to notify the user while the system account setting changed."
        ::= { geneConfigAccountSettingChangedAction 2 }

    geneConfigAccountSettingChangedMgmtRelayEnable OBJECT-TYPE
        SYNTAX TruthValue
        MAX-ACCESS read-write
        STATUS current
        DESCRIPTION
            "This enables or disables the notification action MGMT relay in the event Account Setting Changed.
            A value of 'true' (1) indicates that the notification action MGMT relay is
            allowed to notify the user while the system account setting changed.
            A value of 'false'(2) indicates that the notification action MGMT relay is not
            allowed to notify the user while the system account setting changed."
        ::= { geneConfigAccountSettingChangedAction 3 }

    geneConfigAccountSettingChangedPwr1RelayEnable OBJECT-TYPE
        SYNTAX TruthValue
        MAX-ACCESS read-write
        STATUS current
        DESCRIPTION
            "This enables or disables the notification action PWR1 relay in the event Account Setting Changed.
            A value of 'true' (1) indicates that the notification action PWR1 relay is
            allowed to notify the user while the system account setting changed.
            A value of 'false'(2) indicates that the notification action PWR1 relay is not
            allowed to notify the user while the system account setting changed."
        ::= { geneConfigAccountSettingChangedAction 4 }

    geneConfigAccountSettingChangedPwr2RelayEnable OBJECT-TYPE
        SYNTAX TruthValue
        MAX-ACCESS read-write
        STATUS current
        DESCRIPTION
            "This enables or disables the notification action PWR2 relay in the event Account Setting Changed.
            A value of 'true' (1) indicates that the notification action PWR2 relay is
            allowed to notify the user while the system account setting changed.
            A value of 'false'(2) indicates that the notification action PWR2 relay is not
            allowed to notify the user while the system account setting changed."
        ::= { geneConfigAccountSettingChangedAction 5 }

    geneConfigAccountSettingChangedRelayEnable OBJECT-TYPE
        SYNTAX TruthValue
        MAX-ACCESS read-write
        STATUS current
        DESCRIPTION 
            "This enables or disables the notification action relay in the event Account Setting Changed. 
            A value of 'true' (1) indicates that the notification action relay is allowed to notify the user while the system account setting changed.
            A value of 'false'(2) indicates that the notification action relay is not allowed to notify the user while the system account setting changed."
        ::= { geneConfigAccountSettingChangedAction 6 }

-- Password Changed

    geneConfigPasswordChanged OBJECT IDENTIFIER ::= { geneConfiguration 10 }

    geneConfigPasswordChangedEnable OBJECT-TYPE
        SYNTAX TruthValue
        MAX-ACCESS read-write
        STATUS current
        DESCRIPTION
            "This enables or disables the event Password Changed in the event notification.
            A value of 'true' (1) indicates that notifications are
            allowed to notify the user while the system password changed.
            A value of 'false'(2) indicates that notifications are not
            allowed to notify the user while the system password changed."
        ::= { geneConfigPasswordChanged 1 }

    geneConfigPasswordChangedAction OBJECT IDENTIFIER ::= { geneConfigPasswordChanged 2 }

    geneConfigPasswordChangedTrapEnable OBJECT-TYPE
        SYNTAX TruthValue
        MAX-ACCESS read-write
        STATUS current
        DESCRIPTION
            "This enables or disables the notification action trap in the event Password Changed.
            A value of 'true' (1) indicates that the notification action trap is
            allowed to notify the user while the system password changed.
            A value of 'false'(2) indicates that the notification action trap is not
            allowed to notify the user while the system password changed."
        ::= { geneConfigPasswordChangedAction 1 }

    geneConfigPasswordChangedEmailEnable OBJECT-TYPE
        SYNTAX TruthValue
        MAX-ACCESS read-write
        STATUS current
        DESCRIPTION
            "This enables or disables the notification action email in the event Password Changed.
            A value of 'true' (1) indicates that the notification action email is
            allowed to notify the user while the system password changed.
            A value of 'false'(2) indicates that the notification action email is not
            allowed to notify the user while the system password changed."
        ::= { geneConfigPasswordChangedAction 2 }

    geneConfigPasswordChangedMgmtRelayEnable OBJECT-TYPE
        SYNTAX TruthValue
        MAX-ACCESS read-write
        STATUS current
        DESCRIPTION
            "This enables or disables the notification action MGMT relay in the event Password Changed.
            A value of 'true' (1) indicates that the notification action MGMT relay is
            allowed to notify the user while the system password changed.
            A value of 'false'(2) indicates that the notification action MGMT relay is not
            allowed to notify the user while the system password changed."
        ::= { geneConfigPasswordChangedAction 3 }

    geneConfigPasswordChangedPwr1RelayEnable OBJECT-TYPE
        SYNTAX TruthValue
        MAX-ACCESS read-write
        STATUS current
        DESCRIPTION
            "This enables or disables the notification action PWR1 relay in the event Password Changed.
            A value of 'true' (1) indicates that the notification action PWR1 relay is
            allowed to notify the user while the system password changed.
            A value of 'false'(2) indicates that the notification action PWR1 relay is not
            allowed to notify the user while the system password changed."
        ::= { geneConfigPasswordChangedAction 4 }

    geneConfigPasswordChangedPwr2RelayEnable OBJECT-TYPE
        SYNTAX TruthValue
        MAX-ACCESS read-write
        STATUS current
        DESCRIPTION
            "This enables or disables the notification action PWR2 relay in the event Password Changed.
            A value of 'true' (1) indicates that the notification action PWR2 relay is
            allowed to notify the user while the system password changed.
            A value of 'false'(2) indicates that the notification action PWR2 relay is not
            allowed to notify the user while the system password changed."
        ::= { geneConfigPasswordChangedAction 5 }

    geneConfigPasswordChangedRelayEnable OBJECT-TYPE
        SYNTAX TruthValue
        MAX-ACCESS read-write
        STATUS current
        DESCRIPTION 
            "This enables or disables the notification action relay in the event Password Changed. 
            A value of 'true' (1) indicates that the notification action relay is allowed to notify the user while the system password changed.
            A value of 'false'(2) indicates that the notification action relay is not allowed to notify the user while the system password changed."
        ::= { geneConfigPasswordChangedAction 6 }

-- SSL Certification Changed

    geneConfigSslCertificationChanged OBJECT IDENTIFIER ::= { geneConfiguration 11 }

    geneConfigSslCertificationChangedEnable OBJECT-TYPE
        SYNTAX TruthValue
        MAX-ACCESS read-write
        STATUS current
        DESCRIPTION
            "This enables or disables the event SSL Certification Changed in the event notification.
            A value of 'true' (1) indicates that notifications are
            allowed to notify the user while the system SSL certification changed.
            A value of 'false'(2) indicates that notifications are not
            allowed to notify the user while the system SSL certification changed."
        ::= { geneConfigSslCertificationChanged 1 }

    geneConfigSslCertificationChangedAction OBJECT IDENTIFIER ::= { geneConfigSslCertificationChanged 2 }

    geneConfigSslCertificationChangedTrapEnable OBJECT-TYPE
        SYNTAX TruthValue
        MAX-ACCESS read-write
        STATUS current
        DESCRIPTION
            "This enables or disables the notification action trap in the event SSL Certification Changed.
            A value of 'true' (1) indicates that the notification action trap is
            allowed to notify the user while the system SSL certification changed.
            A value of 'false'(2) indicates that the notification action trap is not
            allowed to notify the user while the system SSL certification changed."
        ::= { geneConfigSslCertificationChangedAction 1 }

    geneConfigSslCertificationChangedEmailEnable OBJECT-TYPE
        SYNTAX TruthValue
        MAX-ACCESS read-write
        STATUS current
        DESCRIPTION
            "This enables or disables the notification action email in the event SSL Certification Changed.
            A value of 'true' (1) indicates that the notification action email is
            allowed to notify the user while the system SSL certification changed.
            A value of 'false'(2) indicates that the notification action email is not
            allowed to notify the user while the system SSL certification changed."
        ::= { geneConfigSslCertificationChangedAction 2 }

    geneConfigSslCertificationChangedMgmtRelayEnable OBJECT-TYPE
        SYNTAX TruthValue
        MAX-ACCESS read-write
        STATUS current
        DESCRIPTION
            "This enables or disables the notification action MGMT relay in the event SSL Certification Changed.
            A value of 'true' (1) indicates that the notification action MGMT relay is
            allowed to notify the user while the system SSL certification changed.
            A value of 'false'(2) indicates that the notification action MGMT relay is not
            allowed to notify the user while the system SSL certification changed."
        ::= { geneConfigSslCertificationChangedAction 3 }

    geneConfigSslCertificationChangedPwr1RelayEnable OBJECT-TYPE
        SYNTAX TruthValue
        MAX-ACCESS read-write
        STATUS current
        DESCRIPTION
            "This enables or disables the notification action PWR1 relay in the event SSL Certification Changed.
            A value of 'true' (1) indicates that the notification action PWR1 relay is
            allowed to notify the user while the system SSL certification changed.
            A value of 'false'(2) indicates that the notification action PWR1 relay is not
            allowed to notify the user while the system SSL certification changed."
        ::= { geneConfigSslCertificationChangedAction 4 }

    geneConfigSslCertificationChangedPwr2RelayEnable OBJECT-TYPE
        SYNTAX TruthValue
        MAX-ACCESS read-write
        STATUS current
        DESCRIPTION
            "This enables or disables the notification action PWR2 relay in the event SSL Certification Changed.
            A value of 'true' (1) indicates that the notification action PWR2 relay is
            allowed to notify the user while the system SSL certification changed.
            A value of 'false'(2) indicates that the notification action PWR2 relay is not
            allowed to notify the user while the system SSL certification changed."
        ::= { geneConfigSslCertificationChangedAction 5 }

    geneConfigSslCertificationChangedRelayEnable OBJECT-TYPE
        SYNTAX TruthValue
        MAX-ACCESS read-write
        STATUS current
        DESCRIPTION 
            "This enables or disables the notification action relay in the event SSL Certification Changed. 
            A value of 'true' (1) indicates that the notification action relay is allowed to notify the user while the system SSL certification changed.
            A value of 'false'(2) indicates that the notification action relay is not allowed to notify the user while the system SSL certification changed."
        ::= { geneConfigSslCertificationChangedAction 6 }

-- Power On

    geneConfigPowerOn OBJECT IDENTIFIER ::= { geneConfiguration 101 }

    geneConfigPowerOnEnable OBJECT-TYPE
        SYNTAX TruthValue
        MAX-ACCESS read-write
        STATUS current
        DESCRIPTION
            "This enables or disables the event Power On in the event notification.
            A value of 'true' (1) indicates that notifications are
            allowed to notify the user while the power module on.
            A value of 'false'(2) indicates that notifications are not
            allowed to notify the user while the power module on."
        ::= { geneConfigPowerOn 1 }

    geneConfigPowerOnAction OBJECT IDENTIFIER ::= { geneConfigPowerOn 2 }

    geneConfigPowerOnTrapEnable OBJECT-TYPE
        SYNTAX TruthValue
        MAX-ACCESS read-write
        STATUS current
        DESCRIPTION
            "This enables or disables the notification action trap in the event Power On.
            A value of 'true' (1) indicates that the notification action trap is
            allowed to notify the user while the power module on.
            A value of 'false'(2) indicates that the notification action trap is not
            allowed to notify the user while the power module on."
        ::= { geneConfigPowerOnAction 1 }

    geneConfigPowerOnEmailEnable OBJECT-TYPE
        SYNTAX TruthValue
        MAX-ACCESS read-write
        STATUS current
        DESCRIPTION
            "This enables or disables the notification action email in the event Power On.
            A value of 'true' (1) indicates that the notification action email is
            allowed to notify the user while the power module on.
            A value of 'false'(2) indicates that the notification action email is not
            allowed to notify the user while the power module on."
        ::= { geneConfigPowerOnAction 2 }

    geneConfigPowerOnMgmtRelayEnable OBJECT-TYPE
        SYNTAX TruthValue
        MAX-ACCESS read-write
        STATUS current
        DESCRIPTION
            "This enables or disables the notification action MGMT relay in the event Power On.
            A value of 'true' (1) indicates that the notification action MGMT relay is
            allowed to notify the user while the power module on.
            A value of 'false'(2) indicates that the notification action MGMT relay is not
            allowed to notify the user while the power module on."
        ::= { geneConfigPowerOnAction 3 }

    geneConfigPowerOnPwr1RelayEnable OBJECT-TYPE
        SYNTAX TruthValue
        MAX-ACCESS read-write
        STATUS current
        DESCRIPTION
            "This enables or disables the notification action PWR1 relay in the event Power On.
            A value of 'true' (1) indicates that the notification action PWR1 relay is
            allowed to notify the user while the power module on.
            A value of 'false'(2) indicates that the notification action PWR1 relay is not
            allowed to notify the user while the power module on."
        ::= { geneConfigPowerOnAction 4 }

    geneConfigPowerOnPwr2RelayEnable OBJECT-TYPE
        SYNTAX TruthValue
        MAX-ACCESS read-write
        STATUS current
        DESCRIPTION
            "This enables or disables the notification action PWR2 relay in the event Power On.
            A value of 'true' (1) indicates that the notification action PWR2 relay is
            allowed to notify the user while the power module on.
            A value of 'false'(2) indicates that the notification action PWR2 relay is not
            allowed to notify the user while the power module on."
        ::= { geneConfigPowerOnAction 5 }

    geneConfigPowerOnRelayEnable OBJECT-TYPE
        SYNTAX TruthValue
        MAX-ACCESS read-write
        STATUS current
        DESCRIPTION 
            "This enables or disables the notification action relay in the event Power On. 
            A value of 'true' (1) indicates that the notification action relay is allowed to notify the user while the power module on.
            A value of 'false'(2) indicates that the notification action relay is not allowed to notify the user while the power module on."
        ::= { geneConfigPowerOnAction 6 }

-- Power Off

    geneConfigPowerOff OBJECT IDENTIFIER ::=  { geneConfiguration 102 }

    geneConfigPowerOffEnable OBJECT-TYPE
        SYNTAX TruthValue
        MAX-ACCESS read-write
        STATUS current
        DESCRIPTION
            "This enables or disables the event Power Off in the event notification.
            A value of 'true' (1) indicates that notifications are
            allowed to notify the user while the power module off.
            A value of 'false'(2) indicates that notifications are not
            allowed to notify the user while the power module off."
        ::= { geneConfigPowerOff 1 }

    geneConfigPowerOffAction OBJECT IDENTIFIER ::= { geneConfigPowerOff 2 }

    geneConfigPowerOffTrapEnable OBJECT-TYPE
        SYNTAX TruthValue
        MAX-ACCESS read-write
        STATUS current
        DESCRIPTION
            "This enables or disables the notification action trap in the event Power Off.
            A value of 'true' (1) indicates that the notification action trap is
            allowed to notify the user while the power module off.
            A value of 'false'(2) indicates that the notification action trap is not
            allowed to notify the user while the power module off."
        ::= { geneConfigPowerOffAction 1 }

    geneConfigPowerOffEmailEnable OBJECT-TYPE
        SYNTAX TruthValue
        MAX-ACCESS read-write
        STATUS current
        DESCRIPTION
            "This enables or disables the notification action email in the event Power Off.
            A value of 'true' (1) indicates that the notification action email is
            allowed to notify the user while the power module off.
            A value of 'false'(2) indicates that the notification action email is not
            allowed to notify the user while the power module off."
        ::= { geneConfigPowerOffAction 2 }

    geneConfigPowerOffMgmtRelayEnable OBJECT-TYPE
        SYNTAX TruthValue
        MAX-ACCESS read-write
        STATUS current
        DESCRIPTION
            "This enables or disables the notification action MGMT relay in the event Power Off.
            A value of 'true' (1) indicates that the notification action MGMT relay is
            allowed to notify the user while the power module off.
            A value of 'false'(2) indicates that the notification action MGMT relay is not
            allowed to notify the user while the power module off."
        ::= { geneConfigPowerOffAction 3 }

    geneConfigPowerOffPwr1RelayEnable OBJECT-TYPE
        SYNTAX TruthValue
        MAX-ACCESS read-write
        STATUS current
        DESCRIPTION
            "This enables or disables the notification action PWR1 relay in the event Power Off.
            A value of 'true' (1) indicates that the notification action PWR1 relay is
            allowed to notify the user while the power module off.
            A value of 'false'(2) indicates that the notification action PWR1 relay is not
            allowed to notify the user while the power module off."
        ::= { geneConfigPowerOffAction 4 }

    geneConfigPowerOffPwr2RelayEnable OBJECT-TYPE
        SYNTAX TruthValue
        MAX-ACCESS read-write
        STATUS current
        DESCRIPTION
            "This enables or disables the notification action PWR2 relay in the event Power Off.
            A value of 'true' (1) indicates that the notification action PWR2 relay is
            allowed to notify the user while the power module off.
            A value of 'false'(2) indicates that the notification action PWR2 relay is not
            allowed to notify the user while the power module off."
        ::= { geneConfigPowerOffAction 5 }

    geneConfigPowerOffRelayEnable OBJECT-TYPE
        SYNTAX TruthValue
        MAX-ACCESS read-write
        STATUS current
        DESCRIPTION 
            "This enables or disables the notification action relay in the event Power Off. 
            A value of 'true' (1) indicates that the notification action relay is allowed to notify the user while the power module off.
            A value of 'false'(2) indicates that the notification action relay is not allowed to notify the user while the power module off."
        ::= { geneConfigPowerOffAction 6 }

-- DI On

    geneConfigDiOn OBJECT IDENTIFIER ::= { geneConfiguration 103 }

    geneConfigDiOnEnable OBJECT-TYPE
        SYNTAX TruthValue
        MAX-ACCESS read-write
        STATUS current
        DESCRIPTION
            "This enables or disables the event DI On in the event notification.
            A value of 'true' (1) indicates that notifications are
            allowed to notify the user while the digital input on.
            A value of 'false'(2) indicates that notifications are not
            allowed to notify the user while the digital input on."
        ::= { geneConfigDiOn 1 }

    geneConfigDiOnAction OBJECT IDENTIFIER ::= { geneConfigDiOn 2 }

    geneConfigDiOnTrapEnable OBJECT-TYPE
        SYNTAX TruthValue
        MAX-ACCESS read-write
        STATUS current
        DESCRIPTION
            "This enables or disables the notification action trap in the event DI On.
            A value of 'true' (1) indicates that the notification action trap is
            allowed to notify the user while the digital input on.
            A value of 'false'(2) indicates that the notification action trap is not
            allowed to notify the user while the digital input on."
        ::= { geneConfigDiOnAction 1 }

    geneConfigDiOnEmailEnable OBJECT-TYPE
        SYNTAX TruthValue
        MAX-ACCESS read-write
        STATUS current
        DESCRIPTION
            "This enables or disables the notification action email in the event DI On.
            A value of 'true' (1) indicates that the notification action email is
            allowed to notify the user while the digital input on.
            A value of 'false'(2) indicates that the notification action email is not
            allowed to notify the user while the digital input on."
        ::= { geneConfigDiOnAction 2 }

    geneConfigDiOnMgmtRelayEnable OBJECT-TYPE
        SYNTAX TruthValue
        MAX-ACCESS read-write
        STATUS current
        DESCRIPTION
            "This enables or disables the notification action MGMT relay in the event DI On.
            A value of 'true' (1) indicates that the notification action MGMT relay is
            allowed to notify the user while the digital input on.
            A value of 'false'(2) indicates that the notification action MGMT relay is not
            allowed to notify the user while the digital input on."
        ::= { geneConfigDiOnAction 3 }

    geneConfigDiOnPwr1RelayEnable OBJECT-TYPE
        SYNTAX TruthValue
        MAX-ACCESS read-write
        STATUS current
        DESCRIPTION
            "This enables or disables the notification action PWR1 relay in the event DI On.
            A value of 'true' (1) indicates that the notification action PWR1 relay is
            allowed to notify the user while the digital input on.
            A value of 'false'(2) indicates that the notification action PWR1 relay is not
            allowed to notify the user while the digital input on."
        ::= { geneConfigDiOnAction 4 }

    geneConfigDiOnPwr2RelayEnable OBJECT-TYPE
        SYNTAX TruthValue
        MAX-ACCESS read-write
        STATUS current
        DESCRIPTION
            "This enables or disables the notification action PWR2 relay in the event DI On.
            A value of 'true' (1) indicates that the notification action PWR2 relay is
            allowed to notify the user while the digital input on.
            A value of 'false'(2) indicates that the notification action PWR2 relay is not
            allowed to notify the user while the digital input on."
        ::= { geneConfigDiOnAction 5 }

    geneConfigDiOnRelayEnable OBJECT-TYPE
        SYNTAX TruthValue
        MAX-ACCESS read-write
        STATUS current
        DESCRIPTION 
            "This enables or disables the notification action relay in the event DI On. 
            A value of 'true' (1) indicates that the notification action relay is allowed to notify the user while the digital input on.
            A value of 'false'(2) indicates that the notification action relay is not allowed to notify the user while the digital input on."
        ::= { geneConfigDiOnAction 6 }

-- DI Off

    geneConfigDiOff OBJECT IDENTIFIER ::= { geneConfiguration 104 }

    geneConfigDiOffEnable OBJECT-TYPE
        SYNTAX TruthValue
        MAX-ACCESS read-write
        STATUS current
        DESCRIPTION
            "This enables or disables the event DI Off in the event notification.
            A value of 'true' (1) indicates that notifications are
            allowed to notify the user while the digital input off.
            A value of 'false'(2) indicates that notifications are not
            allowed to notify the user while the digital input off."
        ::= { geneConfigDiOff 1 }

    geneConfigDiOffAction OBJECT IDENTIFIER ::= { geneConfigDiOff 2 }

    geneConfigDiOffTrapEnable OBJECT-TYPE
        SYNTAX TruthValue
        MAX-ACCESS read-write
        STATUS current
        DESCRIPTION
            "This enables or disables the notification action trap in the event DI Off.
            A value of 'true' (1) indicates that the notification action trap is
            allowed to notify the user while the digital input off.
            A value of 'false'(2) indicates that the notification action trap is not
            allowed to notify the user while the digital input off."
        ::= { geneConfigDiOffAction 1 }

    geneConfigDiOffEmailEnable OBJECT-TYPE
        SYNTAX TruthValue
        MAX-ACCESS read-write
        STATUS current
        DESCRIPTION
            "This enables or disables the notification action email in the event DI Off.
            A value of 'true' (1) indicates that the notification action email is
            allowed to notify the user while the digital input off.
            A value of 'false'(2) indicates that the notification action email is not
            allowed to notify the user while the digital input off."
        ::= { geneConfigDiOffAction 2 }

    geneConfigDiOffMgmtRelayEnable OBJECT-TYPE
        SYNTAX TruthValue
        MAX-ACCESS read-write
        STATUS current
        DESCRIPTION
            "This enables or disables the notification action MGMT relay in the event DI Off.
            A value of 'true' (1) indicates that the notification action MGMT relay is
            allowed to notify the user while the digital input off.
            A value of 'false'(2) indicates that the notification action MGMT relay is not
            allowed to notify the user while the digital input off."
        ::= { geneConfigDiOffAction 3 }

    geneConfigDiOffPwr1RelayEnable OBJECT-TYPE
        SYNTAX TruthValue
        MAX-ACCESS read-write
        STATUS current
        DESCRIPTION
            "This enables or disables the notification action PWR1 relay in the event DI Off.
            A value of 'true' (1) indicates that the notification action PWR1 relay is
            allowed to notify the user while the digital input off.
            A value of 'false'(2) indicates that the notification action PWR1 relay is not
            allowed to notify the user while the digital input off."
        ::= { geneConfigDiOffAction 4 }

    geneConfigDiOffPwr2RelayEnable OBJECT-TYPE
        SYNTAX TruthValue
        MAX-ACCESS read-write
        STATUS current
        DESCRIPTION
            "This enables or disables the notification action PWR2 relay in the event DI Off.
            A value of 'true' (1) indicates that the notification action PWR2 relay is
            allowed to notify the user while the digital input off.
            A value of 'false'(2) indicates that the notification action PWR2 relay is not
            allowed to notify the user while the digital input off."
        ::= { geneConfigDiOffAction 5 }

    geneConfigDiOffRelayEnable OBJECT-TYPE
        SYNTAX TruthValue
        MAX-ACCESS read-write
        STATUS current
        DESCRIPTION 
            "This enables or disables the notification action relay in the event DI Off. 
            A value of 'true' (1) indicates that the notification action relay is allowed to notify the user while the digital input off.
            A value of 'false'(2) indicates that the notification action relay is not allowed to notify the user while the digital input off."
        ::= { geneConfigDiOffAction 6 }

-- -------------------------------------------------------------
-- Status group
-- -------------------------------------------------------------

    geneStatusLoginUsername OBJECT-TYPE
        SYNTAX DisplayString
        MAX-ACCESS accessible-for-notify
        STATUS current
        DESCRIPTION
            "The username which user used to login"
        ::= { geneStatus 1 }

    geneStatusLoginInterface OBJECT-TYPE
        SYNTAX DisplayString
        MAX-ACCESS accessible-for-notify
        STATUS current
        DESCRIPTION
            "The username which user used to login"
        ::= { geneStatus 2 }

    geneStatusLoginFailedTimes OBJECT-TYPE
        SYNTAX INTEGER
        MAX-ACCESS accessible-for-notify
        STATUS current
        DESCRIPTION
            "The username which user used to login"
        ::= { geneStatus 3 }

-- -------------------------------------------------------------
-- Notification group
-- -------------------------------------------------------------

    geneNotifyLoginSuccess NOTIFICATION-TYPE,
        enterprises
        OBJECTS {
            geneStatusLoginUsername,
            geneStatusLoginInterface
        }
        STATUS current
        DESCRIPTION
            "Notification for login success"
        ::= { geneNotification 1 }

    geneNotifyAccountChanged NOTIFICATION-TYPE,
        enterprises
        OBJECTS {
            geneStatusLoginUsername
        }
        STATUS current
        DESCRIPTION
            "Notification for account setting changed"
        ::= { geneNotification 2 }

    geneNotifyPasswordChanged NOTIFICATION-TYPE,
        enterprises
        OBJECTS {
            geneStatusLoginUsername
        }
        STATUS current
        DESCRIPTION
            "Notification for password changed"
        ::= { geneNotification 3 }

    geneNotifyLoginLockout NOTIFICATION-TYPE,
        enterprises
        OBJECTS {
            geneStatusLoginUsername,
            geneStatusLoginFailedTimes
        }
        STATUS current
        DESCRIPTION
            "Notification for login lockout"
        ::= { geneNotification 4 }

    geneNotifyCertChanged NOTIFICATION-TYPE,
        enterprises
        STATUS current
        DESCRIPTION
            "Notification for SSL certification changed"
        ::= { geneNotification 5 }

    geneNotifyDyingGasp NOTIFICATION-TYPE,
        enterprises
        STATUS current
        DESCRIPTION
            "The system power has lost"
        ::= { geneNotification 6 }

END
