LLDP-EXT-ODVA-MIB DEFINITIONS ::= BEGIN

IMPORTS
    Unsigned32,
    MODULE-IDENTITY,
    OBJECT-TYPE            FROM SNMPv2-SMI
    MacAddress,
    DisplayString          FROM SNMPv2-TC
    MODULE-COMPLIANCE,
    OBJECT-GROUP           FROM SNMPv2-CONF
    lldpExtensions,
    lldpRemTimeMark,
    lldpRemLocalPortNum,
    lldpRemIndex,
    lldpLocPortNum         FROM LLDP-MIB
	TimeFilter             FROM RMON2-MIB;

lldpXOdvaMIB               MODULE-IDENTITY
    LAST-UPDATED           "202205200000Z"
    ORGANIZATION           "ODVA, Inc."
    CONTACT-INFO           "+1 734 975 8840, odva@odva.org"
    DESCRIPTION            "MIB supporting the EtherNet/IP Implementation of LLDP"
-- OUI for ODVA 8556 (00-21-6C)
    ::= { lldpExtensions 8556 }

------------------------------------------------------------------------------
--
-- Organizationally Defined Information Extension - ODVA
--
------------------------------------------------------------------------------

lldpXOdvaObjects           OBJECT IDENTIFIER ::= { lldpXOdvaMIB 1 }

-- LLDP ODVA extension MIB groups
lldpXOdvaConfig            OBJECT IDENTIFIER ::= { lldpXOdvaObjects 1 }
lldpXOdvaLocalData         OBJECT IDENTIFIER ::= { lldpXOdvaObjects 2 }
lldpXOdvaRemoteData        OBJECT IDENTIFIER ::= { lldpXOdvaObjects 3 }

------------------------------------------------------------------------------
-- ODVA - Configuration
------------------------------------------------------------------------------

-- Security best practice indicates configuration should no longer be supported via SNMP

------------------------------------------------------------------------------
-- ODVA - Local System Information
------------------------------------------------------------------------------

lldpXOdvaLocTable          OBJECT-TYPE
    SYNTAX                 SEQUENCE OF LldpXOdvaLocEntry
    MAX-ACCESS             not-accessible
    STATUS                 current
    DESCRIPTION            "
                           This table contains one row per port for ODVA
                           organizationally defined LLDP extension on the
                           local system known to this agent.
                           "
    ::= { lldpXOdvaLocalData 1 }

lldpXOdvaLocEntry          OBJECT-TYPE
    SYNTAX                 LldpXOdvaLocEntry
    MAX-ACCESS             not-accessible
    STATUS                 current
    DESCRIPTION            "
                           Additional information about a particular port
                           component.

                           This object is indexed by the lldpLocPortNum
                           of the LLDP-MIB, therefore it is only present
                           along with the port entry defined by the
                           associated lldpLocPortEntry entry.

                           Each active lldpXOdvaLocEntry shall be restored
                           from non-volatile storage (along with the
                           corresponding lldpLocPortEntry) after a
                           re-initialization of the management system.
                           "
    INDEX                  { lldpLocPortNum  }
    ::= { lldpXOdvaLocTable 1 }

LldpXOdvaLocEntry ::=      SEQUENCE {
    lldpXOdvaLocCIPIdentVendorID        Unsigned32,
    lldpXOdvaLocCIPIdentDeviceType      Unsigned32,
    lldpXOdvaLocCIPIdentProductCode     Unsigned32,
    lldpXOdvaLocCIPIdentMajorRev        Unsigned32,
    lldpXOdvaLocCIPIdentMinorRev        Unsigned32,
    lldpXOdvaLocCIPIdentSerialNumber    Unsigned32,
    lldpXOdvaLocCIPMacAddress           MacAddress,
    lldpXOdvaLocCIPInterfaceLabel       DisplayString,
    lldpXOdvaLocCIPPositionID           Unsigned32,
    lldpXOdvaLocCIPPHYMode              Unsigned32,
    lldpXOdvaLocCIPPLCAPHYNodeID        Unsigned32
}

lldpXOdvaLocCIPIdentVendorID     OBJECT-TYPE
    SYNTAX                 Unsigned32
    MAX-ACCESS             read-only
    STATUS                 current
    DESCRIPTION            "
                           Identification of each vendor by ODVA assigned number.
                           "
    REFERENCE              "ODVA CIP Networks Library Volume 1: Identity Object, Instance Attribute #1"
    ::= { lldpXOdvaLocEntry 1 }

lldpXOdvaLocCIPIdentDeviceType     OBJECT-TYPE
    SYNTAX                 Unsigned32
    MAX-ACCESS             read-only
    STATUS                 current
    DESCRIPTION            "
                           Indication of general type of product.
                           "
    REFERENCE              " ODVA CIP Networks Library Volume 1: Identity Object, Instance Attribute #2"
    ::= { lldpXOdvaLocEntry 2 }

lldpXOdvaLocCIPIdentProductCode     OBJECT-TYPE
    SYNTAX                 Unsigned32
    MAX-ACCESS             read-only
    STATUS                 current
    DESCRIPTION            "
                           Identification of a particular product of an individual vendor.
                           "
    REFERENCE              "ODVA CIP Networks Library Volume 1: Identity Object, Instance Attribute #3"
    ::= { lldpXOdvaLocEntry 3 }

lldpXOdvaLocCIPIdentMajorRev    OBJECT-TYPE
    SYNTAX                 Unsigned32
    MAX-ACCESS             read-only
    STATUS                 current
    DESCRIPTION            "
                           Major Revision of the device.
                           "
    REFERENCE              "ODVA CIP Networks Library Volume 1: Identity Object, Instance Attribute #4"
    ::= { lldpXOdvaLocEntry 4 }

lldpXOdvaLocCIPIdentMinorRev    OBJECT-TYPE
    SYNTAX                 Unsigned32
    MAX-ACCESS             read-only
    STATUS                 current
    DESCRIPTION            "
                           Minor Revision of the device.
                           "
    REFERENCE              "ODVA CIP Networks Library Volume 1: Identity Object, Instance Attribute #4"
    ::= { lldpXOdvaLocEntry 5 }

lldpXOdvaLocCIPIdentSerialNumber     OBJECT-TYPE
    SYNTAX                 Unsigned32
    MAX-ACCESS             read-only
    STATUS                 current
    DESCRIPTION            "
                           Serial Number of the device.
                           "
    REFERENCE              "ODVA CIP Networks Library Volume 1: Identity Object, Instance Attribute #6"
    ::= { lldpXOdvaLocEntry 6 }

lldpXOdvaLocCIPMacAddress     OBJECT-TYPE
    SYNTAX                 MacAddress
    MAX-ACCESS             read-only
    STATUS                 current
    DESCRIPTION            "
                           MAC address of the device.
                           "
    REFERENCE              "RFC 2863 - ifPhysAddress"
    ::= { lldpXOdvaLocEntry 7 }

lldpXOdvaLocCIPInterfaceLabel     OBJECT-TYPE
    SYNTAX                 DisplayString
    MAX-ACCESS             read-only
    STATUS                 current
    DESCRIPTION            "
                           Interface Label of the device from the CIP Ethernet Link Object.
                           "
    REFERENCE              "RFC 2863 - ifDescr"
    ::= { lldpXOdvaLocEntry 8 }

lldpXOdvaLocCIPPositionID  OBJECT-TYPE
    SYNTAX                 Unsigned32
    MAX-ACCESS             read-only
    STATUS                 current
    DESCRIPTION            "
                           Position ID on the network segment for the In-Cabinet EtherNet/IP Profile device.
                           "
    REFERENCE              "ODVA CIP Networks Library Volume 2: LLDP Data Table Object, Instance Attribute #10"

    ::= { lldpXOdvaLocEntry 9 }

lldpXOdvaLocCIPPHYMode     OBJECT-TYPE
    SYNTAX                 Unsigned32
    MAX-ACCESS             read-only
    STATUS                 current
    DESCRIPTION            "
                           T1S PHY collision avoidance mode 0=CSMA/CD, 1=PLCA
                           "
    REFERENCE              "ODVA CIP Networks Library Volume 2: LLDP Data Table Object, Instance Attribute #11"

    ::= { lldpXOdvaLocEntry 10 }

lldpXOdvaLocCIPPLCAPHYNodeID OBJECT-TYPE
    SYNTAX                 Unsigned32
    MAX-ACCESS             read-only
    STATUS                 current
    DESCRIPTION            "
                           Node ID for PLCA Operation
                           "
    REFERENCE              "ODVA CIP Networks Library Volume 2: LLDP Data Table Object, Instance Attribute #11"

    ::= { lldpXOdvaLocEntry 11 }


------------------------------------------------------------------------------
-- ODVA - Remote System Information
------------------------------------------------------------------------------

lldpXOdvaRemTable          OBJECT-TYPE
    SYNTAX                 SEQUENCE OF LldpXOdvaRemEntry
    MAX-ACCESS             not-accessible
    STATUS                 current
    DESCRIPTION            "
                           This table contains one or more rows per physical network
                           connection known to this agent. The agent may wish to
                           ensure that only one lldpXOdvaRemEntry is present for
                           each local port, or it may choose to maintain multiple
                           lldpXOdvaRemEntries for the same local port.
                           "
    ::= { lldpXOdvaRemoteData 1 }

lldpXOdvaRemEntry          OBJECT-TYPE
    SYNTAX                 LldpXOdvaRemEntry
    MAX-ACCESS             not-accessible
    STATUS                 current
    DESCRIPTION            "
                           Each entry represents the received information of the
                           communication partner on this physical connection.

                           The entries feature multiple indices from the
                           lldpRemEntry of the LLDP-MIB, therefore it is
                           only present along with the description defined
                           by the associated lldpRemEntry entry.
                           "
    INDEX                  { lldpXOdvaRemTimeMark, lldpXOdvaRemLocalPortNum, lldpXOdvaRemIndex, lldpXOdvaRemCIPOUI, lldpXOdvaRemCIPSubtype, lldpXOdvaRemCIPIndex }
    ::= { lldpXOdvaRemTable 1 }

LldpXOdvaRemEntry ::=       SEQUENCE {
    lldpXOdvaRemTimeMark                TimeFilter,
    lldpXOdvaRemLocalPortNum            Integer32,
    lldpXOdvaRemIndex                   Integer32,
	lldpXOdvaRemCIPOUI                  OCTET STRING,
    lldpXOdvaRemCIPSubtype              Integer32,
    lldpXOdvaRemCIPIndex                Integer32,
    lldpXOdvaRemCIPIdentVendorID        Unsigned32,
    lldpXOdvaRemCIPIdentDeviceType      Unsigned32,
    lldpXOdvaRemCIPIdentProductCode     Unsigned32,
    lldpXOdvaRemCIPIdentMajorRev        Unsigned32,
    lldpXOdvaRemCIPIdentMinorRev        Unsigned32,
    lldpXOdvaRemCIPIdentSerialNumber    Unsigned32,
    lldpXOdvaRemCIPMacAddress           MacAddress,
    lldpXOdvaRemCIPInterfaceLabel       DisplayString,
    lldpXOdvaRemCIPPositionID           Unsigned32,
    lldpXOdvaRemCIPPHYMode              Unsigned32,
    lldpXOdvaRemCIPPLCAPHYNodeID        Unsigned32,
    lldpXOdvaRemTTL                     Unsigned32

}

lldpXOdvaRemTimeMark       OBJECT-TYPE
    SYNTAX                 TimeFilter
    MAX-ACCESS             not-accessible
    STATUS                 current
    DESCRIPTION            "A TimeFilter for this entry.  See the TimeFilter textual
                           convention in IETF RFC 2021 and
                           http://www.ietf.org/IESG/Implementations/RFC2021-Implementation.txt
                           to see how TimeFilter works."
    REFERENCE              "IETF RFC 2021 section 6"
    ::= { lldpXOdvaRemEntry 1 }

lldpXOdvaRemLocalPortNum   OBJECT-TYPE
    SYNTAX                 Integer32
    MAX-ACCESS             not-accessible
    STATUS                 current
    DESCRIPTION            "The index value used to identify the port component
                           (contained in the local chassis with the LLDP agent)
                           associated with this entry.  The lldpRemLocalPortNum
                           identifies the port on which the remote system information
                           is received.
                           The value of this object is used as a port index to the
                           lldpRemTable."
    ::= { lldpXOdvaRemEntry 2 }

lldpXOdvaRemIndex          OBJECT-TYPE
    SYNTAX                 Integer32(1..2147483647)
    MAX-ACCESS             not-accessible
    STATUS                 current
    DESCRIPTION            "This object represents an arbitrary local integer value used
                           by this agent to identify a particular connection instance,
                           unique only for the indicated remote system.
                           An agent is encouraged to assign monotonically increasing
                           index values to new entries, starting with one, after each
                           reboot.  It is considered unlikely that the lldpRemIndex
                           will wrap between reboots."
    ::= { lldpXOdvaRemEntry 3 }

lldpXOdvaRemCIPOUI         OBJECT-TYPE
    SYNTAX                 OCTET STRING (SIZE(3))
    MAX-ACCESS             not-accessible
    STATUS                 current
    DESCRIPTION            "The Organizationally Unique Identifier (OUI), as defined
                           in IEEE std 802-2001, is a 24 bit (three octets) globally
                           unique assigned number referenced by various standards,
                           of the information received from the remote system."
    REFERENCE              "IEEE 802.1AB-2005 9.5.1.3"
    ::= { lldpXOdvaRemEntry 4 }

lldpXOdvaRemCIPSubtype     OBJECT-TYPE
    SYNTAX                 Integer32(1..255)
    MAX-ACCESS             not-accessible
    STATUS                 current
    DESCRIPTION
                           "The integer value used to identify the subtype of the
                           organizationally defined information received from the
                           remote system.
                           The subtype value is required to identify different instances
                           of organizationally defined information that could not be
                           retrieved without a unique identifier that indicates the
                           particular type of information contained in the information
                           string."
    REFERENCE              "IEEE 802.1AB-2005 9.5.1.4"
    ::= { lldpXOdvaRemEntry 5 }

lldpXOdvaRemCIPIndex       OBJECT-TYPE
    SYNTAX                 Integer32(1..2147483647)
    MAX-ACCESS             not-accessible
    STATUS                 current
    DESCRIPTION            "This object represents an arbitrary local integer value
                           used by this agent to identify a particular unrecognized
                           organizationally defined information instance, unique only
                           for the lldpXOdvaRemOUI and lldpXOdvaRemSubtype
                           from the same remote system.
                           An agent is encouraged to assign monotonically increasing
                           index values to new entries, starting with one, after each
                           reboot.  It is considered unlikely that the
                           lldpRemOrgDefInfoIndex will wrap between reboots."
    ::= { lldpXOdvaRemEntry 6 }

lldpXOdvaRemCIPIdentVendorID     OBJECT-TYPE
    SYNTAX                 Unsigned32
    MAX-ACCESS             read-only
    STATUS                 current
    DESCRIPTION            "
                           Identification of the remote device vendor by ODVA assigned number.
                           "
    REFERENCE              "ODVA CIP Networks Library Volume 1: Identity Object, Instance Attribute #1"
    ::= { lldpXOdvaRemEntry 7 }

lldpXOdvaRemCIPIdentDeviceType     OBJECT-TYPE
    SYNTAX                 Unsigned32
    MAX-ACCESS             read-only
    STATUS                 current
    DESCRIPTION            "
                           Indication of general type of product relating to the remote device.
                           "
    REFERENCE              "ODVA CIP Networks Library Volume 1: Identity Object, Instance Attribute #2"
    ::= { lldpXOdvaRemEntry 8 }

lldpXOdvaRemCIPIdentProductCode     OBJECT-TYPE
    SYNTAX                 Unsigned32
    MAX-ACCESS             read-only
    STATUS                 current
    DESCRIPTION            "
                           Identification of the remote device unique by individual vendor.
                           "
    REFERENCE              "ODVA CIP Networks Library Volume 1: Identity Object, Instance Attribute #3"
    ::= { lldpXOdvaRemEntry 9 }

lldpXOdvaRemCIPIdentMajorRev     OBJECT-TYPE
    SYNTAX                 Unsigned32
    MAX-ACCESS             read-only
    STATUS                 current
    DESCRIPTION            "
                           Major Revision of the remote device.
                           "
    REFERENCE              "ODVA CIP Networks Library Volume 1: Identity Object, Instance Attribute #4"
    ::= { lldpXOdvaRemEntry 10 }

lldpXOdvaRemCIPIdentMinorRev     OBJECT-TYPE
    SYNTAX                 Unsigned32
    MAX-ACCESS             read-only
    STATUS                 current
    DESCRIPTION            "
                           Minor Revision of the remote device.
                           "
    REFERENCE              "ODVA CIP Networks Library Volume 1: Identity Object, Instance Attribute #4"
    ::= { lldpXOdvaRemEntry 11 }


lldpXOdvaRemCIPIdentSerialNumber     OBJECT-TYPE
    SYNTAX                 Unsigned32
    MAX-ACCESS             read-only
    STATUS                 current
    DESCRIPTION            "
                           Serial Number of the remote device.
                           "
    REFERENCE              "ODVA CIP Networks Library Volume 1: Identity Object, Instance Attribute #6"
    ::= { lldpXOdvaRemEntry 12 }

lldpXOdvaRemCIPMacAddress     OBJECT-TYPE
    SYNTAX                 MacAddress
    MAX-ACCESS             read-only
    STATUS                 current
    DESCRIPTION            "
                           MAC address of the remote device.
                           "
    REFERENCE              "RFC 2863 - ifPhysAddress"
    ::= { lldpXOdvaRemEntry 13 }

lldpXOdvaRemCIPInterfaceLabel     OBJECT-TYPE
    SYNTAX                 DisplayString
    MAX-ACCESS             read-only
    STATUS                 current
    DESCRIPTION            "
                           Interface Label of the remote device from the CIP Ethernet Link Object.
                           "
    REFERENCE              "RFC 2863 - ifDescr"
    ::= { lldpXOdvaRemEntry 14 }

lldpXOdvaRemCIPPositionID  OBJECT-TYPE
    SYNTAX                 Unsigned32
    MAX-ACCESS             read-only
    STATUS                 current
    DESCRIPTION            "
                           Position ID on the network segment for the In-Cabinet EtherNet/IP Profile remote device.
                           "
    REFERENCE              "ODVA CIP Networks Library Volume 2: LLDP Data Table Object, Instance Attribute #10"

    ::= { lldpXOdvaRemEntry 15 }

lldpXOdvaRemCIPPHYMode     OBJECT-TYPE
    SYNTAX                 Unsigned32
    MAX-ACCESS             read-only
    STATUS                 current
    DESCRIPTION            "
                           T1S PHY collision avoidance mode of the remote device                                     0=CSMA/CD, 1=PLCA
                           "
    REFERENCE              "ODVA CIP Networks Library Volume 2: LLDP Data Table Object, Instance Attribute #11"

    ::= { lldpXOdvaRemEntry 16 }

lldpXOdvaRemCIPPLCAPHYNodeID OBJECT-TYPE
    SYNTAX                 Unsigned32
    MAX-ACCESS             read-only
    STATUS                 current
    DESCRIPTION            "
                           Remote Device Node ID for PLCA Operation
                           "
    REFERENCE              "ODVA CIP Networks Library Volume 2: LLDP Data Table Object, Instance Attribute #11"

    ::= { lldpXOdvaRemEntry 17 }

lldpXOdvaRemTTL            OBJECT-TYPE
    SYNTAX                 Unsigned32
    MAX-ACCESS             read-only
    STATUS                 current
    DESCRIPTION            "The number of seconds the neighboring information is to be considered valid"
    REFERENCE              "ODVA CIP Networks Library Volume 2: LLDP Data Table Object, Instance Attribute #4"

    ::= { lldpXOdvaRemEntry 18 }

------------------------------------------------------------------------------
-- Conformance Information
------------------------------------------------------------------------------

lldpXOdvaConformance       OBJECT IDENTIFIER ::= { lldpXOdvaMIB 2 }
lldpXOdvaCompliances       OBJECT IDENTIFIER ::= { lldpXOdvaConformance 1 }
lldpXOdvaGroups            OBJECT IDENTIFIER ::= { lldpXOdvaConformance 2 }

-- compliance statements

lldpXOdvaCompliance        MODULE-COMPLIANCE
    STATUS                 current
    DESCRIPTION            "
                           The compliance statement for SNMP entities which
                           implement the ODVA organizationally defined LLDP
                           extension MIB.
                           "
    MODULE                 -- compliant to this module
    MANDATORY-GROUPS       { lldpXOdvaLocGroup, lldpXOdvaRemGroup }
    ::= { lldpXOdvaCompliances 1 }

-- MIB groupings

lldpXOdvaLocGroup          OBJECT-GROUP
    OBJECTS                { lldpXOdvaLocCIPIdentVendorID,
                             lldpXOdvaLocCIPIdentDeviceType,
                             lldpXOdvaLocCIPIdentProductCode,
                             lldpXOdvaLocCIPIdentMajorRev,
                             lldpXOdvaLocCIPIdentMinorRev,
                             lldpXOdvaLocCIPIdentSerialNumber,
                             lldpXOdvaLocCIPMacAddress,
                             lldpXOdvaLocCIPInterfaceLabel,
                             lldpXOdvaLocCIPPositionID,
                             lldpXOdvaLocCIPPHYMode,
                             lldpXOdvaLocCIPPLCAPHYNodeID

                           }
    STATUS                 current
    DESCRIPTION            "
                           Group of Local ODVA specific MIB variables
                           "
    ::= { lldpXOdvaGroups 1 }

lldpXOdvaRemGroup          OBJECT-GROUP
    OBJECTS                { lldpXOdvaRemCIPIdentVendorID,
                             lldpXOdvaRemCIPIdentDeviceType,
                             lldpXOdvaRemCIPIdentProductCode,
                             lldpXOdvaRemCIPIdentMajorRev,
                             lldpXOdvaRemCIPIdentMinorRev,
                             lldpXOdvaRemCIPIdentSerialNumber,
                             lldpXOdvaRemCIPMacAddress,
                             lldpXOdvaRemCIPInterfaceLabel,
                             lldpXOdvaRemCIPPositionID,
                             lldpXOdvaRemCIPPHYMode,
                             lldpXOdvaRemCIPPLCAPHYNodeID,
                             lldpXOdvaRemTTL

                           }
    STATUS                 current
    DESCRIPTION            "
                           Group of remote ODVA specific MIB variables
                           "
    ::= { lldpXOdvaGroups 2 }

END
