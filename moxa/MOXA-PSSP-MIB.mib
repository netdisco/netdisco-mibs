-- ****************************************************************
-- *  Moxa Switching - Port Security Static Port Lock (PSSP) PRIVATE MIB
-- *
-- *  Copyright (c) 2019 by Moxa Inc.
-- *  All rights reserved.
-- *****************************************************************

MOXA-PSSP-MIB DEFINITIONS ::= BEGIN
    IMPORTS
        MODULE-IDENTITY, NOTIFICATION-TYPE, OBJECT-TYPE, Integer32, Counter32
            FROM SNMPv2-SMI
        TEXTUAL-CONVENTION, DateAndTime, MacAddress, DisplayString, TruthValue, RowStatus
            FROM SNMPv2-TC
        VlanId,PortList
            FROM Q-BRIDGE-MIB
        layer2Security
          FROM MOXA-SWITCHING-MIB;

    mxPssp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa port security statis port lock"

        REVISION    "202202170000Z"
        DESCRIPTION "update CONTACT-INFO"

        REVISION    "201906300000Z"
        DESCRIPTION "Initial Revision"

        ::= { layer2Security 1 }

-- -------------------------------------------------------------
-- groups in the MOXA-PSSP-MIB MIB
-- -------------------------------------------------------------

  -- psspNotification      OBJECT IDENTIFIER ::= { mxPssp 0 }
  psspConfiguration     OBJECT IDENTIFIER ::= { mxPssp 1 }
  psspStatus            OBJECT IDENTIFIER ::= { mxPssp 2 }
  -- psspExtensions        OBJECT IDENTIFIER ::= { mxPssp 3 }

-- -------------------------------------------------------------
-- configuration group
-- -------------------------------------------------------------
    psspConfigEnable OBJECT-TYPE
        SYNTAX       TruthValue
        MAX-ACCESS   read-write
        STATUS       current
        DESCRIPTION
            "The administrative module status requested by management for Static
            Port Lock in Port Security Module. This enables or disables Port Security
            in the system. A value of 'true' (1) indicates that Port Security is
            allowed to be enabled/disabled in the device on all the ports.
            A value of 'false'(2) indicates that PSSP must be disabled in the
            device on all the ports."
        ::= { psspConfiguration 1 }

    psspConfigMode OBJECT-TYPE
        SYNTAX      INTEGER {
                        staticPortLock(1),
                        macSticky(2)
                    }
        MAX-ACCESS  read-write
        STATUS      current
        DESCRIPTION
            "To configure Port Security mode to Static Port Lock (1) or Statis Port Lock (2)."
        ::= { psspConfiguration 2 }

-- Port Table Configuration Start

    psspConfigPortTable OBJECT-TYPE
        SYNTAX SEQUENCE OF PsspConfigPortEntry
        MAX-ACCESS not-accessible
        STATUS current
        DESCRIPTION
            "A table to store the port specific parameters for MAC sticky
            like limit value, secure action, etc. And the parameters can be manipulated
            by administrators"
        ::= { psspConfiguration 3 }

    psspConfigPortEntry OBJECT-TYPE
        SYNTAX PsspConfigPortEntry
        MAX-ACCESS not-accessible
        STATUS current
        DESCRIPTION
            "An entry appears in this Port Table represent port information about
            Port Security Statis Port Lock Mode."
        INDEX { psspConfigPortNum }
        ::= { psspConfigPortTable 1 }

    PsspConfigPortEntry ::=
        SEQUENCE {
            psspConfigPortNum
                Integer32,
            psspConfigPortEnable
                TruthValue,
            psspConfigDbFlush
                TruthValue
    }

    psspConfigPortNum OBJECT-TYPE
        SYNTAX Integer32 (1..256)
        MAX-ACCESS read-only
        STATUS current
        DESCRIPTION
            "A unique value, greater than zero, indicating the Port number of
             port configuration table."
        ::= { psspConfigPortEntry 1 }

    psspConfigPortEnable OBJECT-TYPE
        SYNTAX TruthValue
        MAX-ACCESS read-write
        STATUS current
        DESCRIPTION
            "This parameter when true(1) indicates that a port is enabled
            port security and false(2) indicates that this feature is disabled
            on the port."
        ::= { psspConfigPortEntry 2 }

    psspConfigDbFlush OBJECT-TYPE
        SYNTAX TruthValue
        MAX-ACCESS read-write
        STATUS current
        DESCRIPTION
            "If this object is set as 'true', then all the entries in specific port
            will be removed. After flush, this object is set to 'false'."
        ::= { psspConfigPortEntry 3 }

-- Address Table Configuration Start

    psspConfigAddressTable OBJECT-TYPE
        SYNTAX      SEQUENCE OF PsspConfigAddressEntry
        MAX-ACCESS  not-accessible
        STATUS      current
        DESCRIPTION
            "A table to store specific address parameters for MAC sticky
            like limit MacAddress and VlanId etc."
        ::= { psspConfiguration 4 }

    psspConfigAddressEntry OBJECT-TYPE
        SYNTAX      PsspConfigAddressEntry
        MAX-ACCESS  not-accessible
        STATUS      current
        DESCRIPTION
            "An entry appears in this Address Table represent port information about
            Port Security Static Port Lock Mode."
        INDEX { psspConfigAddressMac,
                psspConfigAddressVlanId }
        ::= { psspConfigAddressTable 1 }

    PsspConfigAddressEntry ::=
        SEQUENCE {
            psspConfigAddressMac
                MacAddress,
            psspConfigAddressVlanId
                VlanId,
            psspConfigAddressPortNum
                Integer32,
            psspConfigAddressRowStatus
                RowStatus
        }

    psspConfigAddressMac OBJECT-TYPE
        SYNTAX MacAddress
        MAX-ACCESS not-accessible
        STATUS current
        DESCRIPTION
            "To represent MAC address for this entry."
        ::= { psspConfigAddressEntry 1 }

    psspConfigAddressVlanId OBJECT-TYPE
        SYNTAX VlanId
        MAX-ACCESS not-accessible
        STATUS current
        DESCRIPTION
            "To indicate the entry's VLAN ID."
        ::= { psspConfigAddressEntry 2 }

    psspConfigAddressPortNum OBJECT-TYPE
        SYNTAX Integer32 (1..256)
        MAX-ACCESS read-write
        STATUS current
        DESCRIPTION
            "To indicate port number of the address entry."
        ::= { psspConfigAddressEntry 3 }

    psspConfigAddressRowStatus OBJECT-TYPE
        SYNTAX RowStatus
        MAX-ACCESS read-create
        STATUS current
        DESCRIPTION
            "This object indicates the status of this entry."
        ::= { psspConfigAddressEntry 4 }

--------------------------------------
-- Address Table Configuration End --
--------------------------------------

-- -------------------------------------------------------------
-- Status group
-- -------------------------------------------------------------

------------
-- System --
------------

    psspStatMaxNumOfAddress OBJECT-TYPE
        SYNTAX       Counter32
        MAX-ACCESS   read-only
        STATUS       current
        DESCRIPTION
            "To represent the max number of address in Port Security Static-Port-Lock."
        ::= { psspStatus 1 }


    psspStatTotalNumOfAddress OBJECT-TYPE
        SYNTAX       Counter32
        MAX-ACCESS   read-only
        STATUS       current
        DESCRIPTION
            "To represent the total number of address in Port Security Static-Port-Lock."
        ::= { psspStatus 2 }


----------------
-- Port Table --
----------------

    psspStatPortTable OBJECT-TYPE
        SYNTAX SEQUENCE OF PsspStatPortEntry
        MAX-ACCESS not-accessible
        STATUS current
        DESCRIPTION
            "The port status table."
        ::= { psspStatus 3 }

    psspStatPortEntry OBJECT-TYPE
        SYNTAX PsspStatPortEntry
        MAX-ACCESS not-accessible
        STATUS current
        DESCRIPTION
            "The port status table entry."
        INDEX { psspStatPortIndex }
        ::= { psspStatPortTable 1 }

    PsspStatPortEntry ::=
        SEQUENCE {
            psspStatPortIndex
                Integer32,
            psspStatCurrentNumberOfAddress
                Counter32
  }

    psspStatPortIndex OBJECT-TYPE
        SYNTAX Integer32 (1..256)
        MAX-ACCESS read-only
        STATUS current
        DESCRIPTION
            "The value of this object uniquely identifies this port table entry."
        ::= { psspStatPortEntry 1 }

    psspStatCurrentNumberOfAddress OBJECT-TYPE
        SYNTAX Counter32
        MAX-ACCESS read-only
        STATUS current
        DESCRIPTION
            "This indicates the current number of address on this port."
        ::= { psspStatPortEntry 2 }

-------------------
-- Address Table --
-------------------

    psspStatAddressTable OBJECT-TYPE
        SYNTAX SEQUENCE OF PsspStatAddressEntry
        MAX-ACCESS not-accessible
        STATUS current
        DESCRIPTION
            "The address table."
        ::= { psspStatus 4 }

    psspStatAddressEntry OBJECT-TYPE
        SYNTAX PsspStatAddressEntry
        MAX-ACCESS not-accessible
        STATUS current
        DESCRIPTION
            "The address table state entry."
        INDEX { psspStatAddressMac,
                psspStatAddressVlanId }
        ::= { psspStatAddressTable 1 }

    PsspStatAddressEntry ::=
        SEQUENCE {
            psspStatAddressMac
                MacAddress,
            psspStatAddressVlanId
                VlanId,
            psspStatAddressPortNum
                Integer32,
            psspStatAddressType
                INTEGER,
            psspStatAddressValid
                TruthValue
    }

    psspStatAddressMac OBJECT-TYPE
        SYNTAX  MacAddress
        MAX-ACCESS read-only
        STATUS current
        DESCRIPTION
            "To show Mac Address of the entry."
        ::= { psspStatAddressEntry 1 }

    psspStatAddressVlanId OBJECT-TYPE
        SYNTAX  VlanId
        MAX-ACCESS read-only
        STATUS current
        DESCRIPTION
            "To show Vlan ID of the entry."
        ::= { psspStatAddressEntry 2 }

    psspStatAddressPortNum OBJECT-TYPE
        SYNTAX Integer32 (1..256)
        MAX-ACCESS read-only
        STATUS current
        DESCRIPTION
            "To show Port Number of the entry."
        ::= { psspStatAddressEntry 3 }

    psspStatAddressType OBJECT-TYPE
        SYNTAX  INTEGER {
                    lockConfigured(1)
                }
        MAX-ACCESS read-only
        STATUS current
        DESCRIPTION
            "To indicate the entry type is Lock-Configured (1)."
        ::= { psspStatAddressEntry 4 }

    psspStatAddressValid OBJECT-TYPE
        SYNTAX  TruthValue
        MAX-ACCESS read-only
        STATUS current
        DESCRIPTION
            "To indicate the address entry is valid (TRUE) or not (FALSE)."
        ::= { psspStatAddressEntry 5 }

END
