-- ****************************************************************
-- *  Moxa Switching - MSTP PRIVATE MIB
-- *
-- *  Copyright (c) 2020 by Moxa Inc.
-- *  All rights reserved.
-- *****************************************************************

MOXA-MSTP-MIB DEFINITIONS ::= BEGIN
    IMPORTS
        MODULE-IDENTITY, NOTIFICATION-TYPE, OBJECT-TYPE, IpAddress,
        Integer32, Counter32
            FROM SNMPv2-SMI
        TEXTUAL-CONVENTION, DateAndTime, MacAddress, DisplayString, TruthValue
            FROM SNMPv2-TC
        layer2Redundancy, Timeout
            FROM MOXA-SWITCHING-MIB;

    mxMstp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module for Moxa mstp feature is new created."

        REVISION    "202202170000Z"
        DESCRIPTION "update CONTACT-INFO"

        REVISION    "202002250000Z"
        DESCRIPTION "Initial Revision"

        ::= { layer2Redundancy 3 }

-- -------------------------------------------------------------
-- groups in the MOXA-MSTP-MIB MIB
-- -------------------------------------------------------------

  mstpNotification      OBJECT IDENTIFIER ::= { mxMstp 0 }
  mstpConfiguration     OBJECT IDENTIFIER ::= { mxMstp 1 }
  mstpStatus            OBJECT IDENTIFIER ::= { mxMstp 2 }
  -- mstpExtensions        OBJECT IDENTIFIER ::= { mxMstp 3 }

-- -------------------------------------------------------------
-- configuration group
-- -------------------------------------------------------------

    mstpConfigEnable OBJECT-TYPE
        SYNTAX       TruthValue
        MAX-ACCESS   read-write
        STATUS       current
        DESCRIPTION
            "The administrative module status requested by management for the MSTP
            Module. This enables or disables MSTP in the system. A value of 'true'
            (1) indicates that MSTP must be enabled in the device on all the ports.
            A value of 'false'(2) indicates that MSTP must be disabled in the
            device on all the ports."
        ::= { mstpConfiguration 1 }

    mstpConfigCistPortTable OBJECT-TYPE
        SYNTAX SEQUENCE OF MstpConfigCistPortEntry
        MAX-ACCESS not-accessible
        STATUS current
        DESCRIPTION
            "The MSTP CIST configuration port table."
        ::= { mstpConfiguration 2 }

    mstpConfigCistPortEntry OBJECT-TYPE
        SYNTAX MstpConfigCistPortEntry
        MAX-ACCESS not-accessible
        STATUS current
        DESCRIPTION
            "The MSTP CIST configuration port table entry."
        INDEX { mstpConfigCistPortIndex }
        ::= { mstpConfigCistPortTable 1 }

    MstpConfigCistPortEntry ::=
        SEQUENCE {
            mstpConfigCistPortIndex
                INTEGER,
            mstpConfigCistPortEnable
                TruthValue
    }

    mstpConfigCistPortIndex OBJECT-TYPE
        SYNTAX INTEGER
        MAX-ACCESS not-accessible
        STATUS current
        DESCRIPTION
            "A unique value, greater than zero, indicating the Port number of port configuration table."
        ::= { mstpConfigCistPortEntry 1 }

    mstpConfigCistPortEnable OBJECT-TYPE
        SYNTAX TruthValue
        MAX-ACCESS read-write
        STATUS current
        DESCRIPTION
            "This parameter when true(1) indicates that enable MSTP CIST on such port  and false(2) indicates that the MSTP is disabled."
        ::= { mstpConfigCistPortEntry 2 }

    mstpConfigInstPortTable OBJECT-TYPE
        SYNTAX SEQUENCE OF MstpConfigInstPortEntry
        MAX-ACCESS not-accessible
        STATUS current
        DESCRIPTION
            "The MSTP Instance configuration port table."
        ::= { mstpConfiguration 3 }

    mstpConfigInstPortEntry OBJECT-TYPE
        SYNTAX MstpConfigInstPortEntry
        MAX-ACCESS not-accessible
        STATUS current
        DESCRIPTION
            "The MSTP Instance configuration port table entry."
        INDEX { mstpConfigInstIndex, mstpConfigInstPortIndex }
        ::= { mstpConfigInstPortTable 1 }

    MstpConfigInstPortEntry ::=
        SEQUENCE {
            mstpConfigInstIndex
                INTEGER,
            mstpConfigInstPortIndex
                INTEGER,
            mstpConfigInstPortEnable
                TruthValue
    }

    mstpConfigInstIndex OBJECT-TYPE
        SYNTAX INTEGER
        MAX-ACCESS not-accessible
        STATUS current
        DESCRIPTION
            "A unique value, greater than zero, indicating the Instance of MSTP instance port table."
        ::= { mstpConfigInstPortEntry 1 }

    mstpConfigInstPortIndex OBJECT-TYPE
        SYNTAX INTEGER
        MAX-ACCESS not-accessible
        STATUS current
        DESCRIPTION
            "A unique value, greater than zero, indicating the Port number of of MSTP instance port table."
        ::= { mstpConfigInstPortEntry 2 }

    mstpConfigInstPortEnable OBJECT-TYPE
        SYNTAX TruthValue
        MAX-ACCESS read-write
        STATUS current
        DESCRIPTION
            "This parameter when true(1) indicates that enable MSTP Instance on such instance/port and false(2) indicates that the MSTP is disabled."
        ::= { mstpConfigInstPortEntry 3 }

-- -------------------------------------------------------------
-- status group
-- -------------------------------------------------------------

    mstpStatInstIndex  OBJECT-TYPE
        SYNTAX INTEGER
        MAX-ACCESS accessible-for-notify
        STATUS current
        DESCRIPTION
            "A unique value, from 0 to maximum instance number, indicating the MSTP Instance Id."
        ::= { mstpStatus 1 }

    mstpStatPortTable OBJECT-TYPE
        SYNTAX SEQUENCE OF MstpStatPortEntry
        MAX-ACCESS not-accessible
        STATUS current
        DESCRIPTION
            "The port status table."
        ::= { mstpStatus 2 }

    mstpStatPortEntry OBJECT-TYPE
        SYNTAX MstpStatPortEntry
        MAX-ACCESS not-accessible
        STATUS current
        DESCRIPTION
            "The port status table entry."
        INDEX { mstpStatPortIndex }
        ::= { mstpStatPortTable 1 }

    MstpStatPortEntry ::=
        SEQUENCE {
            mstpStatPortIndex
                INTEGER,
            mstpStatNewRoleType
                INTEGER,
            mstpStatOldRoleType
                INTEGER
    }

    mstpStatPortIndex OBJECT-TYPE
        SYNTAX INTEGER
        MAX-ACCESS not-accessible
        STATUS current
        DESCRIPTION
            "A unique value, greater than zero, indicating the Port number of port status table."
        ::= { mstpStatPortEntry 1 }

    mstpStatNewRoleType OBJECT-TYPE
        SYNTAX INTEGER {
            disabledPort(0),
            alternatePort(1),
            backupPort(2),
            rootPort(3),
            designatedPort(4),
            masterPort(5)
        }
        MAX-ACCESS accessible-for-notify
        STATUS current
        DESCRIPTION
            "This indicates the Port Role assumed by this Port."
        ::= { mstpStatPortEntry 2 }

    mstpStatOldRoleType OBJECT-TYPE
        SYNTAX INTEGER {
            disabledPort(0),
            alternatePort(1),
            backupPort(2),
            rootPort(3),
            designatedPort(4),
            masterPort(5)
        }
        MAX-ACCESS accessible-for-notify
        STATUS current
        DESCRIPTION
            "This indicates the Port Role assumed by this Port."
        ::= { mstpStatPortEntry 3 }

-- -------------------------------------------------------------
-- Notification group
-- -------------------------------------------------------------

    mstpNotifyTopologyChg NOTIFICATION-TYPE
        OBJECTS {
            mstpStatInstIndex
        }
        STATUS current
        DESCRIPTION
            "Generated when topology change is detected."
        ::= { mstpNotification 1 }

    mstpNotifyNewRoot NOTIFICATION-TYPE
        OBJECTS {
            mstpStatInstIndex
        }
        STATUS current
        DESCRIPTION
            "Generated whenever a new root bridge is selected in the topology."
        ::= { mstpNotification 2 }

    mstpNotifyNewPortRole NOTIFICATION-TYPE
        OBJECTS {
            mstpStatInstIndex,
            mstpStatPortIndex,
            mstpStatNewRoleType,
            mstpStatOldRoleType
        }
        STATUS current
        DESCRIPTION
            "Generated whenever a new role is selected for the port."
        ::= { mstpNotification 3 }

END
