-- ****************************************************************
-- *  Moxa Switching - QoS PRIVATE MIB
-- *
-- *  Copyright (c) 2019 by Moxa Inc.
-- *  All rights reserved.
-- *****************************************************************

MOXA-QoS-MIB DEFINITIONS ::= BEGIN
    IMPORTS
        MODULE-IDENTITY, NOTIFICATION-TYPE, OBJECT-TYPE, IpAddress
        	FROM SNMPv2-SMI
        TEXTUAL-CONVENTION, DateAndTime, MacAddress, DisplayString, TruthValue
        	FROM SNMPv2-TC
        basicLayer2
          FROM MOXA-SWITCHING-MIB;

    mxQos MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa qos"

        REVISION    "202202170000Z"
        DESCRIPTION "update CONTACT-INFO"

        REVISION    "201906300000Z"
        DESCRIPTION "Initial Revision"

        ::= { basicLayer2 9 }

-- -------------------------------------------------------------
-- groups in the MOXA-QOS-MIB MIB
-- -------------------------------------------------------------

  -- qosNotification		 OBJECT IDENTIFIER ::= { mxQos 0 }
  qosConfiguration		 OBJECT IDENTIFIER ::= { mxQos 1 }
  -- qosStatus		   OBJECT IDENTIFIER ::= { mxQos 2 }
  -- qosExtensions		 OBJECT IDENTIFIER ::= { mxQos 3 }

-- -------------------------------------------------------------
-- configuration group
-- -------------------------------------------------------------

  qosConfigDscpMappingTable OBJECT-TYPE
      SYNTAX SEQUENCE OF QoSConfigDscpMappingEntry
      MAX-ACCESS not-accessible
      STATUS current
      DESCRIPTION
          "The QoS DSCP mapping rule table."
      ::= { qosConfiguration 1 }

  qosConfigDscpMappingEntry OBJECT-TYPE
      SYNTAX QoSConfigDscpMappingEntry
      MAX-ACCESS not-accessible
      STATUS current
      DESCRIPTION
          "The QoS DSCP mapping rule entry."
      INDEX { qosConfigDscpMappingIndex }
      ::= { qosConfigDscpMappingTable 1 }

  QoSConfigDscpMappingEntry ::=
      SEQUENCE {
          qosConfigDscpMappingIndex
              INTEGER,
          qosConfigDscpMappingValue
              INTEGER
      }

  qosConfigDscpMappingIndex OBJECT-TYPE
      SYNTAX INTEGER 
      MAX-ACCESS not-accessible
      STATUS current
      DESCRIPTION
          "The QoS DSCP mapping rule index."
      ::= { qosConfigDscpMappingEntry 1 }

  qosConfigDscpMappingValue OBJECT-TYPE
      SYNTAX INTEGER (0..7)
      MAX-ACCESS read-write
      STATUS current
      DESCRIPTION
          "This object is used to set the DSCP priority mapping rule.

           Classification of QoS will mapping DSCP priority of receive
		   packet to CoS priority for each port.

           If port receive packet with DSCP priority, then
		   will refer the CoS priority which is configure on this 
		   port for packet."
		   
      ::= { qosConfigDscpMappingEntry 2 }

  qosConfigCoSMappingTable OBJECT-TYPE
      SYNTAX SEQUENCE OF QoSConfigCoSMappingEntry
      MAX-ACCESS not-accessible
      STATUS current
      DESCRIPTION
          "The QoS CoS mapping rule table."
      ::= { qosConfiguration 2 }

  qosConfigCoSMappingEntry OBJECT-TYPE
      SYNTAX QoSConfigCoSMappingEntry
      MAX-ACCESS not-accessible
      STATUS current
      DESCRIPTION
          "The QoS CoS mapping rule entry."
      INDEX { qosConfigCoSMappingIndex }
      ::= { qosConfigCoSMappingTable 1 }

  QoSConfigCoSMappingEntry ::=
      SEQUENCE {
          qosConfigCoSMappingIndex
              INTEGER,
          qosConfigCoSMappingValue
              INTEGER
      }

  qosConfigCoSMappingIndex OBJECT-TYPE
      SYNTAX INTEGER 
      MAX-ACCESS not-accessible
      STATUS current
      DESCRIPTION
          "The QoS DSCP mapping rule index."
      ::= { qosConfigCoSMappingEntry 1 }
  
  qosConfigCoSMappingValue OBJECT-TYPE
      SYNTAX INTEGER (1..8)
      MAX-ACCESS read-write
      STATUS current
      DESCRIPTION
          "This object is used to set the CoS priority mapping rule.

           Classification of QoS will mapping CoS priority of receive
		   packet to queue ID for each port.

           If port receive packet with CoS priority with DSCP priority 
		   is mapping to CoS priority, then will refer the queue ID 
		   which is configure on this port for packet."
		   
      ::= { qosConfigCoSMappingEntry 2 }
  
  qosConfigDefaultPriorityTable OBJECT-TYPE
      SYNTAX SEQUENCE OF QoSConfigDefaultPriorityEntry
      MAX-ACCESS not-accessible
      STATUS current
      DESCRIPTION
          "The QoS default priority of port table."
      ::= { qosConfiguration 3 }

  qosConfigDefaultPriorityEntry OBJECT-TYPE
      SYNTAX QoSConfigDefaultPriorityEntry
      MAX-ACCESS not-accessible
      STATUS current
      DESCRIPTION
          "The QoS default priority of port entry."
      INDEX { qosConfigDefaultPriorityIndex }
      ::= { qosConfigDefaultPriorityTable 1 }

  QoSConfigDefaultPriorityEntry ::=
      SEQUENCE {
          qosConfigDefaultPriorityIndex
              INTEGER,
          qosConfigDefaultPriorityValue
              INTEGER
      }
  
  qosConfigDefaultPriorityIndex OBJECT-TYPE
      SYNTAX INTEGER 
      MAX-ACCESS not-accessible
      STATUS current
      DESCRIPTION
          "The QoS default priority of port index."
      ::= { qosConfigDefaultPriorityEntry 1 }
  
  qosConfigDefaultPriorityValue OBJECT-TYPE
      SYNTAX INTEGER (0..7)
      MAX-ACCESS read-write
      STATUS current
      DESCRIPTION
          "This object is used to set the default priority of port."
		   
      ::= { qosConfigDefaultPriorityEntry 2 }
  
  qosConfigPbitPreferenceTable OBJECT-TYPE
      SYNTAX SEQUENCE OF QoSConfigPbitPreferenceEntry
      MAX-ACCESS not-accessible
      STATUS current
      DESCRIPTION
          "The QoS Pbit Preference of port table."
      ::= { qosConfiguration 4 }

  qosConfigPbitPreferenceEntry OBJECT-TYPE
      SYNTAX QoSConfigPbitPreferenceEntry
      MAX-ACCESS not-accessible
      STATUS current
      DESCRIPTION
          "The QoS Pbit Preference of port entry."
      INDEX { qosConfigPbitPreferenceIndex }
      ::= { qosConfigPbitPreferenceTable 1 }

  QoSConfigPbitPreferenceEntry ::=
      SEQUENCE {
          qosConfigPbitPreferenceIndex
              INTEGER,
          qosConfigPbitPreferenceType
              INTEGER
      }
  
  qosConfigPbitPreferenceIndex OBJECT-TYPE
      SYNTAX INTEGER 
      MAX-ACCESS not-accessible
      STATUS current
      DESCRIPTION
          "The QoS Pbit Preference of port index."
      ::= { qosConfigPbitPreferenceEntry 1 }
  
  qosConfigPbitPreferenceType OBJECT-TYPE
      SYNTAX INTEGER {dscp(0), cos(1)}
      MAX-ACCESS read-write
      STATUS current
      DESCRIPTION
          "This object is used to set the Pbit Preference of port."
		   
      ::= { qosConfigPbitPreferenceEntry 2 }
  
  qosConfigMeterTable OBJECT-TYPE
      SYNTAX SEQUENCE OF QoSConfigMeterEntry
      MAX-ACCESS not-accessible
      STATUS current
      DESCRIPTION
          "The QoS meter rule table."
      ::= { qosConfiguration 5 }

  qosConfigMeterEntry OBJECT-TYPE
      SYNTAX QoSConfigMeterEntry
      MAX-ACCESS not-accessible
      STATUS current
      DESCRIPTION
          "The QoS meter rule entry."
      INDEX { qosConfigMeterIndex }
      ::= { qosConfigMeterTable 1 }

  QoSConfigMeterEntry ::=
      SEQUENCE {
          qosConfigMeterIndex
              INTEGER,
		  qosConfigMeterColorModeType
			  INTEGER,
		  qosConfigMeterType
		      INTEGER,
		  qosConfigMeterCIRValue
		      INTEGER,
		  qosConfigMeterCBSValue
		      INTEGER,
		  qosConfigMeterEBSValue
		      INTEGER,
		  qosConfigMeterConActType
		      INTEGER,
		  qosConfigMeterConReMarkCoSValue
		      INTEGER,
		  qosConfigMeterConReMarkDSCPValue
		      INTEGER,
		  qosConfigMeterExcActType
		      INTEGER,
		  qosConfigMeterExcReMarkCoSValue
		      INTEGER,
		  qosConfigMeterExcReMarkDSCPValue
		      INTEGER,
		  qosConfigMeterVioActType
		      INTEGER,
		  qosConfigMeterVioReMarkCoSValue
		      INTEGER,
		  qosConfigMeterVioReMarkDSCPValue
		      INTEGER
      }
  
  qosConfigMeterIndex OBJECT-TYPE
      SYNTAX INTEGER 
      MAX-ACCESS not-accessible
      STATUS current
      DESCRIPTION
          "The QoS meter rule index."
      ::= { qosConfigMeterEntry 1 }
  
  qosConfigMeterColorModeType OBJECT-TYPE
      SYNTAX INTEGER {blind(0), aware(1)}
      MAX-ACCESS read-write
      STATUS current
      DESCRIPTION
          "This object is used to set the color mode of port.
		  
		   If color mode is set to blind, QoS will not refer the preview 
		   color information of packet.
		   
		   On the other hand, QoS refer preview color information of packet
		   when color mode set to aware"
		   
      ::= { qosConfigMeterEntry 2 }
	  
  qosConfigMeterType OBJECT-TYPE
      SYNTAX INTEGER {simpleTokenBucket(0), srTCM(1)}
      MAX-ACCESS read-write
      STATUS current
      DESCRIPTION
          "This object is used to set the meter type of port.
		  
		   srTCM is description in RFC 2697"
		   
      ::= { qosConfigMeterEntry 3 }
	  
  qosConfigMeterCIRValue OBJECT-TYPE
      SYNTAX INTEGER (1..1000)
      MAX-ACCESS read-write
      STATUS current
      DESCRIPTION
          "This object is used to set the meter CIR of port.
		   
		   The unit of CIR is Mbps"
		   
      ::= { qosConfigMeterEntry 4 }
	
  qosConfigMeterCBSValue OBJECT-TYPE
      SYNTAX INTEGER (10..10240)
      MAX-ACCESS read-write
      STATUS current
      DESCRIPTION
          "This object is used to set the meter CBS of port.
		   
		   The unit of CBS is KByte"
		   
      ::= { qosConfigMeterEntry 5 }
	  	
  qosConfigMeterEBSValue OBJECT-TYPE
      SYNTAX INTEGER (10..10240)
      MAX-ACCESS read-write
      STATUS current
      DESCRIPTION
          "This object is used to set the meter EBS of port.
		   
		   The unit of EBS is KByte
		   EBS can configure when meter type is srTCM"
		   
      ::= { qosConfigMeterEntry 6 }
	  
  qosConfigMeterConActType OBJECT-TYPE
      SYNTAX INTEGER {do-nothing(0), remark-cos(1), remark-dscp(2)}
      MAX-ACCESS read-write
      STATUS current
      DESCRIPTION
          "This object is used to set the confirm action of port.
		   
		   do-nothing will not doning any action
		   remark cos will change cos priority of packet
		   remakr dscp will change dscp priority of packet"
		   
      ::= { qosConfigMeterEntry 7 }
	  
  qosConfigMeterConReMarkCoSValue OBJECT-TYPE
      SYNTAX INTEGER (0..7)
      MAX-ACCESS read-write
      STATUS current
      DESCRIPTION
          "This object is used to set the new cos priority on 
		   confirm packetof port.
		   
		   remark cos change cos priority value of packet when action
		   type is setting to remark cos only"
		   
      ::= { qosConfigMeterEntry 8 }
	  
  qosConfigMeterConReMarkDSCPValue OBJECT-TYPE
      SYNTAX INTEGER (0..63)
      MAX-ACCESS read-write
      STATUS current
      DESCRIPTION
          "This object is used to set the new dscp priority on 
		   confirm packetof port.
		   
		   remark dscp change cos priority value of packet when action
		   type is setting to remark dscp only"
		   
      ::= { qosConfigMeterEntry 9 }
	  
  qosConfigMeterExcActType OBJECT-TYPE
      SYNTAX INTEGER {drop(0), remark-cos(1), remark-dscp(2)}
      MAX-ACCESS read-write
      STATUS current
      DESCRIPTION
          "This object is used to set the exceed action of port.
		   
		   drop will drop packet
		   remark cos will change cos priority of packet
		   remakr dscp will change dscp priority of packet
		   
		   exceed action is not support simpleTokenBucket"
		   
      ::= { qosConfigMeterEntry 10 }
	  
  qosConfigMeterExcReMarkCoSValue OBJECT-TYPE
      SYNTAX INTEGER (0..7)
      MAX-ACCESS read-write
      STATUS current
      DESCRIPTION
          "This object is used to set the new cos priority on 
		   exceed packetof port.
		   
		   remark cos change cos priority value of packet when action
		   type is setting to remark cos only
		   
		   exceed action is not support simpleTokenBucket"
		   
      ::= { qosConfigMeterEntry 11 }
	  
  qosConfigMeterExcReMarkDSCPValue OBJECT-TYPE
      SYNTAX INTEGER (0..63)
      MAX-ACCESS read-write
      STATUS current
      DESCRIPTION
          "This object is used to set the new dscp priority on 
		   exceed packetof port.
		   
		   remark dscp change cos priority value of packet when action
		   type is setting to remark dscp only
		   
		   exceed action is not support simpleTokenBucket"
		   
      ::= { qosConfigMeterEntry 12 }
  
  qosConfigMeterVioActType OBJECT-TYPE
      SYNTAX INTEGER {drop(0), remark-cos(1), remark-dscp(2)}
      MAX-ACCESS read-write
      STATUS current
      DESCRIPTION
          "This object is used to set the violate action of port.
		   
		   drop will drop packet
		   remark cos will change cos priority of packet
		   remakr dscp will change dscp priority of packet"
		   
      ::= { qosConfigMeterEntry 13 }
	  
  qosConfigMeterVioReMarkCoSValue OBJECT-TYPE
      SYNTAX INTEGER (0..7)
      MAX-ACCESS read-write
      STATUS current
      DESCRIPTION
          "This object is used to set the new cos priority on 
		   violate packetof port.
		   
		   remark cos change cos priority value of packet when action
		   type is setting to remark cos only"
		   
      ::= { qosConfigMeterEntry 14 }
	  
  qosConfigMeterVioReMarkDSCPValue OBJECT-TYPE
      SYNTAX INTEGER (0..63)
      MAX-ACCESS read-write
      STATUS current
      DESCRIPTION
          "This object is used to set the new dscp priority on 
		   violate packetof port.
		   
		   remark dscp change cos priority value of packet when action
		   type is setting to remark dscp only"
		   
      ::= { qosConfigMeterEntry 15 }
  
  qosConfigSchedulerTable OBJECT-TYPE
      SYNTAX SEQUENCE OF QoSConfigSchedulerEntry
      MAX-ACCESS not-accessible
      STATUS current
      DESCRIPTION
          "The QoS scheduler rule table."
      ::= { qosConfiguration 6 }

  qosConfigSchedulerEntry OBJECT-TYPE
      SYNTAX QoSConfigSchedulerEntry
      MAX-ACCESS not-accessible
      STATUS current
      DESCRIPTION
          "The QoS scheduler rule entry."
      INDEX { qosConfigSchedulerIndex }
      ::= { qosConfigSchedulerTable 1 }

  QoSConfigSchedulerEntry ::=
      SEQUENCE {
          qosConfigSchedulerIndex
              INTEGER,
		  qosConfigSchedulerType
			  INTEGER
      }
  
  qosConfigSchedulerIndex OBJECT-TYPE
      SYNTAX INTEGER 
      MAX-ACCESS not-accessible
      STATUS current
      DESCRIPTION
          "The QoS scheduler rule index."
      ::= { qosConfigSchedulerEntry 1 }
  
  qosConfigSchedulerType OBJECT-TYPE
      SYNTAX INTEGER {strict-priority(0), wrr(1)}
      MAX-ACCESS read-write
      STATUS current
      DESCRIPTION
          "This object is used to set the scheduler type of port."
	  
      ::= { qosConfigSchedulerEntry 2 }
  
  qosConfigShaperTable OBJECT-TYPE
      SYNTAX SEQUENCE OF QoSConfigShaperEntry
      MAX-ACCESS not-accessible
      STATUS current
      DESCRIPTION
          "The QoS shaper rule table."
      ::= { qosConfiguration 7 }

  qosConfigShaperEntry OBJECT-TYPE
      SYNTAX QoSConfigShaperEntry
      MAX-ACCESS not-accessible
      STATUS current
      DESCRIPTION
          "The QoS shaper rule entry."
      INDEX { qosConfigShaperIndex }
      ::= { qosConfigShaperTable 1 }

  QoSConfigShaperEntry ::=
      SEQUENCE {
          qosConfigShaperIndex
              INTEGER,
		  qosConfigShaperCIRValue
		      INTEGER,
		  qosConfigShaperCBSValue
		      INTEGER
      }
  
  qosConfigShaperIndex OBJECT-TYPE
      SYNTAX INTEGER 
      MAX-ACCESS not-accessible
      STATUS current
      DESCRIPTION
          "The QoS shaper rule index."
      ::= { qosConfigShaperEntry 1 }
	  
  qosConfigShaperCIRValue OBJECT-TYPE
      SYNTAX INTEGER (1..1000)
      MAX-ACCESS read-write
      STATUS current
      DESCRIPTION
          "This object is used to set the shaper CIR of port.
		   
		   The unit of CIR is Mbps"
      ::= { qosConfigShaperEntry 2 }
	  
  qosConfigShaperCBSValue OBJECT-TYPE
      SYNTAX INTEGER (10..10240)
      MAX-ACCESS read-write
      STATUS current
      DESCRIPTION
          "This object is used to set the shaper CBS of port.
		   
		   The unit of CBS is KByte"
      ::= { qosConfigShaperEntry 3 }
  
END
