-- ****************************************************************
-- *  Moxa Switching - Rate Limit Port Shutdown (RLPS) PRIVATE MIB
-- *
-- *  Copyright (c) 2019 by Moxa Inc.
-- *  All rights reserved.
-- *****************************************************************

MOXA-RLPS-MIB DEFINITIONS ::= BEGIN
    IMPORTS
        MODULE-IDENTITY, NOTIFICATION-TYPE, OBJECT-TYPE, IpAddress, TimeTicks, Counter32
        	FROM SNMPv2-SMI
        TEXTUAL-CONVENTION, DateAndTime, MacAddress, DisplayString, TruthValue, RowStatus
        	FROM SNMPv2-TC
        layer2Security
          FROM MOXA-SWITCHING-MIB;

    mxRlps MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa rate limit port disable"

        REVISION    "202202170000Z"
        DESCRIPTION "update CONTACT-INFO"

        REVISION    "201906300000Z"
        DESCRIPTION "Initial Revision"

        ::= { layer2Security 8 }

-- -------------------------------------------------------------
-- groups in the MOXA-RLPS-MIB MIB
-- -------------------------------------------------------------

  rlpsConfiguration		 OBJECT IDENTIFIER ::= { mxRlps 1 }
  -- rlpsStatus		   	 OBJECT IDENTIFIER ::= { mxRlps 2 }
  -- rlpsExtensions		 OBJECT IDENTIFIER ::= { mxRlps 3 }
  rlpsNotification		 OBJECT IDENTIFIER ::= { mxRlps 0 }

-- -------------------------------------------------------------
-- configuration group
-- -------------------------------------------------------------
  rlpsConfigEnable OBJECT-TYPE
	  SYNTAX      INTEGER {
                        enable(1),
                        disable(2)
                  }
      MAX-ACCESS read-write
      STATUS current
      DESCRIPTION
		  " The administrative module status requested by management for Static
            Port Lock in Port Security Module. This enables or disables Port Security
            in the system."
	  DEFVAL  { enable }
      ::= { rlpsConfiguration 1 }
  rlpsConfigReleaseInterval OBJECT-TYPE
      SYNTAX  INTEGER
      MAX-ACCESS read-write
      STATUS current
      DESCRIPTION
		  " The port will startup after the release interval
 	     of time since the port start shutdown. The value range
		 from 0 to 65535 minutes. 0 means unlimited."
	  DEFVAL  { 60 }
      ::= { rlpsConfiguration 2 }


  rlpsConfigPortThresholdTable OBJECT-TYPE
      SYNTAX SEQUENCE OF RlpsConfigPortThresholdEntry
      MAX-ACCESS not-accessible
      STATUS current
      DESCRIPTION
          "display traffic statistics information of interfaces."
      ::= { rlpsConfiguration 3 }

  rlpsConfigPortThresholdEntry OBJECT-TYPE
      SYNTAX RlpsConfigPortThresholdEntry
      MAX-ACCESS not-accessible
      STATUS current
      DESCRIPTION
          "There is one entry in this table for each interface
               port threshold."
      INDEX { rlpsConfigIfIndex }
      ::= { rlpsConfigPortThresholdTable 1 }

  RlpsConfigPortThresholdEntry ::=
      SEQUENCE {
          rlpsConfigIfIndex
              INTEGER,
		  rlpsConfigPortEnable
			  INTEGER,
          rlpsConfigThreshold
              INTEGER
      }

  rlpsConfigIfIndex OBJECT-TYPE
      SYNTAX INTEGER
      MAX-ACCESS not-accessible
      STATUS current
      DESCRIPTION
          "The ifIndex of the port interface"
      ::= { rlpsConfigPortThresholdEntry 1}

  rlpsConfigPortEnable OBJECT-TYPE
      SYNTAX INTEGER
      MAX-ACCESS read-write
      STATUS current
      DESCRIPTION
          "This parameter when true(1) indicates that a port is enabled
            rate limit port shutdown and false(2) indicates that this feature is disabled
            on the port."
      ::= { rlpsConfigPortThresholdEntry 2}

  rlpsConfigThreshold OBJECT-TYPE
      SYNTAX INTEGER
      MAX-ACCESS read-write
      STATUS current
      DESCRIPTION
          "The ingress rate limit. If the traffic loading is
		 over the threshold continue 30 seconds, the port will
		 shut down. 0 means unlimited."
      ::= { rlpsConfigPortThresholdEntry 3}

-- -------------------------------------------------------------
-- Notification group
-- -------------------------------------------------------------
    rlpsNotifyRateLimitOn NOTIFICATION-TYPE
        OBJECTS {
            rlpsConfigIfIndex
        }
        STATUS      current
        DESCRIPTION
            "the port recovery traffic with port up."
        ::= { rlpsNotification 1 }

    rlpsNotifyRateLimitOff NOTIFICATION-TYPE
        OBJECTS {
            rlpsConfigIfIndex
        }
        STATUS      current
        DESCRIPTION
            "The port excessive traffic with port shutdown."
        ::= { rlpsNotification 2 }

END
