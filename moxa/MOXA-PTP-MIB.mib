-- ****************************************************************
-- *  Moxa General (Time) - PTP PRIVATE MIB
-- *
-- *  Copyright (c) 2021 by Moxa Inc.
-- *  All rights reserved.
-- *****************************************************************

MOXA-PTP-MIB DEFINITIONS ::= BEGIN
    IMPORTS
        MODULE-IDENTITY, NOTIFICATION-TYPE,
        enterprises, OBJECT-TYPE, OBJECT-IDENTITY, Gauge32, Unsigned32, Counter32, Counter64, mib-2, Integer32
            FROM SNMPv2-SMI
        TEXTUAL-CONVENTION, DateAndTime, DisplayString, TruthValue, AutonomousType
            FROM SNMPv2-TC
        OBJECT-GROUP, MODULE-COMPLIANCE
            FROM SNMPv2-CONF
        time
            FROM MOXA-GENERAL-MIB
        InterfaceIndexOrZero
            FROM IF-MIB
        PtpClockDomainType, PtpClockIdentity, PtpClockInstanceType, PtpClockIntervalBase2, PtpClockMechanismType, PtpClockPortNumber, PtpClockPortState, PtpClockPortTransportTypeAddress, PtpClockProfileType, PtpClockQualityAccuracyType, PtpClockQualityClassType, PtpClockRoleType, PtpClockStateType, PtpClockTimeInterval, PtpClockTimeSourceType, PtpClockTxModeType, PtpClockType
            FROM PTPBASE-MIB;

    mxPtp MODULE-IDENTITY
        LAST-UPDATED "202111030000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa PTP"

        REVISION    "202111030000Z"
        DESCRIPTION
            "
            Added objects:
                iec6185093Objects
                ieeeC37238Objects
            "

        REVISION    "202103090000Z"
        DESCRIPTION
            "
            Removed objects:
                ieee1588StatSyncLocked
            Added objects:
                ieee1588StatSyncStatus
            "

        REVISION    "201905280000Z"
        DESCRIPTION "Initial Revision"

        ::= { time 3 }

    moxa               OBJECT IDENTIFIER ::= { enterprises 8691 }
    general            OBJECT IDENTIFIER ::= { moxa 602 }
    time               OBJECT IDENTIFIER ::= { general 3 }

-- -------------------------------------------------------------
-- groups in the MOXA-PTP-MIB MIB
-- -------------------------------------------------------------
    ptpObjects                  OBJECT IDENTIFIER ::= { mxPtp 1 }
    ieee1588Objects             OBJECT IDENTIFIER ::= { mxPtp 2 }
    ieee8021AsObjects           OBJECT IDENTIFIER ::= { mxPtp 3 }
    iec6185093Objects           OBJECT IDENTIFIER ::= { mxPtp 4 }
    ieeeC37238Objects           OBJECT IDENTIFIER ::= { mxPtp 5 }

    -- ptpNotification          OBJECT IDENTIFIER ::= { ptpObjects 0 }
    ptpConfiguration            OBJECT IDENTIFIER ::= { ptpObjects 1 }
    -- ptpStatus                OBJECT IDENTIFIER ::= { ptpObjects 2 }
    -- ptpExtensions            OBJECT IDENTIFIER ::= { ptpObjects 3 }

    -- ieee1588Notification     OBJECT IDENTIFIER ::= { ieee1588Objects 0 }
    ieee1588Configuration       OBJECT IDENTIFIER ::= { ieee1588Objects 1 }
    ieee1588Status              OBJECT IDENTIFIER ::= { ieee1588Objects 2 }
    -- ieee1588Extensions       OBJECT IDENTIFIER ::= { ieee1588Objects 3 }

    -- ieee8021AsNotification   OBJECT IDENTIFIER ::= { ieee8021AsObjects 0 }
    ieee8021AsConfiguration     OBJECT IDENTIFIER ::= { ieee8021AsObjects 1 }
    ieee8021AsStatus            OBJECT IDENTIFIER ::= { ieee8021AsObjects 2 }
    -- ieee8021AsExtensions     OBJECT IDENTIFIER ::= { ieee8021AsObjects 3 }

    -- iec6185093Notification   OBJECT IDENTIFIER ::= { iec6185093Objects 0 }
    iec6185093Configuration     OBJECT IDENTIFIER ::= { iec6185093Objects 1 }
    iec6185093Status            OBJECT IDENTIFIER ::= { iec6185093Objects 2 }
    -- iec6185093Extensions     OBJECT IDENTIFIER ::= { iec6185093Objects 3 }

    -- ieeeC37238Notification   OBJECT IDENTIFIER ::= { ieeeC37238Objects 0 }
    ieeeC37238Configuration     OBJECT IDENTIFIER ::= { ieeeC37238Objects 1 }
    ieeeC37238Status            OBJECT IDENTIFIER ::= { ieeeC37238Objects 2 }
    -- ieeeC37238Extensions     OBJECT IDENTIFIER ::= { ieeeC37238Objects 3 }
 
-- -------------------------------------------------------------
-- configuration group
-- -------------------------------------------------------------
------------
-- Global -- 
------------

    ptpConfigEnable OBJECT-TYPE
        SYNTAX      TruthValue
        MAX-ACCESS  read-write
        STATUS      current
        DESCRIPTION
               "This globally enables or disables PTP service in the system. 
                A value of 'enabled' (1) indicates that PTP service is enabled
                on the device. A value of 'disabled' (2) indicates that PTP
                service is disabled."
        ::= { ptpConfiguration 1 }

    ptpPortConfigTable OBJECT-TYPE
        SYNTAX      SEQUENCE OF PtpPortConfigEntry
        MAX-ACCESS  not-accessible
        STATUS      current
        DESCRIPTION
                "Table of information about the PTP port profile."
        ::= { ptpConfiguration 2 }

    ptpPortConfigEntry OBJECT-TYPE
        SYNTAX      PtpPortConfigEntry
        MAX-ACCESS  not-accessible
        STATUS      current
        DESCRIPTION
                "A table entry that contains profile information for
                 a single clock port."
        INDEX  { ptpPortConfigIndex }
        ::= { ptpPortConfigTable 1 }

    PtpPortConfigEntry ::= 
        SEQUENCE {
            ptpPortConfigIndex          PtpClockPortNumber,
            ptpPortConfigProfile        INTEGER
        }

    ptpPortConfigIndex OBJECT-TYPE
        SYNTAX      PtpClockPortNumber 
        MAX-ACCESS  not-accessible
        STATUS      current
        DESCRIPTION
                "This object specifies the PTP portNumber associated with this
                 PTP port."
        ::= { ptpPortConfigEntry 1 }

    ptpPortConfigProfile OBJECT-TYPE
        SYNTAX  INTEGER {
                    as(1),
                    as-rev(2),
                    ieee-1588-default-2008(3),
                    iec-61850-9-3-2016(4),
                    ieee-c37-238-2017(5)
                }
        MAX-ACCESS  read-write
        STATUS      current
        DESCRIPTION
                "This object specifies the profile of the system."
        DEFVAL  { 1 }   
        ::= { ptpPortConfigEntry 2 }

-- -------------------------------------------------------------
-- status group
-- -------------------------------------------------------------
---------------
-- IEEE 1588 -- 
---------------
    ieee1588StatSyncStatus OBJECT-TYPE
        SYNTAX Unsigned32
        MAX-ACCESS read-only
        STATUS current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 1 }
        ::= { ieee1588Status 1 }

    ieee1588StatSlavePort OBJECT-TYPE
        SYNTAX      Integer32(1..255)
        MAX-ACCESS  read-only
        STATUS      current
        DESCRIPTION
                "Indicate the port which is in the SLAVE state."
        ::= { ieee1588Status 2 }

    ieee1588StatClockTime OBJECT-TYPE
        SYNTAX      DisplayString
        MAX-ACCESS  read-only
        STATUS      current
        DESCRIPTION
                "Indicate the PTP Clock Time."
        ::= { ieee1588Status 3 }

---------------
-- 802 1AS -- 
---------------
    ieee8021AsStatSyncStatus OBJECT-TYPE
        SYNTAX Unsigned32
        MAX-ACCESS read-only
        STATUS current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 2 }
        ::= { ieee8021AsStatus 1 }

    ieee8021AsStatSlavePort OBJECT-TYPE
        SYNTAX      Integer32(1..255)
        MAX-ACCESS  read-only
        STATUS      current
        DESCRIPTION
                "Indicate the port which is in the SLAVE state."
        ::= { ieee8021AsStatus 2 }

    ieee8021AsStatClockTime OBJECT-TYPE
        SYNTAX      DisplayString
        MAX-ACCESS  read-only
        STATUS      current
        DESCRIPTION
                "Indicate the PTP Clock Time."
        ::= { ieee8021AsStatus 3 }

------------------
-- IEC61850-9-3 -- 
------------------
    iec6185093StatSyncStatus OBJECT-TYPE
        SYNTAX Unsigned32
        MAX-ACCESS read-only
        STATUS current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 2 }
        ::= { iec6185093Status 1 }

    iec6185093StatSlavePort OBJECT-TYPE
        SYNTAX      Integer32(1..255)
        MAX-ACCESS  read-only
        STATUS      current
        DESCRIPTION
                "Indicate the port which is in the SLAVE state."
        ::= { iec6185093Status 2 }

    iec6185093StatClockTime OBJECT-TYPE
        SYNTAX      DisplayString
        MAX-ACCESS  read-only
        STATUS      current
        DESCRIPTION
                "Indicate the PTP Clock Time."
        ::= { iec6185093Status 3 }

--------------
-- C37.238 -- 
--------------
    ieeeC37238StatSyncStatus OBJECT-TYPE
        SYNTAX Unsigned32
        MAX-ACCESS read-only
        STATUS current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 2 }
        ::= { ieeeC37238Status 1 }

    ieeeC37238StatSlavePort OBJECT-TYPE
        SYNTAX      Integer32(1..255)
        MAX-ACCESS  read-only
        STATUS      current
        DESCRIPTION
                "Indicate the port which is in the SLAVE state."
        ::= { ieeeC37238Status 2 }

    ieeeC37238StatClockTime OBJECT-TYPE
        SYNTAX      DisplayString
        MAX-ACCESS  read-only
        STATUS      current
        DESCRIPTION
                "Indicate the PTP Clock Time."
        ::= { ieeeC37238Status 3 }

END
