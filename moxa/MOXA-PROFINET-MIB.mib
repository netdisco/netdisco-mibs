-- *****************************************************************
-- *  Moxa General (System Management) - PROFINET PRIVATE MIB
-- *
-- *  Copyright (c) 2019 by Moxa Inc.
-- *  All rights reserved. 
-- *****************************************************************
MOXA-PROFINET-MIB DEFINITIONS ::= BEGIN
    IMPORTS
        MODULE-IDENTITY, OBJECT-TYPE, Integer32,
        enterprises
            FROM SNMPv2-SMI
        TEXTUAL-CONVENTION, TruthValue
            FROM SNMPv2-TC;

    mxProfinet MODULE-IDENTITY
        LAST-UPDATED "202303130000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines settings used for PROFINET"

        REVISION    "202303130000Z"
        DESCRIPTION "Initial Revision"

        ::= { systemManagement 11 }

    moxa               OBJECT IDENTIFIER ::= { enterprises 8691 }
    general            OBJECT IDENTIFIER ::= { moxa 602 }
    systemManagement   OBJECT IDENTIFIER ::= { general 1 }

-- -------------------------------------------------------------
-- groups in the MOXA-PROFINET-MIB MIB
-- -------------------------------------------------------------

    -- profinetNotification  OBJECT IDENTIFIER ::= { mxProfinet 0 }
       profinetConfiguration OBJECT IDENTIFIER ::= { mxProfinet 1 }
       profinetStatus        OBJECT IDENTIFIER ::= { mxProfinet 2 }
    -- profinetExtensions    OBJECT IDENTIFIER ::= { mxProfinet 3 }

-- -------------------------------------------------------------
-- configuration group
-- -------------------------------------------------------------

    profinetEnable OBJECT-TYPE
        SYNTAX      TruthValue
        MAX-ACCESS  read-write
        STATUS      current
        DESCRIPTION
            "Enable or Disable PROFINET"
        ::= { profinetConfiguration 1 }

    profinetDeviceName  OBJECT-TYPE
        SYNTAX      OCTET STRING (SIZE(0..240))
        MAX-ACCESS  read-write
        STATUS      current
        DESCRIPTION
            "This object indicates the device name of PROFINET."
        ::= { profinetConfiguration 2 }

-- -------------------------------------------------------------
-- status group
-- -------------------------------------------------------------

    profinetLinkStatus  OBJECT-TYPE
        SYNTAX      TruthValue
        MAX-ACCESS  read-only
        STATUS      current
        DESCRIPTION
            "This object indicates the PROFINET link status between PLC and device."
        ::= { profinetStatus 1 }
END
