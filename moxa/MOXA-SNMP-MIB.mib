-- ****************************************************************
-- *  Moxa General (network Management) - SNMP PRIVATE MIB
-- *
-- *  Copyright (c) 2019 by Moxa Inc.
-- *  All rights reserved.
-- *****************************************************************

MOXA-SNMP-MIB DEFINITIONS ::= BEGIN
    IMPORTS
        MODULE-IDENTITY, OBJECT-TYPE,
        enterprises
            FROM SNMPv2-SMI
        DisplayString
            FROM SNMPv2-TC;

  mxSnmp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines moxa SNMP"

        REVISION    "202202170000Z"
        DESCRIPTION "update CONTACT-INFO"

        REVISION    "201906300000Z"
        DESCRIPTION "Initial Revision"

        ::= { networkManagement 1 }

    moxa                 OBJECT IDENTIFIER ::= { enterprises 8691 }
    general              OBJECT IDENTIFIER ::= { moxa 602 }
    networkManagement    OBJECT IDENTIFIER ::= { general 4 }

-- -------------------------------------------------------------
-- groups in the MOXA-SNMP-MIB MIB
-- -------------------------------------------------------------

  -- snmpNotification    OBJECT IDENTIFIER ::= { mxSnmp 0 }
  snmpConfiguration   OBJECT IDENTIFIER ::= { mxSnmp 1 }
  snmpStatus          OBJECT IDENTIFIER ::= { mxSnmp 2 }
  -- snmpExtensions      OBJECT IDENTIFIER ::= { mxSnmp 3 }
-- -------------------------------------------------------------
-- groups in the snmpConfiguration
-- -------------------------------------------------------------

  version OBJECT-TYPE
      SYNTAX INTEGER { v1v2cv3(1), v1v2c(2), v3only(3) }
      MAX-ACCESS read-only
      STATUS current
      DESCRIPTION
          "SNMP Agent Version
           Value :
            1 -> v1v2cv3,
            2 -> v1v2c,
            3 -> v3only"
      ::= { snmpConfiguration 1 }

  readOnlyCommunity OBJECT-TYPE
      SYNTAX DisplayString
      MAX-ACCESS read-write
      STATUS current
      DESCRIPTION
          "SNMP Agent community for Read Only"
      ::= { snmpConfiguration 2 }

-- -------------------------------------------------------------
-- groups in the snmpStatus
-- -------------------------------------------------------------

    snmpServerUserAccountTable OBJECT-TYPE
        SYNTAX SEQUENCE OF SnmpServerUserAccountEntry
        MAX-ACCESS not-accessible
        STATUS current
        DESCRIPTION
            "Table of the DHCP pools configuration."
        ::= { snmpStatus 1 }

    snmpServerUserAccountEntry OBJECT-TYPE
      SYNTAX SnmpServerUserAccountEntry
      MAX-ACCESS not-accessible
      STATUS current
      DESCRIPTION
          "An entry for SNMP Server User Account Table."
      INDEX { snmpServerUserIndex }
      ::= { snmpServerUserAccountTable 1 }

    SnmpServerUserAccountEntry ::=
        SEQUENCE {
            snmpServerUserIndex         INTEGER,
            snmpServerUserName          DisplayString,
            snmpServerUserAuthType      INTEGER,
            snmpServerUserEncryptMethod INTEGER
        }

    snmpServerUserIndex OBJECT-TYPE
        SYNTAX      INTEGER
        MAX-ACCESS  not-accessible
        STATUS      current
        DESCRIPTION
            "Index of Snmp Server User Account Table."
         ::= { snmpServerUserAccountEntry 1 }

    snmpServerUserName OBJECT-TYPE
        SYNTAX      DisplayString
        MAX-ACCESS  read-only
        STATUS      current
        DESCRIPTION
            "User-name of Snmp Server User Account Table Entry."
         ::= { snmpServerUserAccountEntry 2 }

    snmpServerUserAuthType OBJECT-TYPE
        SYNTAX      INTEGER{
                        none (1),
                        md5  (2),
                        sha  (3)
                    }
        MAX-ACCESS  read-only
        STATUS      current
        DESCRIPTION
            "Authentication-type of Snmp Server User Account Table Entry."
         ::= { snmpServerUserAccountEntry 3 }

    snmpServerUserEncryptMethod OBJECT-TYPE
        SYNTAX      INTEGER{
                        disable (1),
                        des (2),
                        aes (3)
                    }
        MAX-ACCESS  read-only
        STATUS      current
        DESCRIPTION
            "Encryption-method of Snmp Server User Account Table Entry."
         ::= { snmpServerUserAccountEntry 4 }

END
