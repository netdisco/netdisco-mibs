-- ****************************************************************
-- *  Moxa General (System Management) - Password Policy PRIVATE MIB
-- *
-- *  Copyright (c) 2019 by Moxa Inc.
-- *  All rights reserved.
-- *****************************************************************

MOXA-SYSTEM-PASSWORD-POLICY-MIB DEFINITIONS ::= BEGIN
    IMPORTS
        MODULE-IDENTITY, OBJECT-TYPE,
        IpAddress, Unsigned32,
        enterprises                     FROM SNMPv2-SMI

        TEXTUAL-CONVENTION, RowStatus,
        DateAndTime, MacAddress,
        DisplayString, TruthValue       FROM SNMPv2-TC;

    mxSysPasswordPolicySvr MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines password policy configuration"

        REVISION    "202202170000Z"
        DESCRIPTION "update CONTACT-INFO"

        REVISION    "201906300000Z"
        DESCRIPTION "Initial Revision"

        ::= { systemManagement 6 }

    moxa              OBJECT IDENTIFIER ::= { enterprises 8691 }
    general           OBJECT IDENTIFIER ::= { moxa 602 }
    systemManagement  OBJECT IDENTIFIER ::= { general 1 }

-- -------------------------------------------------------------
-- groups in the PASSWORD POLICY PRIVATE MIB
-- -------------------------------------------------------------

   -- ppNotification  OBJECT IDENTIFIER ::= { mxSysPasswordPolicySvr 0 }
   ppConfiguration  OBJECT IDENTIFIER ::= { mxSysPasswordPolicySvr 1 }
   -- ppStatus  OBJECT IDENTIFIER ::= { mxSysPasswordPolicySvr 2 }
   -- ppExtension  OBJECT IDENTIFIER ::= { mxSysPasswordPolicySvr 3 }

-- -------------------------------------------------------------
-- Config group
-- -------------------------------------------------------------

    ppConfigPasswordExpireDay OBJECT-TYPE
        SYNTAX      Unsigned32
        MAX-ACCESS  read-write
        STATUS      current
        DESCRIPTION
            "Password Expire Day."
         ::= { ppConfiguration 1 }

    ppConfigMinimumLength OBJECT-TYPE
        SYNTAX      Unsigned32
        MAX-ACCESS  read-write
        STATUS      current
        DESCRIPTION
            "Minimum Length."
         ::= { ppConfiguration 2 }

    ppConfigNumbers OBJECT-TYPE
        SYNTAX      TruthValue
        MAX-ACCESS  read-write
        STATUS      current
        DESCRIPTION
            "Numbers."
         ::= { ppConfiguration 3 }

    ppConfigUppercase OBJECT-TYPE
        SYNTAX      TruthValue
        MAX-ACCESS  read-write
        STATUS      current
        DESCRIPTION
            "Uppercase."
         ::= { ppConfiguration 4 }

    ppConfigLowercase OBJECT-TYPE
        SYNTAX      TruthValue
        MAX-ACCESS  read-write
        STATUS      current
        DESCRIPTION
            "Lowercase."
         ::= { ppConfiguration 5 }

    ppConfigSymbols OBJECT-TYPE
        SYNTAX      TruthValue
        MAX-ACCESS  read-write
        STATUS      current
        DESCRIPTION
            "Symbols."
         ::= { ppConfiguration 6 }

END
