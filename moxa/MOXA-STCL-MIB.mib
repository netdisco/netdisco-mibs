-- ****************************************************************
-- *  Moxa Switching - Storm Control PRIVATE MIB
-- *
-- *  Copyright (c) 2019 by Moxa Inc.
-- *  All rights reserved.
-- *****************************************************************

MOXA-STCL-MIB DEFINITIONS ::= BEGIN
    IMPORTS
        MODULE-IDENTITY, NOTIFICATION-TYPE, OBJECT-TYPE, IpAddress, Integer32
        	FROM SNMPv2-SMI
        TEXTUAL-CONVENTION, DateAndTime, MacAddress, DisplayString, TruthValue
        	FROM SNMPv2-TC
        layer2Security
          FROM MOXA-SWITCHING-MIB;

    mxStcl MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
	    DESCRIPTION
	        "The MIB module defines Moxa storm control"

        REVISION    "202202170000Z"
        DESCRIPTION "update CONTACT-INFO"

	    REVISION    "202012040000Z"
	    DESCRIPTION "Modify the input value range"

    	REVISION    "201906300000Z"
    	DESCRIPTION "Initial Revision"

	    ::= { layer2Security 4 }

-- -------------------------------------------------------------
-- groups in the MOXA-STCL-MIB MIB
-- -------------------------------------------------------------

  -- stclNotification		 OBJECT IDENTIFIER ::= { mxStcl 0 }
  stclConfiguration		 OBJECT IDENTIFIER ::= { mxStcl 1 }
  -- stclStatus		   OBJECT IDENTIFIER ::= { mxStcl 2 }
  -- stclExtensions		 OBJECT IDENTIFIER ::= { mxStcl 3 }

-- -------------------------------------------------------------
-- configuration group
-- -------------------------------------------------------------
	stclConfigTable OBJECT-TYPE 
	   SYNTAX      SEQUENCE OF StclConfigEntry
	   MAX-ACCESS  not-accessible 
	   STATUS      current 
	   DESCRIPTION 
		  "A table to control the rate limiting parameters 
		   either for the entire switch or for each interface in the switch."
	   ::= { stclConfiguration 1 }

	stclConfigEntry OBJECT-TYPE 
	   SYNTAX      StclConfigEntry
	   MAX-ACCESS  not-accessible 
	   STATUS      current 
	   DESCRIPTION 
		  "An entry appears in this table for each physical
		   interface in the switch."
	   INDEX { stclConfigPortIndex }
	   ::= { stclConfigTable 1 }
	   
	StclConfigEntry ::= 
	   SEQUENCE { 
		  stclConfigPortIndex 
			 Integer32, 
		  stclConfigDLFLimitValue
			 Integer32, 
		  stclConfigBCASTLimitValue
			 Integer32, 
		  stclConfigMCASTLimitValue
			 Integer32
	  }

	stclConfigPortIndex OBJECT-TYPE 
	   SYNTAX      Integer32 
	   MAX-ACCESS  not-accessible 
	   STATUS      current 
	   DESCRIPTION 
		  "The interface index for which the configuration in this 
		   entry applies."
	   ::= { stclConfigEntry 1 }
		
	stclConfigDLFLimitValue OBJECT-TYPE 
	   SYNTAX      Integer32 (0..2147483647)
	   MAX-ACCESS  read-write 
	   STATUS      current 
	   DESCRIPTION 
		  "Allows to configure the limiting value for the maximum number
		   of dlf packets that can be transmitted per second over this interface.
		   This value depends on hardware platform.
		   0 is indicate disable storm control on DLF packet."
		   
	   ::= { stclConfigEntry 2 }

	stclConfigBCASTLimitValue OBJECT-TYPE 
	   SYNTAX      Integer32 (0..2147483647)
	   MAX-ACCESS  read-write 
	   STATUS      current 
	   DESCRIPTION 
		  "Allows to configure the limiting value for the maximum number of 
		   broadcast packets that can be transmitted per second over this interface. 
		   This value depends on hardware platform.
		   0 is indicate disable storm control on broadcast packet."
		   
	   ::= { stclConfigEntry 3 }


	stclConfigMCASTLimitValue OBJECT-TYPE 
	   SYNTAX      Integer32 (0..2147483647)
	   MAX-ACCESS  read-write 
	   STATUS      current 
	   DESCRIPTION 
		  "Allows to configure the limiting value for the maximum number of 
		   multicast packets that can be transmitted per second over this interface. 
		   This value depends on hardware platform.
		   0 is indicate disable storm control on multicast packet."
		   
	   ::= { stclConfigEntry 4}

END
