-- ****************************************************************
-- *  Moxa General - Relay Configuration (RC) PRIVATE MIB
-- *
-- *  Copyright (c) 2019 by Moxa Inc.
-- *  All rights reserved.
-- *****************************************************************

MOXA-RELAY-CONFIGURATION-MIB DEFINITIONS ::= BEGIN
    IMPORTS
        MODULE-IDENTITY, NOTIFICATION-TYPE, OBJECT-TYPE, IpAddress, Integer32,
        enterprises
            FROM SNMPv2-SMI
        TEXTUAL-CONVENTION, DateAndTime, MacAddress, DisplayString, TruthValue, RowStatus
            FROM SNMPv2-TC
        eventNotification
            FROM MOXA-GENERAL-MIB;

    mxRelayConfig MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa event notification relay configuration"

        REVISION    "202202170000Z"
        DESCRIPTION "update CONTACT-INFO"

        REVISION    "202109290000Z"
        DESCRIPTION "Add a Relay option in rcConfigRelayAlarmCutoff"

        REVISION    "201906300000Z"
        DESCRIPTION "Initial Revision"

        ::= { eventNotification 4 }

    moxa                 OBJECT IDENTIFIER ::= { enterprises 8691 }
    general              OBJECT IDENTIFIER ::= { moxa         602 }
    eventNotification    OBJECT IDENTIFIER ::= { general        7 }

-- -------------------------------------------------------------
-- groups in the MOXA-RELAY-CONFIGURATION-MIB MIB
-- -------------------------------------------------------------

  -- rcNotification      OBJECT IDENTIFIER ::= { mxRelayConfig 0 }
  rcConfiguration     OBJECT IDENTIFIER ::= { mxRelayConfig 1 }
  -- rcStatus            OBJECT IDENTIFIER ::= { mxRelayConfig 2 }
  -- rcExtensions        OBJECT IDENTIFIER ::= { mxRelayConfig 3 }

-- -------------------------------------------------------------
-- Notification group
-- -------------------------------------------------------------


-- -------------------------------------------------------------
-- configuration group
-- -------------------------------------------------------------

-- Relay Alarm Cut-off

    rcConfigRelayAlarmCutoff OBJECT-TYPE
        SYNTAX INTEGER {
            mgmtRelay(0),
            pwr1Relay(1),
            pwr2Relay(2),
            relay(3)
        }
        MAX-ACCESS read-write
        STATUS current
        DESCRIPTION
            "This command is used to override the relay"
        ::= { rcConfiguration 1 }

-- -------------------------------------------------------------
-- Status group
-- -------------------------------------------------------------



END
