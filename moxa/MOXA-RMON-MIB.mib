-- ****************************************************************
-- *  Moxa Switching - RMON PRIVATE MIB
-- *
-- *  Copyright (c) 2019 by Moxa Inc.
-- *  All rights reserved.
-- *****************************************************************

MOXA-RMON-MIB DEFINITIONS ::= BEGIN
    IMPORTS
        MODULE-IDENTITY, NOTIFICATION-TYPE, OBJECT-TYPE, IpAddress, TimeTicks
            FROM SNMPv2-SMI
        TEXTUAL-CONVENTION, DateAndTime, MacAddress, DisplayString, TruthValue, RowStatus
            FROM SNMPv2-TC
        layer2Diagnosic
            FROM MOXA-SWITCHING-MIB;

    mxRmon MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa RMON"

        REVISION    "202202170000Z"
        DESCRIPTION "update CONTACT-INFO"

        REVISION    "201906300000Z"
        DESCRIPTION "Initial Revision"

        ::= { layer2Diagnosic 7 }

-- -------------------------------------------------------------
-- groups in the MOXA-RMON-MIB MIB
-- -------------------------------------------------------------

    -- rmonNotification          OBJECT IDENTIFIER ::= { mxRmon 0 }
    rmonConfiguration         OBJECT IDENTIFIER ::= { mxRmon 1 }
    -- rmonStatus                OBJECT IDENTIFIER ::= { mxRmon 2 }
    -- rmonExtensions            OBJECT IDENTIFIER ::= { mxRmon 3 }

-- -------------------------------------------------------------
-- configuration group
-- -------------------------------------------------------------
    rmonConfigEnableStatus OBJECT-TYPE
        SYNTAX TruthValue
        MAX-ACCESS read-write
        STATUS current
        DESCRIPTION
            "This object defines the rmonenable flag for rmon"
        ::= { rmonConfiguration 1 }

END
