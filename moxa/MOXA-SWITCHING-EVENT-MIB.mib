-- ****************************************************************
-- *  Moxa General (Events) - Switching Event (SWE) PRIVATE MIB
-- *
-- *  Copyright (c) 2019 by Moxa Inc.
-- *  All rights reserved.
-- *****************************************************************

MOXA-SWITCHING-EVENT-MIB DEFINITIONS ::= BEGIN
    IMPORTS
        MODULE-IDENTITY, NOTIFICATION-TYPE, OBJECT-TYPE, IpAddress, Unsigned32,
        enterprises
            FROM SNMPv2-SMI
        TEXTUAL-CONVENTION, DateAndTime, MacAddress, DisplayString, TruthValue, RowStatus
            FROM SNMPv2-TC
        eventNotification
            FROM MOXA-GENERAL-MIB;

    mxSwEvent MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa Event Notification switching event"

        REVISION    "202202170000Z"
        DESCRIPTION "update CONTACT-INFO"

        REVISION    "202109290000Z"
        DESCRIPTION
            "Add OIDs:
                 sweConfigRstpTopologyChangedRelayEnable
                 sweConfigLldpTableChangedRelayEnable"

        REVISION    "201906300000Z"
        DESCRIPTION "Initial Revision"

        ::= { mxEvents 3 }

    moxa                 OBJECT IDENTIFIER ::= { enterprises 8691 }
    general              OBJECT IDENTIFIER ::= { moxa 602 }
    eventNotification    OBJECT IDENTIFIER ::= { general 7 }
    mxEvents             OBJECT IDENTIFIER ::= { eventNotification 1 }

-- -------------------------------------------------------------
-- groups in the MOXA-SWITCHING-EVENT-MIB MIB 
-- -------------------------------------------------------------

  sweNotification      OBJECT IDENTIFIER ::= { mxSwEvent 0 }
  sweConfiguration     OBJECT IDENTIFIER ::= { mxSwEvent 1 }
  sweStatus            OBJECT IDENTIFIER ::= { mxSwEvent 2 }
  -- sweExtensions        OBJECT IDENTIFIER ::= { mxSwEvent 3 }


-- -------------------------------------------------------------
-- configuration group
-- -------------------------------------------------------------

-- Topology Changed

    sweConfigTopologyChanged OBJECT IDENTIFIER ::= { sweConfiguration 1 }

    sweConfigTopologyChangedEnable OBJECT-TYPE
        SYNTAX TruthValue
        MAX-ACCESS read-write
        STATUS current
        DESCRIPTION
            "This enables or disables the event Topology Changed in the event notification. 
            A value of 'true' (1) indicates that notifications are 
            allowed to notify the user while the redundant protocol topology changed.
            A value of 'false'(2) indicates that notifications are not 
            allowed to notify the user while the redundant protocol topology changed."
        ::= { sweConfigTopologyChanged 1 }

    sweConfigTopologyChangedAction OBJECT IDENTIFIER ::= { sweConfigTopologyChanged 2 }

    sweConfigTopologyChangedTrapEnable OBJECT-TYPE
        SYNTAX TruthValue
        MAX-ACCESS read-write
        STATUS current
        DESCRIPTION
            "This enables or disables the notification action trap in the event Topology Changed. 
            A value of 'true' (1) indicates that the notification action trap is 
            allowed to notify the user while the redundant protocol topology changed.
            A value of 'false'(2) indicates that the notification action trap is not 
            allowed to notify the user while the redundant protocol topology changed."
        ::= { sweConfigTopologyChangedAction 1 }

    sweConfigTopologyChangedEmailEnable OBJECT-TYPE
        SYNTAX TruthValue
        MAX-ACCESS read-write
        STATUS current
        DESCRIPTION
            "This enables or disables the notification action email in the event Topology Changed. 
            A value of 'true' (1) indicates that the notification action email is 
            allowed to notify the user while the redundant protocol topology changed.
            A value of 'false'(2) indicates that the notification action email is not 
            allowed to notify the user while the redundant protocol topology changed."
        ::= { sweConfigTopologyChangedAction 2 }

    sweConfigTopologyChangedMgmtRelayEnable OBJECT-TYPE
        SYNTAX TruthValue
        MAX-ACCESS read-write
        STATUS current
        DESCRIPTION
            "This enables or disables the notification action MGMT relay in the event Topology Changed. 
            A value of 'true' (1) indicates that the notification action MGMT relay is 
            allowed to notify the user while the redundant protocol topology changed.
            A value of 'false'(2) indicates that the notification action MGMT relay is not 
            allowed to notify the user while the redundant protocol topology changed."
        ::= { sweConfigTopologyChangedAction 3 }

    sweConfigTopologyChangedPwr1RelayEnable OBJECT-TYPE
        SYNTAX TruthValue
        MAX-ACCESS read-write
        STATUS current
        DESCRIPTION
            "This enables or disables the notification action PWR1 relay in the event Topology Changed. 
            A value of 'true' (1) indicates that the notification action PWR1 relay is 
            allowed to notify the user while the redundant protocol topology changed.
            A value of 'false'(2) indicates that the notification action PWR1 relay is not 
            allowed to notify the user while the redundant protocol topology changed."
        ::= { sweConfigTopologyChangedAction 4 }

    sweConfigTopologyChangedPwr2RelayEnable OBJECT-TYPE
        SYNTAX TruthValue
        MAX-ACCESS read-write
        STATUS current
        DESCRIPTION
            "This enables or disables the notification action PWR2 relay in the event Topology Changed. 
            A value of 'true' (1) indicates that the notification action PWR2 relay is 
            allowed to notify the user while the redundant protocol topology changed.
            A value of 'false'(2) indicates that the notification action PWR2 relay is not 
            allowed to notify the user while the redundant protocol topology changed."
        ::= { sweConfigTopologyChangedAction 5 }

-- Coupling Changed

    sweConfigCouplingChanged OBJECT IDENTIFIER ::= { sweConfiguration 2 }

    sweConfigCouplingChangedEnable OBJECT-TYPE
        SYNTAX TruthValue
        MAX-ACCESS read-write
        STATUS current
        DESCRIPTION
            "This enables or disables the event Coupling Changed in the event notification. 
            A value of 'true' (1) indicates that notifications are 
            allowed to notify the user while the turbo ring coupling changed.
            A value of 'false'(2) indicates that notifications are not 
            allowed to notify the user while the turbo ring coupling changed."
        ::= { sweConfigCouplingChanged 1 }

    sweConfigCouplingChangedAction OBJECT IDENTIFIER ::= { sweConfigCouplingChanged 2 }

    sweConfigCouplingChangedTrapEnable OBJECT-TYPE
        SYNTAX TruthValue
        MAX-ACCESS read-write
        STATUS current
        DESCRIPTION
            "This enables or disables the notification action trap in the event Coupling Changed. 
            A value of 'true' (1) indicates that the notification action trap is 
            allowed to notify the user while the turbo ring coupling changed.
            A value of 'false'(2) indicates that the notification action trap is not 
            allowed to notify the user while the turbo ring coupling changed."
        ::= { sweConfigCouplingChangedAction 1 }

    sweConfigCouplingChangedEmailEnable OBJECT-TYPE
        SYNTAX TruthValue
        MAX-ACCESS read-write
        STATUS current
        DESCRIPTION
            "This enables or disables the notification action email in the event Coupling Changed. 
            A value of 'true' (1) indicates that the notification action email is 
            allowed to notify the user while the turbo ring coupling changed.
            A value of 'false'(2) indicates that the notification action email is not 
            allowed to notify the user while the turbo ring coupling changed."
        ::= { sweConfigCouplingChangedAction 2 }

    sweConfigCouplingChangedMgmtRelayEnable OBJECT-TYPE
        SYNTAX TruthValue
        MAX-ACCESS read-write
        STATUS current
        DESCRIPTION
            "This enables or disables the notification action MGMT relay in the event Coupling Changed. 
            A value of 'true' (1) indicates that the notification action MGMT relay is 
            allowed to notify the user while the turbo ring coupling changed.
            A value of 'false'(2) indicates that the notification action MGMT relay is not 
            allowed to notify the user while the turbo ring coupling changed."
        ::= { sweConfigCouplingChangedAction 3 }

    sweConfigCouplingChangedPwr1RelayEnable OBJECT-TYPE
        SYNTAX TruthValue
        MAX-ACCESS read-write
        STATUS current
        DESCRIPTION
            "This enables or disables the notification action PWR1 relay in the event Coupling Changed. 
            A value of 'true' (1) indicates that the notification action PWR1 relay is 
            allowed to notify the user while the turbo ring coupling changed.
            A value of 'false'(2) indicates that the notification action PWR1 relay is not 
            allowed to notify the user while the turbo ring coupling changed."
        ::= { sweConfigCouplingChangedAction 4 }

    sweConfigCouplingChangedPwr2RelayEnable OBJECT-TYPE
        SYNTAX TruthValue
        MAX-ACCESS read-write
        STATUS current
        DESCRIPTION
            "This enables or disables the notification action PWR2 relay in the event Coupling Changed. 
            A value of 'true' (1) indicates that the notification action PWR2 relay is 
            allowed to notify the user while the turbo ring coupling changed.
            A value of 'false'(2) indicates that the notification action PWR2 relay is not 
            allowed to notify the user while the turbo ring coupling changed."
        ::= { sweConfigCouplingChangedAction 5 }


-- Master Changed

    sweConfigMasterChanged OBJECT IDENTIFIER ::= { sweConfiguration 3 }

    sweConfigMasterChangedEnable OBJECT-TYPE
        SYNTAX TruthValue
        MAX-ACCESS read-write
        STATUS current
        DESCRIPTION
            "This enables or disables the event Master Changed in the event notification. 
            A value of 'true' (1) indicates that notifications are 
            allowed to notify the user while the turbo ring master changed.
            A value of 'false'(2) indicates that notifications are not 
            allowed to notify the user while the turbo ring master changed."
        ::= { sweConfigMasterChanged 1 }

    sweConfigMasterChangedAction OBJECT IDENTIFIER ::= { sweConfigMasterChanged 2 }

    sweConfigMasterChangedTrapEnable OBJECT-TYPE
        SYNTAX TruthValue
        MAX-ACCESS read-write
        STATUS current
        DESCRIPTION
            "This enables or disables the notification action trap in the event Master Changed. 
            A value of 'true' (1) indicates that the notification action trap is 
            allowed to notify the user while the turbo ring master changed.
            A value of 'false'(2) indicates that the notification action trap is not 
            allowed to notify the user while the turbo ring master changed."
        ::= { sweConfigMasterChangedAction 1 }

    sweConfigMasterChangedEmailEnable OBJECT-TYPE
        SYNTAX TruthValue
        MAX-ACCESS read-write
        STATUS current
        DESCRIPTION
            "This enables or disables the notification action email in the event Master Changed. 
            A value of 'true' (1) indicates that the notification action email is 
            allowed to notify the user while the turbo ring master changed.
            A value of 'false'(2) indicates that the notification action email is not 
            allowed to notify the user while the turbo ring master changed."
        ::= { sweConfigMasterChangedAction 2 }

    sweConfigMasterChangedMgmtRelayEnable OBJECT-TYPE
        SYNTAX TruthValue
        MAX-ACCESS read-write
        STATUS current
        DESCRIPTION
            "This enables or disables the notification action MGMT relay in the event Master Changed. 
            A value of 'true' (1) indicates that the notification action MGMT relay is 
            allowed to notify the user while the turbo ring master changed.
            A value of 'false'(2) indicates that the notification action MGMT relay is not 
            allowed to notify the user while the turbo ring master changed."
        ::= { sweConfigMasterChangedAction 3 }

    sweConfigMasterChangedPwr1RelayEnable OBJECT-TYPE
        SYNTAX TruthValue
        MAX-ACCESS read-write
        STATUS current
        DESCRIPTION
            "This enables or disables the notification action PWR1 relay in the event Master Changed. 
            A value of 'true' (1) indicates that the notification action PWR1 relay is 
            allowed to notify the user while the turbo ring master changed.
            A value of 'false'(2) indicates that the notification action PWR1 relay is not 
            allowed to notify the user while the turbo ring master changed."
        ::= { sweConfigMasterChangedAction 4 }

    sweConfigMasterChangedPwr2RelayEnable OBJECT-TYPE
        SYNTAX TruthValue
        MAX-ACCESS read-write
        STATUS current
        DESCRIPTION
            "This enables or disables the notification action PWR2 relay in the event Master Changed. 
            A value of 'true' (1) indicates that the notification action PWR2 relay is 
            allowed to notify the user while the turbo ring master changed.
            A value of 'false'(2) indicates that the notification action PWR2 relay is not 
            allowed to notify the user while the turbo ring master changed."
        ::= { sweConfigMasterChangedAction 5 }

-- Master Mismatch

    sweConfigMasterMismatch OBJECT IDENTIFIER ::= { sweConfiguration 4 }

    sweConfigMasterMismatchEnable OBJECT-TYPE
        SYNTAX TruthValue
        MAX-ACCESS read-write
        STATUS current
        DESCRIPTION
            "This enables or disables the event Master Mismatch in the event notification. 
            A value of 'true' (1) indicates that notifications are 
            allowed to notify the user while the turbo ring master mismatch.
            A value of 'false'(2) indicates that notifications are not 
            allowed to notify the user while the turbo ring master mismatch."
        ::= { sweConfigMasterMismatch 1 }

    sweConfigMasterMismatchAction OBJECT IDENTIFIER ::= { sweConfigMasterMismatch 2 }

    sweConfigMasterMismatchTrapEnable OBJECT-TYPE
        SYNTAX TruthValue
        MAX-ACCESS read-write
        STATUS current
        DESCRIPTION
            "This enables or disables the notification action trap in the event Master Mismatch. 
            A value of 'true' (1) indicates that the notification action trap is 
            allowed to notify the user while the turbo ring master mismatch.
            A value of 'false'(2) indicates that the notification action trap is not 
            allowed to notify the user while the turbo ring master mismatch."
        ::= { sweConfigMasterMismatchAction 1 }

    sweConfigMasterMismatchEmailEnable OBJECT-TYPE
        SYNTAX TruthValue
        MAX-ACCESS read-write
        STATUS current
        DESCRIPTION
            "This enables or disables the notification action email in the event Master Mismatch. 
            A value of 'true' (1) indicates that the notification action email is 
            allowed to notify the user while the turbo ring master mismatch.
            A value of 'false'(2) indicates that the notification action email is not 
            allowed to notify the user while the turbo ring master mismatch."
        ::= { sweConfigMasterMismatchAction 2 }

    sweConfigMasterMismatchMgmtRelayEnable OBJECT-TYPE
        SYNTAX TruthValue
        MAX-ACCESS read-write
        STATUS current
        DESCRIPTION
            "This enables or disables the notification action MGMT relay in the event Master Mismatch. 
            A value of 'true' (1) indicates that the notification action MGMT relay is 
            allowed to notify the user while the turbo ring master mismatch.
            A value of 'false'(2) indicates that the notification action MGMT relay is not 
            allowed to notify the user while the turbo ring master mismatch."
        ::= { sweConfigMasterMismatchAction 3 }

    sweConfigMasterMismatchPwr1RelayEnable OBJECT-TYPE
        SYNTAX TruthValue
        MAX-ACCESS read-write
        STATUS current
        DESCRIPTION
            "This enables or disables the notification action PWR1 relay in the event Master Mismatch. 
            A value of 'true' (1) indicates that the notification action PWR1 relay is 
            allowed to notify the user while the turbo ring master mismatch.
            A value of 'false'(2) indicates that the notification action PWR1 relay is not 
            allowed to notify the user while the turbo ring master mismatch."
        ::= { sweConfigMasterMismatchAction 4 }

    sweConfigMasterMismatchPwr2RelayEnable OBJECT-TYPE
        SYNTAX TruthValue
        MAX-ACCESS read-write
        STATUS current
        DESCRIPTION
            "This enables or disables the notification action PWR2 relay in the event Master Mismatch. 
            A value of 'true' (1) indicates that the notification action PWR2 relay is 
            allowed to notify the user while the turbo ring master mismatch.
            A value of 'false'(2) indicates that the notification action PWR2 relay is not 
            allowed to notify the user while the turbo ring master mismatch."
        ::= { sweConfigMasterMismatchAction 5 }

-- RSTP Topology Changed

    sweConfigRstpTopologyChanged OBJECT IDENTIFIER ::= { sweConfiguration 5 }

    sweConfigRstpTopologyChangedEnable OBJECT-TYPE
        SYNTAX TruthValue
        MAX-ACCESS read-write
        STATUS current
        DESCRIPTION
            "This enables or disables the event RSTP Topology Changed in the event notification. 
            A value of 'true' (1) indicates that notifications are 
            allowed to notify the user while the RSTP topology changed.
            A value of 'false'(2) indicates that notifications are not 
            allowed to notify the user while the RSTP topology changed."
        ::= { sweConfigRstpTopologyChanged 1 }

    sweConfigRstpTopologyChangedAction OBJECT IDENTIFIER ::= { sweConfigRstpTopologyChanged 2 }

    sweConfigRstpTopologyChangedTrapEnable OBJECT-TYPE
        SYNTAX TruthValue
        MAX-ACCESS read-write
        STATUS current
        DESCRIPTION
            "This enables or disables the notification action trap in the event RSTP Topology Changed. 
            A value of 'true' (1) indicates that the notification action trap is 
            allowed to notify the user while the RSTP topology changed.
            A value of 'false'(2) indicates that the notification action trap is not 
            allowed to notify the user while the RSTP topology changed."
        ::= { sweConfigRstpTopologyChangedAction 1 }

    sweConfigRstpTopologyChangedEmailEnable OBJECT-TYPE
        SYNTAX TruthValue
        MAX-ACCESS read-write
        STATUS current
        DESCRIPTION
            "This enables or disables the notification action email in the event RSTP Topology Changed. 
            A value of 'true' (1) indicates that the notification action email is 
            allowed to notify the user while the RSTP topology changed.
            A value of 'false'(2) indicates that the notification action email is not 
            allowed to notify the user while the RSTP topology changed."
        ::= { sweConfigRstpTopologyChangedAction 2 }

    sweConfigRstpTopologyChangedMgmtRelayEnable OBJECT-TYPE
        SYNTAX TruthValue
        MAX-ACCESS read-write
        STATUS current
        DESCRIPTION
            "This enables or disables the notification action MGMT relay in the event RSTP Topology Changed. 
            A value of 'true' (1) indicates that the notification action MGMT relay is 
            allowed to notify the user while the RSTP topology changed.
            A value of 'false'(2) indicates that the notification action MGMT relay is not 
            allowed to notify the user while the RSTP topology changed."
        ::= { sweConfigRstpTopologyChangedAction 3 }

    sweConfigRstpTopologyChangedPwr1RelayEnable OBJECT-TYPE
        SYNTAX TruthValue
        MAX-ACCESS read-write
        STATUS current
        DESCRIPTION
            "This enables or disables the notification action PWR1 relay in the event RSTP Topology Changed. 
            A value of 'true' (1) indicates that the notification action PWR1 relay is 
            allowed to notify the user while the RSTP topology changed.
            A value of 'false'(2) indicates that the notification action PWR1 relay is not 
            allowed to notify the user while the RSTP topology changed."
        ::= { sweConfigRstpTopologyChangedAction 4 }

    sweConfigRstpTopologyChangedPwr2RelayEnable OBJECT-TYPE
        SYNTAX TruthValue
        MAX-ACCESS read-write
        STATUS current
        DESCRIPTION
            "This enables or disables the notification action PWR2 relay in the event RSTP Topology Changed. 
            A value of 'true' (1) indicates that the notification action PWR2 relay is 
            allowed to notify the user while the RSTP topology changed.
            A value of 'false'(2) indicates that the notification action PWR2 relay is not 
            allowed to notify the user while the RSTP topology changed."
        ::= { sweConfigRstpTopologyChangedAction 5 }

    sweConfigRstpTopologyChangedRelayEnable OBJECT-TYPE
        SYNTAX TruthValue
        MAX-ACCESS read-write
        STATUS current
        DESCRIPTION
            "This enables or disables the notification action relay in the event RSTP Topology Changed. 
            A value of 'true' (1) indicates that the notification action relay is allowed to notify the user while the RSTP topology changed.
            A value of 'false'(2) indicates that the notification action relay is not allowed to notify the user while the RSTP topology changed."
        ::= { sweConfigRstpTopologyChangedAction 6 }

-- RSTP Root Changed

    sweConfigRstpRootChanged OBJECT IDENTIFIER ::= { sweConfiguration 6 }

    sweConfigRstpRootChangedEnable OBJECT-TYPE
        SYNTAX TruthValue
        MAX-ACCESS read-write
        STATUS current
        DESCRIPTION
            "This enables or disables the event RSTP Root Changed in the event notification. 
            A value of 'true' (1) indicates that notifications are 
            allowed to notify the user while the RSTP root changed.
            A value of 'false'(2) indicates that notifications are not 
            allowed to notify the user while the RSTP root changed."
        ::= { sweConfigRstpRootChanged 1 }

    sweConfigRstpRootChangedAction OBJECT IDENTIFIER ::= { sweConfigRstpRootChanged 2 }

    sweConfigRstpRootChangedTrapEnable OBJECT-TYPE
        SYNTAX TruthValue
        MAX-ACCESS read-write
        STATUS current
        DESCRIPTION
            "This enables or disables the notification action trap in the event RSTP Root Changed. 
            A value of 'true' (1) indicates that the notification action trap is 
            allowed to notify the user while the RSTP root changed.
            A value of 'false'(2) indicates that the notification action trap is not 
            allowed to notify the user while the RSTP root changed."
        ::= { sweConfigRstpRootChangedAction 1 }

    sweConfigRstpRootChangedEmailEnable OBJECT-TYPE
        SYNTAX TruthValue
        MAX-ACCESS read-write
        STATUS current
        DESCRIPTION
            "This enables or disables the notification action email in the event RSTP Root Changed. 
            A value of 'true' (1) indicates that the notification action email is 
            allowed to notify the user while the RSTP root changed.
            A value of 'false'(2) indicates that the notification action email is not 
            allowed to notify the user while the RSTP root changed."
        ::= { sweConfigRstpRootChangedAction 2 }

    sweConfigRstpRootChangedMgmtRelayEnable OBJECT-TYPE
        SYNTAX TruthValue
        MAX-ACCESS read-write
        STATUS current
        DESCRIPTION
            "This enables or disables the notification action MGMT relay in the event RSTP Root Changed. 
            A value of 'true' (1) indicates that the notification action MGMT relay is 
            allowed to notify the user while the RSTP root changed.
            A value of 'false'(2) indicates that the notification action MGMT relay is not 
            allowed to notify the user while the RSTP root changed."
        ::= { sweConfigRstpRootChangedAction 3 }

    sweConfigRstpRootChangedPwr1RelayEnable OBJECT-TYPE
        SYNTAX TruthValue
        MAX-ACCESS read-write
        STATUS current
        DESCRIPTION
            "This enables or disables the notification action PWR1 relay in the event RSTP Root Changed. 
            A value of 'true' (1) indicates that the notification action PWR1 relay is 
            allowed to notify the user while the RSTP root changed.
            A value of 'false'(2) indicates that the notification action PWR1 relay is not 
            allowed to notify the user while the RSTP root changed."
        ::= { sweConfigRstpRootChangedAction 4 }

    sweConfigRstpRootChangedPwr2RelayEnable OBJECT-TYPE
        SYNTAX TruthValue
        MAX-ACCESS read-write
        STATUS current
        DESCRIPTION
            "This enables or disables the notification action PWR2 relay in the event RSTP Root Changed. 
            A value of 'true' (1) indicates that the notification action PWR2 relay is 
            allowed to notify the user while the RSTP root changed.
            A value of 'false'(2) indicates that the notification action PWR2 relay is not 
            allowed to notify the user while the RSTP root changed."
        ::= { sweConfigRstpRootChangedAction 5 }

-- RSTP Migration

    sweConfigRstpMigration OBJECT IDENTIFIER ::= { sweConfiguration 7 }

    sweConfigRstpMigrationEnable OBJECT-TYPE
        SYNTAX TruthValue
        MAX-ACCESS read-write
        STATUS current
        DESCRIPTION
            "This enables or disables the event RSTP Migration in the event notification. 
            A value of 'true' (1) indicates that notifications are 
            allowed to notify the user while the RSTP migration.
            A value of 'false'(2) indicates that notifications are not 
            allowed to notify the user while the RSTP migration."
        ::= { sweConfigRstpMigration 1 }

    sweConfigRstpMigrationAction OBJECT IDENTIFIER ::= { sweConfigRstpMigration 2 }

    sweConfigRstpMigrationTrapEnable OBJECT-TYPE
        SYNTAX TruthValue
        MAX-ACCESS read-write
        STATUS current
        DESCRIPTION
            "This enables or disables the notification action trap in the event RSTP Migration. 
            A value of 'true' (1) indicates that the notification action trap is 
            allowed to notify the user while the RSTP migration.
            A value of 'false'(2) indicates that the notification action trap is not 
            allowed to notify the user while the RSTP migration."
        ::= { sweConfigRstpMigrationAction 1 }

    sweConfigRstpMigrationEmailEnable OBJECT-TYPE
        SYNTAX TruthValue
        MAX-ACCESS read-write
        STATUS current
        DESCRIPTION
            "This enables or disables the notification action email in the event RSTP Migration. 
            A value of 'true' (1) indicates that the notification action email is 
            allowed to notify the user while the RSTP migration.
            A value of 'false'(2) indicates that the notification action email is not 
            allowed to notify the user while the RSTP migration."
        ::= { sweConfigRstpMigrationAction 2 }

    sweConfigRstpMigrationMgmtRelayEnable OBJECT-TYPE
        SYNTAX TruthValue
        MAX-ACCESS read-write
        STATUS current
        DESCRIPTION
            "This enables or disables the notification action MGMT relay in the event RSTP Migration. 
            A value of 'true' (1) indicates that the notification action MGMT relay is 
            allowed to notify the user while the RSTP migration.
            A value of 'false'(2) indicates that the notification action MGMT relay is not 
            allowed to notify the user while the RSTP migration."
        ::= { sweConfigRstpMigrationAction 3 }

    sweConfigRstpMigrationPwr1RelayEnable OBJECT-TYPE
        SYNTAX TruthValue
        MAX-ACCESS read-write
        STATUS current
        DESCRIPTION
            "This enables or disables the notification action PWR1 relay in the event RSTP Migration. 
            A value of 'true' (1) indicates that the notification action PWR1 relay is 
            allowed to notify the user while the RSTP migration.
            A value of 'false'(2) indicates that the notification action PWR1 relay is not 
            allowed to notify the user while the RSTP migration."
        ::= { sweConfigRstpMigrationAction 4 }

    sweConfigRstpMigrationPwr2RelayEnable OBJECT-TYPE
        SYNTAX TruthValue
        MAX-ACCESS read-write
        STATUS current
        DESCRIPTION
            "This enables or disables the notification action PWR2 relay in the event RSTP Migration. 
            A value of 'true' (1) indicates that the notification action PWR2 relay is 
            allowed to notify the user while the RSTP migration.
            A value of 'false'(2) indicates that the notification action PWR2 relay is not 
            allowed to notify the user while the RSTP migration."
        ::= { sweConfigRstpMigrationAction 5 }

-- RSTP Invalid BPDU

    sweConfigRstpInvalidBpdu OBJECT IDENTIFIER ::= { sweConfiguration 8 }

    sweConfigRstpInvalidBpduEnable OBJECT-TYPE
        SYNTAX TruthValue
        MAX-ACCESS read-write
        STATUS current
        DESCRIPTION
            "This enables or disables the event RSTP Invalid BPDU in the event notification. 
            A value of 'true' (1) indicates that notifications are 
            allowed to notify the user while the device receive invalid BPDU.
            A value of 'false'(2) indicates that notifications are not 
            allowed to notify the user while the device receive invalid BPDU."
        ::= { sweConfigRstpInvalidBpdu 1 }

    sweConfigRstpInvalidBpduAction OBJECT IDENTIFIER ::= { sweConfigRstpInvalidBpdu 2 }

    sweConfigRstpInvalidBpduTrapEnable OBJECT-TYPE
        SYNTAX TruthValue
        MAX-ACCESS read-write
        STATUS current
        DESCRIPTION
            "This enables or disables the notification action trap in the event RSTP Invalid BPDU. 
            A value of 'true' (1) indicates that the notification action trap is 
            allowed to notify the user while the device receive invalid BPDU.
            A value of 'false'(2) indicates that the notification action trap is not 
            allowed to notify the user while the device receive invalid BPDU."
        ::= { sweConfigRstpInvalidBpduAction 1 }

    sweConfigRstpInvalidBpduEmailEnable OBJECT-TYPE
        SYNTAX TruthValue
        MAX-ACCESS read-write
        STATUS current
        DESCRIPTION
            "This enables or disables the notification action email in the event RSTP Invalid BPDU. 
            A value of 'true' (1) indicates that the notification action email is 
            allowed to notify the user while the device receive invalid BPDU.
            A value of 'false'(2) indicates that the notification action email is not 
            allowed to notify the user while the device receive invalid BPDU."
        ::= { sweConfigRstpInvalidBpduAction 2 }

    sweConfigRstpInvalidBpduMgmtRelayEnable OBJECT-TYPE
        SYNTAX TruthValue
        MAX-ACCESS read-write
        STATUS current
        DESCRIPTION
            "This enables or disables the notification action MGMT relay in the event RSTP Invalid BPDU. 
            A value of 'true' (1) indicates that the notification action MGMT relay is 
            allowed to notify the user while the device receive invalid BPDU.
            A value of 'false'(2) indicates that the notification action MGMT relay is not 
            allowed to notify the user while the device receive invalid BPDU."
        ::= { sweConfigRstpInvalidBpduAction 3 }

    sweConfigRstpInvalidBpduPwr1RelayEnable OBJECT-TYPE
        SYNTAX TruthValue
        MAX-ACCESS read-write
        STATUS current
        DESCRIPTION
            "This enables or disables the notification action PWR1 relay in the event RSTP Invalid BPDU. 
            A value of 'true' (1) indicates that the notification action PWR1 relay is 
            allowed to notify the user while the device receive invalid BPDU.
            A value of 'false'(2) indicates that the notification action PWR1 relay is not 
            allowed to notify the user while the device receive invalid BPDU."
        ::= { sweConfigRstpInvalidBpduAction 4 }

    sweConfigRstpInvalidBpduPwr2RelayEnable OBJECT-TYPE
        SYNTAX TruthValue
        MAX-ACCESS read-write
        STATUS current
        DESCRIPTION
            "This enables or disables the notification action PWR2 relay in the event RSTP Invalid BPDU. 
            A value of 'true' (1) indicates that the notification action PWR2 relay is 
            allowed to notify the user while the device receive invalid BPDU.
            A value of 'false'(2) indicates that the notification action PWR2 relay is not 
            allowed to notify the user while the device receive invalid BPDU."
        ::= { sweConfigRstpInvalidBpduAction 5 }

-- RSTP New Port Role

    sweConfigRstpNewPortRole OBJECT IDENTIFIER ::= { sweConfiguration 9 }

    sweConfigRstpNewPortRoleEnable OBJECT-TYPE
        SYNTAX TruthValue
        MAX-ACCESS read-write
        STATUS current
        DESCRIPTION
            "This enables or disables the event RSTP New Port Role in the event notification. 
            A value of 'true' (1) indicates that notifications are 
            allowed to notify the user while the port role changed.
            A value of 'false'(2) indicates that notifications are not 
            allowed to notify the user while the port role changed."
        ::= { sweConfigRstpNewPortRole 1 }

    sweConfigRstpNewPortRoleAction OBJECT IDENTIFIER ::= { sweConfigRstpNewPortRole 2 }

    sweConfigRstpNewPortRoleTrapEnable OBJECT-TYPE
        SYNTAX TruthValue
        MAX-ACCESS read-write
        STATUS current
        DESCRIPTION
            "This enables or disables the notification action trap in the event RSTP New Port Role. 
            A value of 'true' (1) indicates that the notification action trap is 
            allowed to notify the user while the port role changed.
            A value of 'false'(2) indicates that the notification action trap is not 
            allowed to notify the user while the port role changed."
        ::= { sweConfigRstpNewPortRoleAction 1 }

    sweConfigRstpNewPortRoleEmailEnable OBJECT-TYPE
        SYNTAX TruthValue
        MAX-ACCESS read-write
        STATUS current
        DESCRIPTION
            "This enables or disables the notification action email in the event RSTP New Port Role. 
            A value of 'true' (1) indicates that the notification action email is 
            allowed to notify the user while the port role changed.
            A value of 'false'(2) indicates that the notification action email is not 
            allowed to notify the user while the port role changed."
        ::= { sweConfigRstpNewPortRoleAction 2 }

    sweConfigRstpNewPortRoleMgmtRelayEnable OBJECT-TYPE
        SYNTAX TruthValue
        MAX-ACCESS read-write
        STATUS current
        DESCRIPTION
            "This enables or disables the notification action MGMT relay in the event RSTP New Port Role. 
            A value of 'true' (1) indicates that the notification action MGMT relay is 
            allowed to notify the user while the port role changed.
            A value of 'false'(2) indicates that the notification action MGMT relay is not 
            allowed to notify the user while the port role changed."
        ::= { sweConfigRstpNewPortRoleAction 3 }

    sweConfigRstpNewPortRolePwr1RelayEnable OBJECT-TYPE
        SYNTAX TruthValue
        MAX-ACCESS read-write
        STATUS current
        DESCRIPTION
            "This enables or disables the notification action PWR1 relay in the event RSTP New Port Role. 
            A value of 'true' (1) indicates that the notification action PWR1 relay is 
            allowed to notify the user while the port role changed.
            A value of 'false'(2) indicates that the notification action PWR1 relay is not 
            allowed to notify the user while the port role changed."
        ::= { sweConfigRstpNewPortRoleAction 4 }

    sweConfigRstpNewPortRolePwr2RelayEnable OBJECT-TYPE
        SYNTAX TruthValue
        MAX-ACCESS read-write
        STATUS current
        DESCRIPTION
            "This enables or disables the notification action PWR2 relay in the event RSTP New Port Role. 
            A value of 'true' (1) indicates that the notification action PWR2 relay is 
            allowed to notify the user while the port role changed.
            A value of 'false'(2) indicates that the notification action PWR2 relay is not 
            allowed to notify the user while the port role changed."
        ::= { sweConfigRstpNewPortRoleAction 5 }

-- Redundant Port Health Check Fail

    sweConfigRedundantPortHealthCheckFail OBJECT IDENTIFIER ::= { sweConfiguration 10 }

    sweConfigRedundantPortHealthCheckFailEnable OBJECT-TYPE
        SYNTAX TruthValue
        MAX-ACCESS read-write
        STATUS current
        DESCRIPTION
            "This enables or disables the event Redundant Port Health Check Fail in the event notification. 
            A value of 'true' (1) indicates that notifications are 
            allowed to notify the user while the redundant port health check fail.
            A value of 'false'(2) indicates that notifications are not 
            allowed to notify the user while the redundant port health check fail."
        ::= { sweConfigRedundantPortHealthCheckFail 1 }

    sweConfigRedundantPortHealthCheckFailAction OBJECT IDENTIFIER ::= { sweConfigRedundantPortHealthCheckFail 2 }

    sweConfigRedundantPortHealthCheckFailTrapEnable OBJECT-TYPE
        SYNTAX TruthValue
        MAX-ACCESS read-write
        STATUS current
        DESCRIPTION
            "This enables or disables the notification action trap in the event Redundant Port Health Check Fail. 
            A value of 'true' (1) indicates that the notification action trap is 
            allowed to notify the user while the redundant port health check fail.
            A value of 'false'(2) indicates that the notification action trap is not 
            allowed to notify the user while the redundant port health check fail."
        ::= { sweConfigRedundantPortHealthCheckFailAction 1 }

    sweConfigRedundantPortHealthCheckFailEmailEnable OBJECT-TYPE
        SYNTAX TruthValue
        MAX-ACCESS read-write
        STATUS current
        DESCRIPTION
            "This enables or disables the notification action email in the event Redundant Port Health Check Fail. 
            A value of 'true' (1) indicates that the notification action email is 
            allowed to notify the user while the redundant port health check fail.
            A value of 'false'(2) indicates that the notification action email is not 
            allowed to notify the user while the redundant port health check fail."
        ::= { sweConfigRedundantPortHealthCheckFailAction 2 }

    sweConfigRedundantPortHealthCheckFailMgmtRelayEnable OBJECT-TYPE
        SYNTAX TruthValue
        MAX-ACCESS read-write
        STATUS current
        DESCRIPTION
            "This enables or disables the notification action MGMT relay in the event Redundant Port Health Check Fail. 
            A value of 'true' (1) indicates that the notification action MGMT relay is 
            allowed to notify the user while the redundant port health check fail.
            A value of 'false'(2) indicates that the notification action MGMT relay is not 
            allowed to notify the user while the redundant port health check fail."
        ::= { sweConfigRedundantPortHealthCheckFailAction 3 }

    sweConfigRedundantPortHealthCheckFailPwr1RelayEnable OBJECT-TYPE
        SYNTAX TruthValue
        MAX-ACCESS read-write
        STATUS current
        DESCRIPTION
            "This enables or disables the notification action PWR1 relay in the event Redundant Port Health Check Fail. 
            A value of 'true' (1) indicates that the notification action PWR1 relay is 
            allowed to notify the user while the redundant port health check fail.
            A value of 'false'(2) indicates that the notification action PWR1 relay is not 
            allowed to notify the user while the redundant port health check fail."
        ::= { sweConfigRedundantPortHealthCheckFailAction 4 }

    sweConfigRedundantPortHealthCheckFailPwr2RelayEnable OBJECT-TYPE
        SYNTAX TruthValue
        MAX-ACCESS read-write
        STATUS current
        DESCRIPTION
            "This enables or disables the notification action PWR2 relay in the event Redundant Port Health Check Fail. 
            A value of 'true' (1) indicates that the notification action PWR2 relay is 
            allowed to notify the user while the redundant port health check fail.
            A value of 'false'(2) indicates that the notification action PWR2 relay is not 
            allowed to notify the user while the redundant port health check fail."
        ::= { sweConfigRedundantPortHealthCheckFailAction 5 }

-- Dual Homing path changed

    sweConfigDualHomingPathChanged OBJECT IDENTIFIER ::= { sweConfiguration 11 }

    sweConfigDualHomingPathChangedEnable OBJECT-TYPE
        SYNTAX TruthValue
        MAX-ACCESS read-write
        STATUS current
        DESCRIPTION
            "This enables or disables the event Dual Homing path changed in the event notification. 
            A value of 'true' (1) indicates that notifications are 
            allowed to notify the user while the dual homing path changed.
            A value of 'false'(2) indicates that notifications are not 
            allowed to notify the user while the dual homing path changed."
        ::= { sweConfigDualHomingPathChanged 1 }

    sweConfigDualHomingPathChangedAction OBJECT IDENTIFIER ::= { sweConfigDualHomingPathChanged 2 }

    sweConfigDualHomingPathChangedTrapEnable OBJECT-TYPE
        SYNTAX TruthValue
        MAX-ACCESS read-write
        STATUS current
        DESCRIPTION
            "This enables or disables the notification action trap in the event Dual Homing path changed. 
            A value of 'true' (1) indicates that the notification action trap is 
            allowed to notify the user while the dual homing path changed.
            A value of 'false'(2) indicates that the notification action trap is not 
            allowed to notify the user while the dual homing path changed."
        ::= { sweConfigDualHomingPathChangedAction 1 }

    sweConfigDualHomingPathChangedEmailEnable OBJECT-TYPE
        SYNTAX TruthValue
        MAX-ACCESS read-write
        STATUS current
        DESCRIPTION
            "This enables or disables the notification action email in the event Dual Homing path changed. 
            A value of 'true' (1) indicates that the notification action email is 
            allowed to notify the user while the dual homing path changed.
            A value of 'false'(2) indicates that the notification action email is not 
            allowed to notify the user while the dual homing path changed."
        ::= { sweConfigDualHomingPathChangedAction 2 }

    sweConfigDualHomingPathChangedMgmtRelayEnable OBJECT-TYPE
        SYNTAX TruthValue
        MAX-ACCESS read-write
        STATUS current
        DESCRIPTION
            "This enables or disables the notification action MGMT relay in the event Dual Homing path changed. 
            A value of 'true' (1) indicates that the notification action MGMT relay is 
            allowed to notify the user while the dual homing path changed.
            A value of 'false'(2) indicates that the notification action MGMT relay is not 
            allowed to notify the user while the dual homing path changed."
        ::= { sweConfigDualHomingPathChangedAction 3 }

    sweConfigDualHomingPathChangedPwr1RelayEnable OBJECT-TYPE
        SYNTAX TruthValue
        MAX-ACCESS read-write
        STATUS current
        DESCRIPTION
            "This enables or disables the notification action PWR1 relay in the event Dual Homing path changed. 
            A value of 'true' (1) indicates that the notification action PWR1 relay is 
            allowed to notify the user while the dual homing path changed.
            A value of 'false'(2) indicates that the notification action PWR1 relay is not 
            allowed to notify the user while the dual homing path changed."
        ::= { sweConfigDualHomingPathChangedAction 4 }

    sweConfigDualHomingPathChangedPwr2RelayEnable OBJECT-TYPE
        SYNTAX TruthValue
        MAX-ACCESS read-write
        STATUS current
        DESCRIPTION
            "This enables or disables the notification action PWR2 relay in the event Dual Homing path changed. 
            A value of 'true' (1) indicates that the notification action PWR2 relay is 
            allowed to notify the user while the dual homing path changed.
            A value of 'false'(2) indicates that the notification action PWR2 relay is not 
            allowed to notify the user while the dual homing path changed."
        ::= { sweConfigDualHomingPathChangedAction 5 }

-- 802.1X Auth Fail

    sweConfigDot1xAuthFail OBJECT IDENTIFIER ::= { sweConfiguration 12 }

    sweConfigDot1xAuthFailEnable OBJECT-TYPE
        SYNTAX TruthValue
        MAX-ACCESS read-write
        STATUS current
        DESCRIPTION
            "This enables or disables the event Dot1x Auth Fail in the event notification. 
            A value of 'true' (1) indicates that notifications are 
            allowed to notify the user while the 802.1x authentication fail.
            A value of 'false'(2) indicates that notifications are not 
            allowed to notify the user while the 802.1x authentication fail."
        ::= { sweConfigDot1xAuthFail 1 }

    sweConfigDot1xAuthFailAction OBJECT IDENTIFIER ::= { sweConfigDot1xAuthFail 2 }

    sweConfigDot1xAuthFailTrapEnable OBJECT-TYPE
        SYNTAX TruthValue
        MAX-ACCESS read-write
        STATUS current
        DESCRIPTION
            "This enables or disables the notification action trap in the event Dot1x Auth Fail. 
            A value of 'true' (1) indicates that the notification action trap is 
            allowed to notify the user while the 802.1x authentication fail.
            A value of 'false'(2) indicates that the notification action trap is not 
            allowed to notify the user while the 802.1x authentication fail."
        ::= { sweConfigDot1xAuthFailAction 1 }

    sweConfigDot1xAuthFailEmailEnable OBJECT-TYPE
        SYNTAX TruthValue
        MAX-ACCESS read-write
        STATUS current
        DESCRIPTION
            "This enables or disables the notification action email in the event Dot1x Auth Fail. 
            A value of 'true' (1) indicates that the notification action email is 
            allowed to notify the user while the 802.1x authentication fail.
            A value of 'false'(2) indicates that the notification action email is not 
            allowed to notify the user while the 802.1x authentication fail."
        ::= { sweConfigDot1xAuthFailAction 2 }

    sweConfigDot1xAuthFailMgmtRelayEnable OBJECT-TYPE
        SYNTAX TruthValue
        MAX-ACCESS read-write
        STATUS current
        DESCRIPTION
            "This enables or disables the notification action MGMT relay in the event Dot1x Auth Fail. 
            A value of 'true' (1) indicates that the notification action MGMT relay is 
            allowed to notify the user while the 802.1x authentication fail.
            A value of 'false'(2) indicates that the notification action MGMT relay is not 
            allowed to notify the user while the 802.1x authentication fail."
        ::= { sweConfigDot1xAuthFailAction 3 }

    sweConfigDot1xAuthFailPwr1RelayEnable OBJECT-TYPE
        SYNTAX TruthValue
        MAX-ACCESS read-write
        STATUS current
        DESCRIPTION
            "This enables or disables the notification action PWR1 relay in the event Dot1x Auth Fail. 
            A value of 'true' (1) indicates that the notification action PWR1 relay is 
            allowed to notify the user while the 802.1x authentication fail.
            A value of 'false'(2) indicates that the notification action PWR1 relay is not 
            allowed to notify the user while the 802.1x authentication fail."
        ::= { sweConfigDot1xAuthFailAction 4 }

    sweConfigDot1xAuthFailPwr2RelayEnable OBJECT-TYPE
        SYNTAX TruthValue
        MAX-ACCESS read-write
        STATUS current
        DESCRIPTION
            "This enables or disables the notification action PWR2 relay in the event Dot1x Auth Fail. 
            A value of 'true' (1) indicates that the notification action PWR2 relay is 
            allowed to notify the user while the 802.1x authentication fail.
            A value of 'false'(2) indicates that the notification action PWR2 relay is not 
            allowed to notify the user while the 802.1x authentication fail."
        ::= { sweConfigDot1xAuthFailAction 5 }


-- LLDP Table Changed

    sweConfigLldpTableChanged OBJECT IDENTIFIER ::= { sweConfiguration 13 }

    sweConfigLldpTableChangedEnable OBJECT-TYPE
        SYNTAX TruthValue
        MAX-ACCESS read-write
        STATUS current
        DESCRIPTION
            "This enables or disables the event LLDP Table Changed in the event notification. 
            A value of 'true' (1) indicates that notifications are 
            allowed to notify the user while the LLDP remote table changed.
            A value of 'false'(2) indicates that notifications are not 
            allowed to notify the user while the LLDP remote table changed."
        ::= { sweConfigLldpTableChanged 1 }

    sweConfigLldpTableChangedAction OBJECT IDENTIFIER ::= { sweConfigLldpTableChanged 2 }

    sweConfigLldpTableChangedTrapEnable OBJECT-TYPE
        SYNTAX TruthValue
        MAX-ACCESS read-write
        STATUS current
        DESCRIPTION
            "This enables or disables the notification action trap in the event LLDP Table Changed. 
            A value of 'true' (1) indicates that the notification action trap is 
            allowed to notify the user while the LLDP remote table changed.
            A value of 'false'(2) indicates that the notification action trap is not 
            allowed to notify the user while the LLDP remote table changed."
        ::= { sweConfigLldpTableChangedAction 1 }

    sweConfigLldpTableChangedEmailEnable OBJECT-TYPE
        SYNTAX TruthValue
        MAX-ACCESS read-write
        STATUS current
        DESCRIPTION
            "This enables or disables the notification action email in the event LLDP Table Changed. 
            A value of 'true' (1) indicates that the notification action email is 
            allowed to notify the user while the LLDP remote table changed.
            A value of 'false'(2) indicates that the notification action email is not 
            allowed to notify the user while the LLDP remote table changed."
        ::= { sweConfigLldpTableChangedAction 2 }

    sweConfigLldpTableChangedMgmtRelayEnable OBJECT-TYPE
        SYNTAX TruthValue
        MAX-ACCESS read-write
        STATUS current
        DESCRIPTION
            "This enables or disables the notification action MGMT relay in the event LLDP Table Changed. 
            A value of 'true' (1) indicates that the notification action MGMT relay is 
            allowed to notify the user while the LLDP remote table changed.
            A value of 'false'(2) indicates that the notification action MGMT relay is not 
            allowed to notify the user while the LLDP remote table changed."
        ::= { sweConfigLldpTableChangedAction 3 }

    sweConfigLldpTableChangedPwr1RelayEnable OBJECT-TYPE
        SYNTAX TruthValue
        MAX-ACCESS read-write
        STATUS current
        DESCRIPTION
            "This enables or disables the notification action PWR1 relay in the event LLDP Table Changed. 
            A value of 'true' (1) indicates that the notification action PWR1 relay is 
            allowed to notify the user while the LLDP remote table changed.
            A value of 'false'(2) indicates that the notification action PWR1 relay is not 
            allowed to notify the user while the LLDP remote table changed."
        ::= { sweConfigLldpTableChangedAction 4 }

    sweConfigLldpTableChangedPwr2RelayEnable OBJECT-TYPE
        SYNTAX TruthValue
        MAX-ACCESS read-write
        STATUS current
        DESCRIPTION
            "This enables or disables the notification action PWR2 relay in the event LLDP Table Changed. 
            A value of 'true' (1) indicates that the notification action PWR2 relay is 
            allowed to notify the user while the LLDP remote table changed.
            A value of 'false'(2) indicates that the notification action PWR2 relay is not 
            allowed to notify the user while the LLDP remote table changed."
        ::= { sweConfigLldpTableChangedAction 5 }

    sweConfigLldpTableChangedRelayEnable OBJECT-TYPE
        SYNTAX TruthValue
        MAX-ACCESS read-write
        STATUS current
        DESCRIPTION
            "This enables or disables the notification action relay in the event LLDP Table Changed. 
            A value of 'true' (1) indicates that the notification action relay is allowed to notify the user while the LLDP remote table changed.
            A value of 'false'(2) indicates that the notification action relay is not allowed to notify the user while the LLDP remote table changed."
        ::= { sweConfigLldpTableChangedAction 6 }

-- RMON Raising Alarm

    sweConfigRmonRaisingAlarm OBJECT IDENTIFIER ::= { sweConfiguration 14 }

    sweConfigRmonRaisingAlarmEnable OBJECT-TYPE
        SYNTAX TruthValue
        MAX-ACCESS read-write
        STATUS current
        DESCRIPTION
            "This enables or disables the event RMON Raising Alarm in the event notification. 
            A value of 'true' (1) indicates that notifications are 
            allowed to notify the user while the RMON monitered oid reach the raising threshold.
            A value of 'false'(2) indicates that notifications are not 
            allowed to notify the user while the RMON monitered oid reach the raising threshold."
        ::= { sweConfigRmonRaisingAlarm 1 }

    sweConfigRmonRaisingAlarmAction OBJECT IDENTIFIER ::= { sweConfigRmonRaisingAlarm 2 }

    sweConfigRmonRaisingAlarmTrapEnable OBJECT-TYPE
        SYNTAX TruthValue
        MAX-ACCESS read-write
        STATUS current
        DESCRIPTION
            "This enables or disables the notification action trap in the event RMON Raising Alarm. 
            A value of 'true' (1) indicates that the notification action trap is 
            allowed to notify the user while the RMON monitered oid reach the raising threshold.
            A value of 'false'(2) indicates that the notification action trap is not 
            allowed to notify the user while the RMON monitered oid reach the raising threshold."
        ::= { sweConfigRmonRaisingAlarmAction 1 }

    sweConfigRmonRaisingAlarmEmailEnable OBJECT-TYPE
        SYNTAX TruthValue
        MAX-ACCESS read-write
        STATUS current
        DESCRIPTION
            "This enables or disables the notification action email in the event RMON Raising Alarm. 
            A value of 'true' (1) indicates that the notification action email is 
            allowed to notify the user while the RMON monitered oid reach the raising threshold.
            A value of 'false'(2) indicates that the notification action email is not 
            allowed to notify the user while the RMON monitered oid reach the raising threshold."
        ::= { sweConfigRmonRaisingAlarmAction 2 }

    sweConfigRmonRaisingAlarmMgmtRelayEnable OBJECT-TYPE
        SYNTAX TruthValue
        MAX-ACCESS read-write
        STATUS current
        DESCRIPTION
            "This enables or disables the notification action MGMT relay in the event RMON Raising Alarm. 
            A value of 'true' (1) indicates that the notification action MGMT relay is 
            allowed to notify the user while the RMON monitered oid reach the raising threshold.
            A value of 'false'(2) indicates that the notification action MGMT relay is not 
            allowed to notify the user while the RMON monitered oid reach the raising threshold."
        ::= { sweConfigRmonRaisingAlarmAction 3 }

    sweConfigRmonRaisingAlarmPwr1RelayEnable OBJECT-TYPE
        SYNTAX TruthValue
        MAX-ACCESS read-write
        STATUS current
        DESCRIPTION
            "This enables or disables the notification action PWR1 relay in the event RMON Raising Alarm. 
            A value of 'true' (1) indicates that the notification action PWR1 relay is 
            allowed to notify the user while the RMON monitered oid reach the raising threshold.
            A value of 'false'(2) indicates that the notification action PWR1 relay is not 
            allowed to notify the user while the RMON monitered oid reach the raising threshold."
        ::= { sweConfigRmonRaisingAlarmAction 4 }

    sweConfigRmonRaisingAlarmPwr2RelayEnable OBJECT-TYPE
        SYNTAX TruthValue
        MAX-ACCESS read-write
        STATUS current
        DESCRIPTION
            "This enables or disables the notification action PWR2 relay in the event RMON Raising Alarm. 
            A value of 'true' (1) indicates that the notification action PWR2 relay is 
            allowed to notify the user while the RMON monitered oid reach the raising threshold.
            A value of 'false'(2) indicates that the notification action PWR2 relay is not 
            allowed to notify the user while the RMON monitered oid reach the raising threshold."
        ::= { sweConfigRmonRaisingAlarmAction 5 }

-- RMON Falling Alarm

    sweConfigRmonFallingAlarm OBJECT IDENTIFIER ::= { sweConfiguration 15 }

    sweConfigRmonFallingAlarmEnable OBJECT-TYPE
        SYNTAX TruthValue
        MAX-ACCESS read-write
        STATUS current
        DESCRIPTION
            "This enables or disables the event RMON Falling Alarm in the event notification. 
            A value of 'true' (1) indicates that notifications are 
            allowed to notify the user while the RMON monitered oid lower than the falling threshold.
            A value of 'false'(2) indicates that notifications are not 
            allowed to notify the user while the RMON monitered oid lower than the falling threshold."
        ::= { sweConfigRmonFallingAlarm 1 }

    sweConfigRmonFallingAlarmAction OBJECT IDENTIFIER ::= { sweConfigRmonFallingAlarm 2 }

    sweConfigRmonFallingAlarmTrapEnable OBJECT-TYPE
        SYNTAX TruthValue
        MAX-ACCESS read-write
        STATUS current
        DESCRIPTION
            "This enables or disables the notification action trap in the event RMON Falling Alarm. 
            A value of 'true' (1) indicates that the notification action trap is 
            allowed to notify the user while the RMON monitered oid lower than the falling threshold.
            A value of 'false'(2) indicates that the notification action trap is not 
            allowed to notify the user while the RMON monitered oid lower than the falling threshold."
        ::= { sweConfigRmonFallingAlarmAction 1 }

    sweConfigRmonFallingAlarmEmailEnable OBJECT-TYPE
        SYNTAX TruthValue
        MAX-ACCESS read-write
        STATUS current
        DESCRIPTION
            "This enables or disables the notification action email in the event RMON Falling Alarm. 
            A value of 'true' (1) indicates that the notification action email is 
            allowed to notify the user while the RMON monitered oid lower than the falling threshold.
            A value of 'false'(2) indicates that the notification action email is not 
            allowed to notify the user while the RMON monitered oid lower than the falling threshold."
        ::= { sweConfigRmonFallingAlarmAction 2 }

    sweConfigRmonFallingAlarmMgmtRelayEnable OBJECT-TYPE
        SYNTAX TruthValue
        MAX-ACCESS read-write
        STATUS current
        DESCRIPTION
            "This enables or disables the notification action MGMT relay in the event RMON Falling Alarm. 
            A value of 'true' (1) indicates that the notification action MGMT relay is 
            allowed to notify the user while the RMON monitered oid lower than the falling threshold.
            A value of 'false'(2) indicates that the notification action MGMT relay is not 
            allowed to notify the user while the RMON monitered oid lower than the falling threshold."
        ::= { sweConfigRmonFallingAlarmAction 3 }

    sweConfigRmonFallingAlarmPwr1RelayEnable OBJECT-TYPE
        SYNTAX TruthValue
        MAX-ACCESS read-write
        STATUS current
        DESCRIPTION
            "This enables or disables the notification action PWR1 relay in the event RMON Falling Alarm. 
            A value of 'true' (1) indicates that the notification action PWR1 relay is 
            allowed to notify the user while the RMON monitered oid lower than the falling threshold.
            A value of 'false'(2) indicates that the notification action PWR1 relay is not 
            allowed to notify the user while the RMON monitered oid lower than the falling threshold."
        ::= { sweConfigRmonFallingAlarmAction 4 }

    sweConfigRmonFallingAlarmPwr2RelayEnable OBJECT-TYPE
        SYNTAX TruthValue
        MAX-ACCESS read-write
        STATUS current
        DESCRIPTION
            "This enables or disables the notification action PWR2 relay in the event RMON Falling Alarm. 
            A value of 'true' (1) indicates that the notification action PWR2 relay is 
            allowed to notify the user while the RMON monitered oid lower than the falling threshold.
            A value of 'false'(2) indicates that the notification action PWR2 relay is not 
            allowed to notify the user while the RMON monitered oid lower than the falling threshold."
        ::= { sweConfigRmonFallingAlarmAction 5 }

-- MSTP Topology Changed

    sweConfigMstpTopologyChanged OBJECT IDENTIFIER ::= { sweConfiguration 16 }

    sweConfigMstpTopologyChangedEnable OBJECT-TYPE
        SYNTAX TruthValue
        MAX-ACCESS read-write
        STATUS current
        DESCRIPTION
            "This enables or disables the event MSTP Topology Changed in the event notification. 
            A value of 'true' (1) indicates that notifications are 
            allowed to notify the user while the MSTP topology changed.
            A value of 'false'(2) indicates that notifications are not 
            allowed to notify the user while the MSTP topology changed."
        ::= { sweConfigMstpTopologyChanged 1 }

    sweConfigMstpTopologyChangedAction OBJECT IDENTIFIER ::= { sweConfigMstpTopologyChanged 2 }

    sweConfigMstpTopologyChangedTrapEnable OBJECT-TYPE
        SYNTAX TruthValue
        MAX-ACCESS read-write
        STATUS current
        DESCRIPTION
            "This enables or disables the notification action trap in the event MSTP Topology Changed. 
            A value of 'true' (1) indicates that the notification action trap is 
            allowed to notify the user while the MSTP topology changed.
            A value of 'false'(2) indicates that the notification action trap is not 
            allowed to notify the user while the MSTP topology changed."
        ::= { sweConfigMstpTopologyChangedAction 1 }

    sweConfigMstpTopologyChangedEmailEnable OBJECT-TYPE
        SYNTAX TruthValue
        MAX-ACCESS read-write
        STATUS current
        DESCRIPTION
            "This enables or disables the notification action email in the event MSTP Topology Changed. 
            A value of 'true' (1) indicates that the notification action email is 
            allowed to notify the user while the MSTP topology changed.
            A value of 'false'(2) indicates that the notification action email is not 
            allowed to notify the user while the MSTP topology changed."
        ::= { sweConfigMstpTopologyChangedAction 2 }

    sweConfigMstpTopologyChangedMgmtRelayEnable OBJECT-TYPE
        SYNTAX TruthValue
        MAX-ACCESS read-write
        STATUS current
        DESCRIPTION
            "This enables or disables the notification action MGMT relay in the event MSTP Topology Changed. 
            A value of 'true' (1) indicates that the notification action MGMT relay is 
            allowed to notify the user while the MSTP topology changed.
            A value of 'false'(2) indicates that the notification action MGMT relay is not 
            allowed to notify the user while the MSTP topology changed."
        ::= { sweConfigMstpTopologyChangedAction 3 }

    sweConfigMstpTopologyChangedPwr1RelayEnable OBJECT-TYPE
        SYNTAX TruthValue
        MAX-ACCESS read-write
        STATUS current
        DESCRIPTION
            "This enables or disables the notification action PWR1 relay in the event MSTP Topology Changed. 
            A value of 'true' (1) indicates that the notification action PWR1 relay is 
            allowed to notify the user while the MSTP topology changed.
            A value of 'false'(2) indicates that the notification action PWR1 relay is not 
            allowed to notify the user while the MSTP topology changed."
        ::= { sweConfigMstpTopologyChangedAction 4 }

    sweConfigMstpTopologyChangedPwr2RelayEnable OBJECT-TYPE
        SYNTAX TruthValue
        MAX-ACCESS read-write
        STATUS current
        DESCRIPTION
            "This enables or disables the notification action PWR2 relay in the event MSTP Topology Changed. 
            A value of 'true' (1) indicates that the notification action PWR2 relay is 
            allowed to notify the user while the MSTP topology changed.
            A value of 'false'(2) indicates that the notification action PWR2 relay is not 
            allowed to notify the user while the MSTP topology changed."
        ::= { sweConfigMstpTopologyChangedAction 5 }

-- MSTP Root Changed

    sweConfigMstpRootChanged OBJECT IDENTIFIER ::= { sweConfiguration 17 }

    sweConfigMstpRootChangedEnable OBJECT-TYPE
        SYNTAX TruthValue
        MAX-ACCESS read-write
        STATUS current
        DESCRIPTION
            "This enables or disables the event MSTP Root Changed in the event notification. 
            A value of 'true' (1) indicates that notifications are 
            allowed to notify the user while the MSTP root changed.
            A value of 'false'(2) indicates that notifications are not 
            allowed to notify the user while the MSTP root changed."
        ::= { sweConfigMstpRootChanged 1 }

    sweConfigMstpRootChangedAction OBJECT IDENTIFIER ::= { sweConfigMstpRootChanged 2 }

    sweConfigMstpRootChangedTrapEnable OBJECT-TYPE
        SYNTAX TruthValue
        MAX-ACCESS read-write
        STATUS current
        DESCRIPTION
            "This enables or disables the notification action trap in the event MSTP Root Changed. 
            A value of 'true' (1) indicates that the notification action trap is 
            allowed to notify the user while the MSTP root changed.
            A value of 'false'(2) indicates that the notification action trap is not 
            allowed to notify the user while the MSTP root changed."
        ::= { sweConfigMstpRootChangedAction 1 }

    sweConfigMstpRootChangedEmailEnable OBJECT-TYPE
        SYNTAX TruthValue
        MAX-ACCESS read-write
        STATUS current
        DESCRIPTION
            "This enables or disables the notification action email in the event MSTP Root Changed. 
            A value of 'true' (1) indicates that the notification action email is 
            allowed to notify the user while the MSTP root changed.
            A value of 'false'(2) indicates that the notification action email is not 
            allowed to notify the user while the MSTP root changed."
        ::= { sweConfigMstpRootChangedAction 2 }

    sweConfigMstpRootChangedMgmtRelayEnable OBJECT-TYPE
        SYNTAX TruthValue
        MAX-ACCESS read-write
        STATUS current
        DESCRIPTION
            "This enables or disables the notification action MGMT relay in the event MSTP Root Changed. 
            A value of 'true' (1) indicates that the notification action MGMT relay is 
            allowed to notify the user while the MSTP root changed.
            A value of 'false'(2) indicates that the notification action MGMT relay is not 
            allowed to notify the user while the MSTP root changed."
        ::= { sweConfigMstpRootChangedAction 3 }

    sweConfigMstpRootChangedPwr1RelayEnable OBJECT-TYPE
        SYNTAX TruthValue
        MAX-ACCESS read-write
        STATUS current
        DESCRIPTION
            "This enables or disables the notification action PWR1 relay in the event MSTP Root Changed. 
            A value of 'true' (1) indicates that the notification action PWR1 relay is 
            allowed to notify the user while the MSTP root changed.
            A value of 'false'(2) indicates that the notification action PWR1 relay is not 
            allowed to notify the user while the MSTP root changed."
        ::= { sweConfigMstpRootChangedAction 4 }

    sweConfigMstpRootChangedPwr2RelayEnable OBJECT-TYPE
        SYNTAX TruthValue
        MAX-ACCESS read-write
        STATUS current
        DESCRIPTION
            "This enables or disables the notification action PWR2 relay in the event MSTP Root Changed. 
            A value of 'true' (1) indicates that the notification action PWR2 relay is 
            allowed to notify the user while the MSTP root changed.
            A value of 'false'(2) indicates that the notification action PWR2 relay is not 
            allowed to notify the user while the MSTP root changed."
        ::= { sweConfigMstpRootChangedAction 5 }

-- MSTP New Port Role

    sweConfigMstpNewPortRole OBJECT IDENTIFIER ::= { sweConfiguration 18 }

    sweConfigMstpNewPortRoleEnable OBJECT-TYPE
        SYNTAX TruthValue
        MAX-ACCESS read-write
        STATUS current
        DESCRIPTION
            "This enables or disables the event MSTP New Port Role in the event notification. 
            A value of 'true' (1) indicates that notifications are 
            allowed to notify the user while the port role changed.
            A value of 'false'(2) indicates that notifications are not 
            allowed to notify the user while the port role changed."
        ::= { sweConfigMstpNewPortRole 1 }

    sweConfigMstpNewPortRoleAction OBJECT IDENTIFIER ::= { sweConfigMstpNewPortRole 2 }

    sweConfigMstpNewPortRoleTrapEnable OBJECT-TYPE
        SYNTAX TruthValue
        MAX-ACCESS read-write
        STATUS current
        DESCRIPTION
            "This enables or disables the notification action trap in the event MSTP New Port Role. 
            A value of 'true' (1) indicates that the notification action trap is 
            allowed to notify the user while the port role changed.
            A value of 'false'(2) indicates that the notification action trap is not 
            allowed to notify the user while the port role changed."
        ::= { sweConfigMstpNewPortRoleAction 1 }

    sweConfigMstpNewPortRoleEmailEnable OBJECT-TYPE
        SYNTAX TruthValue
        MAX-ACCESS read-write
        STATUS current
        DESCRIPTION
            "This enables or disables the notification action email in the event MSTP New Port Role. 
            A value of 'true' (1) indicates that the notification action email is 
            allowed to notify the user while the port role changed.
            A value of 'false'(2) indicates that the notification action email is not 
            allowed to notify the user while the port role changed."
        ::= { sweConfigMstpNewPortRoleAction 2 }

    sweConfigMstpNewPortRoleMgmtRelayEnable OBJECT-TYPE
        SYNTAX TruthValue
        MAX-ACCESS read-write
        STATUS current
        DESCRIPTION
            "This enables or disables the notification action MGMT relay in the event MSTP New Port Role. 
            A value of 'true' (1) indicates that the notification action MGMT relay is 
            allowed to notify the user while the port role changed.
            A value of 'false'(2) indicates that the notification action MGMT relay is not 
            allowed to notify the user while the port role changed."
        ::= { sweConfigMstpNewPortRoleAction 3 }

    sweConfigMstpNewPortRolePwr1RelayEnable OBJECT-TYPE
        SYNTAX TruthValue
        MAX-ACCESS read-write
        STATUS current
        DESCRIPTION
            "This enables or disables the notification action PWR1 relay in the event MSTP New Port Role. 
            A value of 'true' (1) indicates that the notification action PWR1 relay is 
            allowed to notify the user while the port role changed.
            A value of 'false'(2) indicates that the notification action PWR1 relay is not 
            allowed to notify the user while the port role changed."
        ::= { sweConfigMstpNewPortRoleAction 4 }

    sweConfigMstpNewPortRolePwr2RelayEnable OBJECT-TYPE
        SYNTAX TruthValue
        MAX-ACCESS read-write
        STATUS current
        DESCRIPTION
            "This enables or disables the notification action PWR2 relay in the event MSTP New Port Role. 
            A value of 'true' (1) indicates that the notification action PWR2 relay is 
            allowed to notify the user while the port role changed.
            A value of 'false'(2) indicates that the notification action PWR2 relay is not 
            allowed to notify the user while the port role changed."
        ::= { sweConfigMstpNewPortRoleAction 5 }

-- DHCPSNP untrust mac discard

    sweConfigDhcpsnpMacDiscard OBJECT IDENTIFIER ::= { sweConfiguration 19 }

    sweConfigDhcpsnpMacDiscardEnable OBJECT-TYPE
        SYNTAX TruthValue
        MAX-ACCESS read-write
        STATUS current
        DESCRIPTION
            "This enables or disables the event DHCPSNP untrust mac discard in the event notification.
            A value of 'true' (1) indicates that notifications are
            allowed to notify the user while the port role changed.
            A value of 'false'(2) indicates that notifications are not
            allowed to notify the user while the port role changed."
        ::= { sweConfigDhcpsnpMacDiscard 1 }

    sweConfigDhcpsnpMacDiscardAction OBJECT IDENTIFIER ::= { sweConfigDhcpsnpMacDiscard 2 }

    sweConfigDhcpsnpMacDiscardTrapEnable OBJECT-TYPE
        SYNTAX TruthValue
        MAX-ACCESS read-write
        STATUS current
        DESCRIPTION
            "This enables or disables the notification action trap in the event DHCPSNP untrust mac discard.
            A value of 'true' (1) indicates that the notification action trap is
            allowed to notify the user while the port role changed.
            A value of 'false'(2) indicates that the notification action trap is not
            allowed to notify the user while the port role changed."
        ::= { sweConfigDhcpsnpMacDiscardAction 1 }

    sweConfigDhcpsnpMacDiscardEmailEnable OBJECT-TYPE
        SYNTAX TruthValue
        MAX-ACCESS read-write
        STATUS current
        DESCRIPTION
            "This enables or disables the notification action email in the event DHCPSNP untrust mac discard.
            A value of 'true' (1) indicates that the notification action email is
            allowed to notify the user while the port role changed.
            A value of 'false'(2) indicates that the notification action email is not
            allowed to notify the user while the port role changed."
        ::= { sweConfigDhcpsnpMacDiscardAction 2 }

    sweConfigDhcpsnpMacDiscardMgmtRelayEnable OBJECT-TYPE
        SYNTAX TruthValue
        MAX-ACCESS read-write
        STATUS current
        DESCRIPTION
            "This enables or disables the notification action MGMT relay in the event DHCPSNP untrust mac discard.
            A value of 'true' (1) indicates that the notification action MGMT relay is
            allowed to notify the user while the port role changed.
            A value of 'false'(2) indicates that the notification action MGMT relay is not
            allowed to notify the user while the port role changed."
        ::= { sweConfigDhcpsnpMacDiscardAction 3 }

    sweConfigDhcpsnpMacDiscardPwr1RelayEnable OBJECT-TYPE
        SYNTAX TruthValue
        MAX-ACCESS read-write
        STATUS current
        DESCRIPTION
            "This enables or disables the notification action PWR1 relay in the event DHCPSNP untrust mac discard.
            A value of 'true' (1) indicates that the notification action PWR1 relay is
            allowed to notify the user while the port role changed.
            A value of 'false'(2) indicates that the notification action PWR1 relay is not
            allowed to notify the user while the port role changed."
        ::= { sweConfigDhcpsnpMacDiscardAction 4 }

    sweConfigDhcpsnpMacDiscardPwr2RelayEnable OBJECT-TYPE
        SYNTAX TruthValue
        MAX-ACCESS read-write
        STATUS current
        DESCRIPTION
            "This enables or disables the notification action PWR2 relay in the event DHCPSNP untrust mac discard.
            A value of 'true' (1) indicates that the notification action PWR2 relay is
            allowed to notify the user while the port role changed.
            A value of 'false'(2) indicates that the notification action PWR2 relay is not
            allowed to notify the user while the port role changed."
        ::= { sweConfigDhcpsnpMacDiscardAction 5 }

-- DHCPSNP untrust server discard

    sweConfigDhcpsnpServerDiscard OBJECT IDENTIFIER ::= { sweConfiguration 20 }

    sweConfigDhcpsnpServerDiscardEnable OBJECT-TYPE
        SYNTAX TruthValue
        MAX-ACCESS read-write
        STATUS current
        DESCRIPTION
            "This enables or disables the event DHCPSNP untrust server discard in the event notification.
            A value of 'true' (1) indicates that notifications are
            allowed to notify the user while the port role changed.
            A value of 'false'(2) indicates that notifications are not
            allowed to notify the user while the port role changed."
        ::= { sweConfigDhcpsnpServerDiscard 1 }

    sweConfigDhcpsnpServerDiscardAction OBJECT IDENTIFIER ::= { sweConfigDhcpsnpServerDiscard 2 }

    sweConfigDhcpsnpServerDiscardTrapEnable OBJECT-TYPE
        SYNTAX TruthValue
        MAX-ACCESS read-write
        STATUS current
        DESCRIPTION
            "This enables or disables the notification action trap in the event DHCPSNP untrust server discard.
            A value of 'true' (1) indicates that the notification action trap is
            allowed to notify the user while the port role changed.
            A value of 'false'(2) indicates that the notification action trap is not
            allowed to notify the user while the port role changed."
        ::= { sweConfigDhcpsnpServerDiscardAction 1 }

    sweConfigDhcpsnpServerDiscardEmailEnable OBJECT-TYPE
        SYNTAX TruthValue
        MAX-ACCESS read-write
        STATUS current
        DESCRIPTION
            "This enables or disables the notification action email in the event DHCPSNP untrust server discard.
            A value of 'true' (1) indicates that the notification action email is
            allowed to notify the user while the port role changed.
            A value of 'false'(2) indicates that the notification action email is not
            allowed to notify the user while the port role changed."
        ::= { sweConfigDhcpsnpServerDiscardAction 2 }

    sweConfigDhcpsnpServerDiscardMgmtRelayEnable OBJECT-TYPE
        SYNTAX TruthValue
        MAX-ACCESS read-write
        STATUS current
        DESCRIPTION
            "This enables or disables the notification action MGMT relay in the event DHCPSNP untrust server discard.
            A value of 'true' (1) indicates that the notification action MGMT relay is
            allowed to notify the user while the port role changed.
            A value of 'false'(2) indicates that the notification action MGMT relay is not
            allowed to notify the user while the port role changed."
        ::= { sweConfigDhcpsnpServerDiscardAction 3 }

    sweConfigDhcpsnpServerDiscardPwr1RelayEnable OBJECT-TYPE
        SYNTAX TruthValue
        MAX-ACCESS read-write
        STATUS current
        DESCRIPTION
            "This enables or disables the notification action PWR1 relay in the event DHCPSNP untrust server discard.
            A value of 'true' (1) indicates that the notification action PWR1 relay is
            allowed to notify the user while the port role changed.
            A value of 'false'(2) indicates that the notification action PWR1 relay is not
            allowed to notify the user while the port role changed."
        ::= { sweConfigDhcpsnpServerDiscardAction 4 }

    sweConfigDhcpsnpServerDiscardPwr2RelayEnable OBJECT-TYPE
        SYNTAX TruthValue
        MAX-ACCESS read-write
        STATUS current
        DESCRIPTION
            "This enables or disables the notification action PWR2 relay in the event DHCPSNP untrust server discard.
            A value of 'true' (1) indicates that the notification action PWR2 relay is
            allowed to notify the user while the port role changed.
            A value of 'false'(2) indicates that the notification action PWR2 relay is not
            allowed to notify the user while the port role changed."
        ::= { sweConfigDhcpsnpServerDiscardAction 5 }

-- MACsec MKA Fail

    sweConfigMACsecInterfaceMKAFail OBJECT IDENTIFIER ::= { sweConfiguration 21 }

    sweConfigMACsecInterfaceMKAFailEnable OBJECT-TYPE
        SYNTAX TruthValue
        MAX-ACCESS read-write
        STATUS current
        DESCRIPTION
            "This enables or disables the event MACsec mka peer expired in the event notification.
            A value of 'true' (1) indicates that notifications are
            allowed to notify the user while the port role changed.
            A value of 'false'(2) indicates that notifications are not
            allowed to notify the user while the port role changed."
        ::= { sweConfigMACsecInterfaceMKAFail 1 }

    sweConfigMACsecInterfaceMKAFailAction OBJECT IDENTIFIER ::= { sweConfigMACsecInterfaceMKAFail 2 }

    sweConfigMACsecInterfaceMKAFailTrapEnable OBJECT-TYPE
        SYNTAX TruthValue
        MAX-ACCESS read-write
        STATUS current
        DESCRIPTION
            "This enables or disables the notification action trap in the event MACsec mka peer expired.
            A value of 'true' (1) indicates that the notification action trap is
            allowed to notify the user while the port role changed.
            A value of 'false'(2) indicates that the notification action trap is not
            allowed to notify the user while the port role changed."
        ::= { sweConfigMACsecInterfaceMKAFailAction 1 }

    sweConfigMACsecInterfaceMKAFailEmailEnable OBJECT-TYPE
        SYNTAX TruthValue
        MAX-ACCESS read-write
        STATUS current
        DESCRIPTION
            "This enables or disables the notification action email in the event MACsec mka peer expired.
            A value of 'true' (1) indicates that the notification action email is
            allowed to notify the user while the port role changed.
            A value of 'false'(2) indicates that the notification action email is not
            allowed to notify the user while the port role changed."
        ::= { sweConfigMACsecInterfaceMKAFailAction 2 }

    sweConfigMACsecInterfaceMKAFailMgmtRelayEnable OBJECT-TYPE
        SYNTAX TruthValue
        MAX-ACCESS read-write
        STATUS current
        DESCRIPTION
            "This enables or disables the notification action MGMT relay in the event MACsec mka peer expired.
            A value of 'true' (1) indicates that the notification action MGMT relay is
            allowed to notify the user while the port role changed.
            A value of 'false'(2) indicates that the notification action MGMT relay is not
            allowed to notify the user while the port role changed."
        ::= { sweConfigMACsecInterfaceMKAFailAction 3 }

    sweConfigMACsecInterfaceMKAFailPwr1RelayEnable OBJECT-TYPE
        SYNTAX TruthValue
        MAX-ACCESS read-write
        STATUS current
        DESCRIPTION
            "This enables or disables the notification action PWR1 relay in the event MACsec mka peer expired.
            A value of 'true' (1) indicates that the notification action PWR1 relay is
            allowed to notify the user while the port role changed.
            A value of 'false'(2) indicates that the notification action PWR1 relay is not
            allowed to notify the user while the port role changed."
        ::= { sweConfigMACsecInterfaceMKAFailAction 4 }

    sweConfigMACsecInterfaceMKAFailPwr2RelayEnable OBJECT-TYPE
        SYNTAX TruthValue
        MAX-ACCESS read-write
        STATUS current
        DESCRIPTION
            "This enables or disables the notification action PWR2 relay in the event MACsec mka peer expired.
            A value of 'true' (1) indicates that the notification action PWR2 relay is
            allowed to notify the user while the port role changed.
            A value of 'false'(2) indicates that the notification action PWR2 relay is not
            allowed to notify the user while the port role changed."
        ::= { sweConfigMACsecInterfaceMKAFailAction 5 }

-- -------------------------------------------------------------
-- Status group
-- -------------------------------------------------------------
    sweStatRedundantProtocol OBJECT-TYPE
        SYNTAX  INTEGER  {
                rstp (1),
                turboRingV2 (2),
                turboChain (3),
                dualHoming (4),
                mstp (5),
                mrp (6)
            }
    MAX-ACCESS    accessible-for-notify
    STATUS    current
    DESCRIPTION
            "This object is only to inform user which the redundant protocol occur Topology Changed."
    ::= { sweStatus 1 }


-- -------------------------------------------------------------
-- Notification group
-- -------------------------------------------------------------
-- Topology Changed
    sweNotifyTopologyChanged NOTIFICATION-TYPE
        OBJECTS {
            sweStatRedundantProtocol
        }
        STATUS      current
        DESCRIPTION
            "The sweNotifyTopologyChanged notification is sent when the topology changed occurs."
        ::= { sweNotification 1 }

END
