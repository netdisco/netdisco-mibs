-- *****************************************************************
-- Moxa General (Device Diagnostics) - Event Log PRIVATE MIB
--
-- Copyright (c) 2019 by Moxa Inc.
-- All rights reserved.
-- *****************************************************************

MOXA-EVENT-LOG-MIB DEFINITIONS ::= BEGIN
    IMPORTS
        MODULE-IDENTITY, NOTIFICATION-TYPE, OBJECT-TYPE, IpAddress, Integer32, Counter32,
        enterprises
            FROM SNMPv2-SMI
        TEXTUAL-CONVENTION, DisplayString, TruthValue
            FROM SNMPv2-TC;

    mxEventLog MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa Event Log"

        REVISION    "202202170000Z"
        DESCRIPTION "update CONTACT-INFO"

        REVISION    "201906300000Z"
        DESCRIPTION "Initial Revision"

        ::= { deviceDiagnostics 3 }

    moxa                 OBJECT IDENTIFIER ::= { enterprises 8691 }
    general              OBJECT IDENTIFIER ::= { moxa 602 }
    deviceDiagnostics    OBJECT IDENTIFIER ::= { general 8 }

-- -------------------------------------------------------------
-- groups in the MOXA-EVENT-LOG-MIB MIB
-- -------------------------------------------------------------

    eventlogNotification  OBJECT IDENTIFIER ::= { mxEventLog 0 }
    eventlogConfiguration OBJECT IDENTIFIER ::= { mxEventLog 1 }
    eventlogStatus        OBJECT IDENTIFIER ::= { mxEventLog 2 }
    -- eventlogExtensions  OBJECT IDENTIFIER ::= { mxEventLog 3 }
-- -------------------------------------------------------------
-- configuration group
-- -------------------------------------------------------------

    eventlogManagement OBJECT IDENTIFIER ::= { eventlogConfiguration 1 }

    logCapacityThresholdEnable OBJECT-TYPE
        SYNTAX     TruthValue
        MAX-ACCESS read-write
        STATUS     current
        DESCRIPTION
             "Configure event log capacity enable."
        ::= { eventlogManagement 1 }

    logCapacityThreshold OBJECT-TYPE
        SYNTAX INTEGER (0..100)
        MAX-ACCESS read-write
        STATUS current
        DESCRIPTION
            "Configure event log capacity warning threshold by percentage."
        ::= { eventlogManagement 2 }

    logOversizeAction OBJECT-TYPE
        SYNTAX INTEGER { overwrite(1), stoprecord(2) }
        MAX-ACCESS read-write
        STATUS current
        DESCRIPTION
            "Set event log over-size action."
        ::= { eventlogManagement 3 }

    eventlogClear OBJECT-TYPE
        SYNTAX    TruthValue
        MAX-ACCESS read-write
        STATUS current
        DESCRIPTION
            "Writing true(1) to this object forces the system to
             clear the eventlog. Any other operation on this object
             has no effect and it always returns false(2) when read."
        ::= { eventlogConfiguration 2 }

-- -------------------------------------------------------------
-- status group
-- -------------------------------------------------------------

    logStatCurrentNumOfLogEntries OBJECT-TYPE
        SYNTAX Counter32
        MAX-ACCESS read-only
        STATUS current
        DESCRIPTION
            "This indicates the current number of log entries in the system storage."
        ::= { eventlogStatus 1 }

-- -------------------------------------------------------------
-- notification group
-- -------------------------------------------------------------

    logNotifyCapacityThreshold NOTIFICATION-TYPE
        OBJECTS {
            logStatCurrentNumOfLogEntries
        }
        STATUS      current
        DESCRIPTION
            "The logNotifyCapacityThreshold notification is sent when the number of log entries
            reach the logCapacityThreshold."
        ::= { eventlogNotification 1 }

END
