-- ****************************************************************
-- *  Moxa General (Events) - Port Event (PORTE) PRIVATE MIB
-- *
-- *  Copyright (c) 2019 by Moxa Inc.
-- *  All rights reserved.
-- *****************************************************************

MOXA-PORT-EVENT-MIB DEFINITIONS ::= BEGIN
    IMPORTS
        MODULE-IDENTITY, NOTIFICATION-TYPE, OBJECT-TYPE, IpAddress, Integer32,
        enterprises
            FROM SNMPv2-SMI
        TEXTUAL-CONVENTION, DateAndTime, MacAddress, DisplayString, TruthValue, RowStatus
            FROM SNMPv2-TC
        eventNotification
            FROM MOXA-GENERAL-MIB;

    mxPortEvent MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa Event Notification Port Event"

        REVISION    "202202170000Z"
        DESCRIPTION "update CONTACT-INFO"

        REVISION    "202201110000Z"
        DESCRIPTION "Support fiber check event"

        REVISION    "202109290000Z"
        DESCRIPTION
            "Add OIDs:
                 porteConfigPortLinkUpRelayEnable
                 porteConfigPortLinkDownRelayEnable"

        REVISION    "201906300000Z"
        DESCRIPTION "Initial Revision"

        ::= { mxEvents 2 }

    moxa                 OBJECT IDENTIFIER ::= { enterprises 8691 }
    general              OBJECT IDENTIFIER ::= { moxa 602 }
    eventNotification    OBJECT IDENTIFIER ::= { general 7 }
    mxEvents             OBJECT IDENTIFIER ::= { eventNotification 1 }

-- -------------------------------------------------------------
-- groups in the MOXA-PORT-EVENT-MIB MIB 
-- -------------------------------------------------------------

  -- porteNotification      OBJECT IDENTIFIER ::= { mxPortEvent 0 }
  porteConfiguration     OBJECT IDENTIFIER ::= { mxPortEvent 1 }
  -- porteStatus            OBJECT IDENTIFIER ::= { mxPortEvent 2 }
  -- porteExtensions        OBJECT IDENTIFIER ::= { mxPortEvent 3 }

-- -------------------------------------------------------------
-- Notification group
-- -------------------------------------------------------------


-- -------------------------------------------------------------
-- configuration group
-- -------------------------------------------------------------


-- Port Link Up

    porteConfigPortLinkUp OBJECT IDENTIFIER ::= { porteConfiguration 1 }

    porteConfigPortLinkUpEnable OBJECT-TYPE
        SYNTAX TruthValue
        MAX-ACCESS read-write
        STATUS current
        DESCRIPTION
            "This enables or disables the event Port Link Up in the event notification. 
            A value of 'true' (1) indicates that notifications are 
            allowed to notify the user while the port link up.
            A value of 'false'(2) indicates that notifications are not 
            allowed to notify the user while the port link up."
        ::= { porteConfigPortLinkUp 1 }

    porteConfigPortLinkUpAction OBJECT IDENTIFIER ::= { porteConfigPortLinkUp 2 }

    porteConfigPortLinkUpTrapEnable OBJECT-TYPE
        SYNTAX TruthValue
        MAX-ACCESS read-write
        STATUS current
        DESCRIPTION
            "This enables or disables the notification action trap in the event Port Link Up. 
            A value of 'true' (1) indicates that the notification action trap is 
            allowed to notify the user while the port link up.
            A value of 'false'(2) indicates that the notification action trap is not 
            allowed to notify the user while the port link up."
        ::= { porteConfigPortLinkUpAction 1 }

    porteConfigPortLinkUpEmailEnable OBJECT-TYPE
        SYNTAX TruthValue
        MAX-ACCESS read-write
        STATUS current
        DESCRIPTION
            "This enables or disables the notification action email in the event Port Link Up. 
            A value of 'true' (1) indicates that the notification action email is 
            allowed to notify the user while the port link up.
            A value of 'false'(2) indicates that the notification action email is not 
            allowed to notify the user while the port link up."
        ::= { porteConfigPortLinkUpAction 2 }

    porteConfigPortLinkUpMgmtRelayEnable OBJECT-TYPE
        SYNTAX TruthValue
        MAX-ACCESS read-write
        STATUS current
        DESCRIPTION
            "This enables or disables the notification action MGMT relay in the event Port Link Up. 
            A value of 'true' (1) indicates that the notification action MGMT relay is 
            allowed to notify the user while the port link up.
            A value of 'false'(2) indicates that the notification action MGMT relay is not 
            allowed to notify the user while the port link up."
        ::= { porteConfigPortLinkUpAction 3 }

    porteConfigPortLinkUpPwr1RelayEnable OBJECT-TYPE
        SYNTAX TruthValue
        MAX-ACCESS read-write
        STATUS current
        DESCRIPTION
            "This enables or disables the notification action PWR1 relay in the event Port Link Up. 
            A value of 'true' (1) indicates that the notification action PWR1 relay is 
            allowed to notify the user while the port link up.
            A value of 'false'(2) indicates that the notification action PWR1 relay is not 
            allowed to notify the user while the port link up."
        ::= { porteConfigPortLinkUpAction 4 }

    porteConfigPortLinkUpPwr2RelayEnable OBJECT-TYPE
        SYNTAX TruthValue
        MAX-ACCESS read-write
        STATUS current
        DESCRIPTION
            "This enables or disables the notification action PWR2 relay in the event Port Link Up. 
            A value of 'true' (1) indicates that the notification action PWR2 relay is 
            allowed to notify the user while the port link up.
            A value of 'false'(2) indicates that the notification action PWR2 relay is not 
            allowed to notify the user while the port link up."
        ::= { porteConfigPortLinkUpAction 5 }

    porteConfigPortLinkUpRelayEnable OBJECT-TYPE
        SYNTAX TruthValue
        MAX-ACCESS read-write
        STATUS current
        DESCRIPTION
            "This enables or disables the notification action relay in the event Port Link Up. 
            A value of 'true' (1) indicates that the notification action relay is allowed to notify the user while the port link up.
            A value of 'false'(2) indicates that the notification action relay is not allowed to notify the user while the port link up."
        ::= { porteConfigPortLinkUpAction 6 }

    porteConfigPortLinkUpPortTable OBJECT-TYPE
        SYNTAX SEQUENCE OF PorteConfigPortLinkUpPortEntry
        MAX-ACCESS not-accessible
        STATUS current
        DESCRIPTION
            "A table to store the port specific parameters for event Port Link Up registered port. And the parameters can be manipulated 
            by administrators."
        ::= { porteConfigPortLinkUp 3 }
 
    porteConfigPortLinkUpPortEntry OBJECT-TYPE
        SYNTAX PorteConfigPortLinkUpPortEntry
        MAX-ACCESS not-accessible
        STATUS current
        DESCRIPTION
            "An entry appears in this Port Table represent port information about 
            Port Link Up event"
        INDEX { porteConfigPortLinkUpPortNum }
        ::= { porteConfigPortLinkUpPortTable 1 }

    PorteConfigPortLinkUpPortEntry ::=
        SEQUENCE {
            porteConfigPortLinkUpPortNum    Integer32,
            porteConfigPortLinkUpPortEnable TruthValue
    }

    porteConfigPortLinkUpPortNum OBJECT-TYPE
        SYNTAX Integer32 (1..256)
        MAX-ACCESS read-only
        STATUS current
        DESCRIPTION
            "A unique value, greater than zero, indicating the Port number of 
             port configuration table."
        ::= { porteConfigPortLinkUpPortEntry 1 }

    porteConfigPortLinkUpPortEnable OBJECT-TYPE
        SYNTAX TruthValue
        MAX-ACCESS read-write
        STATUS current
        DESCRIPTION
            "This parameter when true(1) indicates that a port is enabled 
            the event Port Link Up and false(2) indicates that this event is disabled 
            on the port."
        ::= { porteConfigPortLinkUpPortEntry 2 }

-- Port Link Down

    porteConfigPortLinkDown OBJECT IDENTIFIER ::= { porteConfiguration 2 }

    porteConfigPortLinkDownEnable OBJECT-TYPE
        SYNTAX TruthValue
        MAX-ACCESS read-write
        STATUS current
        DESCRIPTION
            "This enables or disables the event Port Link Down in the event notification. 
            A value of 'true' (1) indicates that notifications are 
            allowed to notify the user while the port link down.
            A value of 'false'(2) indicates that notifications are not 
            allowed to notify the user while the port link down."
        ::= { porteConfigPortLinkDown 1 }

    porteConfigPortLinkDownAction OBJECT IDENTIFIER ::= { porteConfigPortLinkDown 2 }

    porteConfigPortLinkDownTrapEnable OBJECT-TYPE
        SYNTAX TruthValue
        MAX-ACCESS read-write
        STATUS current
        DESCRIPTION
            "This enables or disables the notification action trap in the event Port Link Down. 
            A value of 'true' (1) indicates that the notification action trap is 
            allowed to notify the user while the port link down.
            A value of 'false'(2) indicates that the notification action trap is not 
            allowed to notify the user while the port link down."
        ::= { porteConfigPortLinkDownAction 1 }

    porteConfigPortLinkDownEmailEnable OBJECT-TYPE
        SYNTAX TruthValue
        MAX-ACCESS read-write
        STATUS current
        DESCRIPTION
            "This enables or disables the notification action email in the event Port Link Down. 
            A value of 'true' (1) indicates that the notification action email is 
            allowed to notify the user while the port link down.
            A value of 'false'(2) indicates that the notification action email is not 
            allowed to notify the user while the port link down."
        ::= { porteConfigPortLinkDownAction 2 }

    porteConfigPortLinkDownMgmtRelayEnable OBJECT-TYPE
        SYNTAX TruthValue
        MAX-ACCESS read-write
        STATUS current
        DESCRIPTION
            "This enables or disables the notification action MGMT relay in the event Port Link Down. 
            A value of 'true' (1) indicates that the notification action MGMT relay is 
            allowed to notify the user while the port link down.
            A value of 'false'(2) indicates that the notification action MGMT relay is not 
            allowed to notify the user while the port link down."
        ::= { porteConfigPortLinkDownAction 3 }

    porteConfigPortLinkDownPwr1RelayEnable OBJECT-TYPE
        SYNTAX TruthValue
        MAX-ACCESS read-write
        STATUS current
        DESCRIPTION
            "This enables or disables the notification action PWR1 relay in the event Port Link Down. 
            A value of 'true' (1) indicates that the notification action PWR1 relay is 
            allowed to notify the user while the port link down.
            A value of 'false'(2) indicates that the notification action PWR1 relay is not 
            allowed to notify the user while the port link down."
        ::= { porteConfigPortLinkDownAction 4 }

    porteConfigPortLinkDownPwr2RelayEnable OBJECT-TYPE
        SYNTAX TruthValue
        MAX-ACCESS read-write
        STATUS current
        DESCRIPTION
            "This enables or disables the notification action PWR2 relay in the event Port Link Down. 
            A value of 'true' (1) indicates that the notification action PWR2 relay is 
            allowed to notify the user while the port link down.
            A value of 'false'(2) indicates that the notification action PWR2 relay is not 
            allowed to notify the user while the port link down."
        ::= { porteConfigPortLinkDownAction 5 }

    porteConfigPortLinkDownRelayEnable OBJECT-TYPE
        SYNTAX TruthValue
        MAX-ACCESS read-write
        STATUS current
        DESCRIPTION
            "This enables or disables the notification action relay in the event Port Link Down. 
            A value of 'true' (1) indicates that the notification action relay is allowed to notify the user while the port link down.
            A value of 'false'(2) indicates that the notification action relay is not allowed to notify the user while the port link down."
        ::= { porteConfigPortLinkDownAction 6 }

    porteConfigPortLinkDownPortTable OBJECT-TYPE
        SYNTAX SEQUENCE OF PorteConfigPortLinkDownPortEntry
        MAX-ACCESS not-accessible
        STATUS current
        DESCRIPTION
            "A table to store the port specific parameters for event Port Link Down registered port. And the parameters can be manipulated 
            by administrators."
        ::= { porteConfigPortLinkDown 3 }
 
    porteConfigPortLinkDownPortEntry OBJECT-TYPE
        SYNTAX PorteConfigPortLinkDownPortEntry
        MAX-ACCESS not-accessible
        STATUS current
        DESCRIPTION
            "An entry appears in this Port Table represent port information about 
            Port Link Down event."
        INDEX { porteConfigPortLinkDownPortNum }
        ::= { porteConfigPortLinkDownPortTable 1 }

    PorteConfigPortLinkDownPortEntry ::=
        SEQUENCE {
            porteConfigPortLinkDownPortNum    Integer32,
            porteConfigPortLinkDownPortEnable TruthValue
    }

    porteConfigPortLinkDownPortNum OBJECT-TYPE
        SYNTAX Integer32 (1..256)
        MAX-ACCESS read-only
        STATUS current
        DESCRIPTION
            "A unique value, greater than zero, indicating the Port number of 
             port configuration table."
        ::= { porteConfigPortLinkDownPortEntry 1 }

    porteConfigPortLinkDownPortEnable OBJECT-TYPE
        SYNTAX TruthValue
        MAX-ACCESS read-write
        STATUS current
        DESCRIPTION
            "This parameter when true(1) indicates that a port is enabled 
            the event Port Link Down and false(2) indicates that this event is disabled 
            on the port."
        ::= { porteConfigPortLinkDownPortEntry 2 }

-- Port Shutdown By Rate Limit

    porteConfigPortShutdownByRateLimit OBJECT IDENTIFIER ::= { porteConfiguration 3 }

    porteConfigPortShutdownByRateLimitEnable OBJECT-TYPE
        SYNTAX TruthValue
        MAX-ACCESS read-write
        STATUS current
        DESCRIPTION
            "This enables or disables the event Port Shutdown By Rate Limit in the event notification. 
            A value of 'true' (1) indicates that notifications are 
            allowed to notify the user while the port shutdown by rate limit.
            A value of 'false'(2) indicates that notifications are not 
            allowed to notify the user while the port shutdown by rate limit."
        ::= { porteConfigPortShutdownByRateLimit 1 }

    porteConfigPortShutdownByRateLimitAction OBJECT IDENTIFIER ::= { porteConfigPortShutdownByRateLimit 2 }

    porteConfigPortShutdownByRateLimitTrapEnable OBJECT-TYPE
        SYNTAX TruthValue
        MAX-ACCESS read-write
        STATUS current
        DESCRIPTION
            "This enables or disables the notification action trap in the event Port Shutdown By Rate Limit. 
            A value of 'true' (1) indicates that the notification action trap is 
            allowed to notify the user while the port shutdown by rate limit.
            A value of 'false'(2) indicates that the notification action trap is not 
            allowed to notify the user while the port shutdown by rate limit."
        ::= { porteConfigPortShutdownByRateLimitAction 1 }

    porteConfigPortShutdownByRateLimitEmailEnable OBJECT-TYPE
        SYNTAX TruthValue
        MAX-ACCESS read-write
        STATUS current
        DESCRIPTION
            "This enables or disables the notification action email in the event Port Shutdown By Rate Limit. 
            A value of 'true' (1) indicates that the notification action email is 
            allowed to notify the user while the port shutdown by rate limit.
            A value of 'false'(2) indicates that the notification action email is not 
            allowed to notify the user while the port shutdown by rate limit."
        ::= { porteConfigPortShutdownByRateLimitAction 2 }

    porteConfigPortShutdownByRateLimitMgmtRelayEnable OBJECT-TYPE
        SYNTAX TruthValue
        MAX-ACCESS read-write
        STATUS current
        DESCRIPTION
            "This enables or disables the notification action MGMT relay in the event Port Shutdown By Rate Limit. 
            A value of 'true' (1) indicates that the notification action MGMT relay is 
            allowed to notify the user while the port shutdown by rate limit.
            A value of 'false'(2) indicates that the notification action MGMT relay is not 
            allowed to notify the user while the port shutdown by rate limit."
        ::= { porteConfigPortShutdownByRateLimitAction 3 }

    porteConfigPortShutdownByRateLimitPwr1RelayEnable OBJECT-TYPE
        SYNTAX TruthValue
        MAX-ACCESS read-write
        STATUS current
        DESCRIPTION
            "This enables or disables the notification action PWR1 relay in the event Port Shutdown By Rate Limit. 
            A value of 'true' (1) indicates that the notification action PWR1 relay is 
            allowed to notify the user while the port shutdown by rate limit.
            A value of 'false'(2) indicates that the notification action PWR1 relay is not 
            allowed to notify the user while the port shutdown by rate limit."
        ::= { porteConfigPortShutdownByRateLimitAction 4 }

    porteConfigPortShutdownByRateLimitPwr2RelayEnable OBJECT-TYPE
        SYNTAX TruthValue
        MAX-ACCESS read-write
        STATUS current
        DESCRIPTION
            "This enables or disables the notification action PWR2 relay in the event Port Shutdown By Rate Limit. 
            A value of 'true' (1) indicates that the notification action PWR2 relay is 
            allowed to notify the user while the port shutdown by rate limit.
            A value of 'false'(2) indicates that the notification action PWR2 relay is not 
            allowed to notify the user while the port shutdown by rate limit."
        ::= { porteConfigPortShutdownByRateLimitAction 5 }

    porteConfigPortShutdownByRateLimitPortTable OBJECT-TYPE
        SYNTAX SEQUENCE OF PorteConfigPortShutdownByRateLimitPortEntry
        MAX-ACCESS not-accessible
        STATUS current
        DESCRIPTION
            "A table to store the port specific parameters for event Port Shutdown By Rate Limit registered port. And the parameters can be manipulated 
            by administrators."
        ::= { porteConfigPortShutdownByRateLimit 3 }
 
    porteConfigPortShutdownByRateLimitPortEntry OBJECT-TYPE
        SYNTAX PorteConfigPortShutdownByRateLimitPortEntry
        MAX-ACCESS not-accessible
        STATUS current
        DESCRIPTION
            "An entry appears in this Port Table represent port information about 
            Port Shutdown By Rate Limit event."
        INDEX { porteConfigPortShutdownByRateLimitPortNum }
        ::= { porteConfigPortShutdownByRateLimitPortTable 1 }

    PorteConfigPortShutdownByRateLimitPortEntry ::=
        SEQUENCE {
            porteConfigPortShutdownByRateLimitPortNum
                Integer32,
            porteConfigPortShutdownByRateLimitPortEnable
                TruthValue
    }

    porteConfigPortShutdownByRateLimitPortNum OBJECT-TYPE
        SYNTAX Integer32 (1..256)
        MAX-ACCESS read-only
        STATUS current
        DESCRIPTION
            "A unique value, greater than zero, indicating the Port number of 
             port configuration table."
        ::= { porteConfigPortShutdownByRateLimitPortEntry 1 }

    porteConfigPortShutdownByRateLimitPortEnable OBJECT-TYPE
        SYNTAX TruthValue
        MAX-ACCESS read-write
        STATUS current
        DESCRIPTION
            "This parameter when true(1) indicates that a port is enabled 
            the event Port Shutdown By Rate Limit and false(2) indicates that this event is disabled 
            on the port."
        ::= { porteConfigPortShutdownByRateLimitPortEntry 2 }

-- Port Recovery By Rate Limit

    porteConfigPortRecoveryByRateLimit OBJECT IDENTIFIER ::= { porteConfiguration 4 }

    porteConfigPortRecoveryByRateLimitEnable OBJECT-TYPE
        SYNTAX TruthValue
        MAX-ACCESS read-write
        STATUS current
        DESCRIPTION
            "This enables or disables the event Port Recovery By Rate Limit in the event notification. 
            A value of 'true' (1) indicates that notifications are 
            allowed to notify the user while the port recovery by rate limit.
            A value of 'false'(2) indicates that notifications are not 
            allowed to notify the user while the port recovery by rate limit."
        ::= { porteConfigPortRecoveryByRateLimit 1 }

    porteConfigPortRecoveryByRateLimitAction OBJECT IDENTIFIER ::= { porteConfigPortRecoveryByRateLimit 2 }

    porteConfigPortRecoveryByRateLimitTrapEnable OBJECT-TYPE
        SYNTAX TruthValue
        MAX-ACCESS read-write
        STATUS current
        DESCRIPTION
            "This enables or disables the notification action trap in the event Port Recovery By Rate Limit. 
            A value of 'true' (1) indicates that the notification action trap is 
            allowed to notify the user while the port recovery by rate limit.
            A value of 'false'(2) indicates that the notification action trap is not 
            allowed to notify the user while the port recovery by rate limit."
        ::= { porteConfigPortRecoveryByRateLimitAction 1 }

    porteConfigPortRecoveryByRateLimitEmailEnable OBJECT-TYPE
        SYNTAX TruthValue
        MAX-ACCESS read-write
        STATUS current
        DESCRIPTION
            "This enables or disables the notification action email in the event Port Recovery By Rate Limit. 
            A value of 'true' (1) indicates that the notification action email is 
            allowed to notify the user while the port recovery by rate limit.
            A value of 'false'(2) indicates that the notification action email is not 
            allowed to notify the user while the port recovery by rate limit."
        ::= { porteConfigPortRecoveryByRateLimitAction 2 }

    porteConfigPortRecoveryByRateLimitMgmtRelayEnable OBJECT-TYPE
        SYNTAX TruthValue
        MAX-ACCESS read-write
        STATUS current
        DESCRIPTION
            "This enables or disables the notification action MGMT relay in the event Port Recovery By Rate Limit. 
            A value of 'true' (1) indicates that the notification action MGMT relay is 
            allowed to notify the user while the port recovery by rate limit.
            A value of 'false'(2) indicates that the notification action MGMT relay is not 
            allowed to notify the user while the port recovery by rate limit."
        ::= { porteConfigPortRecoveryByRateLimitAction 3 }

    porteConfigPortRecoveryByRateLimitPwr1RelayEnable OBJECT-TYPE
        SYNTAX TruthValue
        MAX-ACCESS read-write
        STATUS current
        DESCRIPTION
            "This enables or disables the notification action PWR1 relay in the event Port Recovery By Rate Limit. 
            A value of 'true' (1) indicates that the notification action PWR1 relay is 
            allowed to notify the user while the port recovery by rate limit.
            A value of 'false'(2) indicates that the notification action PWR1 relay is not 
            allowed to notify the user while the port recovery by rate limit."
        ::= { porteConfigPortRecoveryByRateLimitAction 4 }

    porteConfigPortRecoveryByRateLimitPwr2RelayEnable OBJECT-TYPE
        SYNTAX TruthValue
        MAX-ACCESS read-write
        STATUS current
        DESCRIPTION
            "This enables or disables the notification action PWR2 relay in the event Port Recovery By Rate Limit. 
            A value of 'true' (1) indicates that the notification action PWR2 relay is 
            allowed to notify the user while the port recovery by rate limit.
            A value of 'false'(2) indicates that the notification action PWR2 relay is not 
            allowed to notify the user while the port recovery by rate limit."
        ::= { porteConfigPortRecoveryByRateLimitAction 5 }

    porteConfigPortRecoveryByRateLimitPortTable OBJECT-TYPE
        SYNTAX SEQUENCE OF PorteConfigPortRecoveryByRateLimitPortEntry
        MAX-ACCESS not-accessible
        STATUS current
        DESCRIPTION
            "A table to store the port specific parameters for event Port Recovery By Rate Limit registered port. And the parameters can be manipulated 
            by administrators."
        ::= { porteConfigPortRecoveryByRateLimit 3 }
 
    porteConfigPortRecoveryByRateLimitPortEntry OBJECT-TYPE
        SYNTAX PorteConfigPortRecoveryByRateLimitPortEntry
        MAX-ACCESS not-accessible
        STATUS current
        DESCRIPTION
            "An entry appears in this Port Table represent port information about 
            Port Recovery By Rate Limit event."
        INDEX { porteConfigPortRecoveryByRateLimitPortNum }
        ::= { porteConfigPortRecoveryByRateLimitPortTable 1 }

    PorteConfigPortRecoveryByRateLimitPortEntry ::=
        SEQUENCE {
            porteConfigPortRecoveryByRateLimitPortNum
                Integer32,
            porteConfigPortRecoveryByRateLimitPortEnable
                TruthValue
    }

    porteConfigPortRecoveryByRateLimitPortNum OBJECT-TYPE
        SYNTAX Integer32 (1..256)
        MAX-ACCESS read-only
        STATUS current
        DESCRIPTION
            "A unique value, greater than zero, indicating the Port number of 
             port configuration table."
        ::= { porteConfigPortRecoveryByRateLimitPortEntry 1 }

    porteConfigPortRecoveryByRateLimitPortEnable OBJECT-TYPE
        SYNTAX TruthValue
        MAX-ACCESS read-write
        STATUS current
        DESCRIPTION
            "This parameter when true(1) indicates that a port is enabled 
            the event Port Recovery By Rate Limit and false(2) indicates that this event is disabled 
            on the port."
        ::= { porteConfigPortRecoveryByRateLimitPortEntry 2 }

-- Port Shutdown By Port Security

    porteConfigPortShutdownByPortSecurity OBJECT IDENTIFIER ::= { porteConfiguration 5 }

    porteConfigPortShutdownByPortSecurityEnable OBJECT-TYPE
        SYNTAX TruthValue
        MAX-ACCESS read-write
        STATUS current
        DESCRIPTION
            "This enables or disables the event Port Shutdown By Port Security in the event notification. 
            A value of 'true' (1) indicates that notifications are 
            allowed to notify the user while the port shutdown by port security.
            A value of 'false'(2) indicates that notifications are not 
            allowed to notify the user while the port shutdown by port security."
        ::= { porteConfigPortShutdownByPortSecurity 1 }

    porteConfigPortShutdownByPortSecurityAction OBJECT IDENTIFIER ::= { porteConfigPortShutdownByPortSecurity 2 }

    porteConfigPortShutdownByPortSecurityTrapEnable OBJECT-TYPE
        SYNTAX TruthValue
        MAX-ACCESS read-write
        STATUS current
        DESCRIPTION
            "This enables or disables the notification action trap in the event Port Shutdown By Port Security. 
            A value of 'true' (1) indicates that the notification action trap is 
            allowed to notify the user while the port shutdown by port security.
            A value of 'false'(2) indicates that the notification action trap is not 
            allowed to notify the user while the port shutdown by port security."
        ::= { porteConfigPortShutdownByPortSecurityAction 1 }

    porteConfigPortShutdownByPortSecurityEmailEnable OBJECT-TYPE
        SYNTAX TruthValue
        MAX-ACCESS read-write
        STATUS current
        DESCRIPTION
            "This enables or disables the notification action email in the event Port Shutdown By Port Security. 
            A value of 'true' (1) indicates that the notification action email is 
            allowed to notify the user while the port shutdown by port security.
            A value of 'false'(2) indicates that the notification action email is not 
            allowed to notify the user while the port shutdown by port security."
        ::= { porteConfigPortShutdownByPortSecurityAction 2 }

    porteConfigPortShutdownByPortSecurityMgmtRelayEnable OBJECT-TYPE
        SYNTAX TruthValue
        MAX-ACCESS read-write
        STATUS current
        DESCRIPTION
            "This enables or disables the notification action MGMT relay in the event Port Shutdown By Port Security. 
            A value of 'true' (1) indicates that the notification action MGMT relay is 
            allowed to notify the user while the port shutdown by port security.
            A value of 'false'(2) indicates that the notification action MGMT relay is not 
            allowed to notify the user while the port shutdown by port security."
        ::= { porteConfigPortShutdownByPortSecurityAction 3 }

    porteConfigPortShutdownByPortSecurityPwr1RelayEnable OBJECT-TYPE
        SYNTAX TruthValue
        MAX-ACCESS read-write
        STATUS current
        DESCRIPTION
            "This enables or disables the notification action PWR1 relay in the event Port Shutdown By Port Security. 
            A value of 'true' (1) indicates that the notification action PWR1 relay is 
            allowed to notify the user while the port shutdown by port security.
            A value of 'false'(2) indicates that the notification action PWR1 relay is not 
            allowed to notify the user while the port shutdown by port security."
        ::= { porteConfigPortShutdownByPortSecurityAction 4 }

    porteConfigPortShutdownByPortSecurityPwr2RelayEnable OBJECT-TYPE
        SYNTAX TruthValue
        MAX-ACCESS read-write
        STATUS current
        DESCRIPTION
            "This enables or disables the notification action PWR2 relay in the event Port Shutdown By Port Security. 
            A value of 'true' (1) indicates that the notification action PWR2 relay is 
            allowed to notify the user while the port shutdown by port security.
            A value of 'false'(2) indicates that the notification action PWR2 relay is not 
            allowed to notify the user while the port shutdown by port security."
        ::= { porteConfigPortShutdownByPortSecurityAction 5 }

    porteConfigPortShutdownByPortSecurityPortTable OBJECT-TYPE
        SYNTAX SEQUENCE OF PorteConfigPortShutdownByPortSecurityPortEntry
        MAX-ACCESS not-accessible
        STATUS current
        DESCRIPTION
            "A table to store the port specific parameters for event Port Shutdown By Port Security registered port. And the parameters can be manipulated 
            by administrators."
        ::= { porteConfigPortShutdownByPortSecurity 3 }
 
    porteConfigPortShutdownByPortSecurityPortEntry OBJECT-TYPE
        SYNTAX PorteConfigPortShutdownByPortSecurityPortEntry
        MAX-ACCESS not-accessible
        STATUS current
        DESCRIPTION
            "An entry appears in this Port Table represent port information about 
            Port Shutdown By Port Security event."
        INDEX { porteConfigPortShutdownByPortSecurityPortNum }
        ::= { porteConfigPortShutdownByPortSecurityPortTable 1 }

    PorteConfigPortShutdownByPortSecurityPortEntry ::=
        SEQUENCE {
            porteConfigPortShutdownByPortSecurityPortNum
                Integer32,
            porteConfigPortShutdownByPortSecurityPortEnable
                TruthValue
    }

    porteConfigPortShutdownByPortSecurityPortNum OBJECT-TYPE
        SYNTAX Integer32 (1..256)
        MAX-ACCESS read-only
        STATUS current
        DESCRIPTION
            "A unique value, greater than zero, indicating the Port number of 
             port configuration table."
        ::= { porteConfigPortShutdownByPortSecurityPortEntry 1 }

    porteConfigPortShutdownByPortSecurityPortEnable OBJECT-TYPE
        SYNTAX TruthValue
        MAX-ACCESS read-write
        STATUS current
        DESCRIPTION
            "This parameter when true(1) indicates that a port is enabled 
            the event Port Shutdown By Port Security and false(2) indicates that this event is disabled on the port."
        ::= { porteConfigPortShutdownByPortSecurityPortEntry 2 }

-- Port Warning By Fiber Check

    porteConfigPortWarningByFiberCheck OBJECT IDENTIFIER ::= { porteConfiguration 6 }

    porteConfigPortWarningByFiberCheckEnable OBJECT-TYPE
        SYNTAX TruthValue
        MAX-ACCESS read-write
        STATUS current
        DESCRIPTION
            "This enables or disables the event Port Warning By Fiber Check in the event notification. 
            A value of 'true' (1) indicates that notifications are 
            allowed to notify the user while the port warning by fiber check.
            A value of 'false'(2) indicates that notifications are not 
            allowed to notify the user while the port warning by fiber check."
        ::= { porteConfigPortWarningByFiberCheck 1 }

    porteConfigPortWarningByFiberCheckAction OBJECT IDENTIFIER ::= { porteConfigPortWarningByFiberCheck 2 }

    porteConfigPortWarningByFiberCheckTrapEnable OBJECT-TYPE
        SYNTAX TruthValue
        MAX-ACCESS read-write
        STATUS current
        DESCRIPTION
            "This enables or disables the notification action trap in the event Port Warning By Fiber Check. 
            A value of 'true' (1) indicates that the notification action trap is 
            allowed to notify the user while the port warning by fiber check.
            A value of 'false'(2) indicates that the notification action trap is not 
            allowed to notify the user while the port warning by fiber check."
        ::= { porteConfigPortWarningByFiberCheckAction 1 }

    porteConfigPortWarningByFiberCheckEmailEnable OBJECT-TYPE
        SYNTAX TruthValue
        MAX-ACCESS read-write
        STATUS current
        DESCRIPTION
            "This enables or disables the notification action email in the event Port Warning By Fiber Check. 
            A value of 'true' (1) indicates that the notification action email is 
            allowed to notify the user while the port warning by fiber check.
            A value of 'false'(2) indicates that the notification action email is not 
            allowed to notify the user while the port warning by fiber check."
        ::= { porteConfigPortWarningByFiberCheckAction 2 }

    porteConfigPortWarningByFiberCheckMgmtRelayEnable OBJECT-TYPE
        SYNTAX TruthValue
        MAX-ACCESS read-write
        STATUS current
        DESCRIPTION
            "This enables or disables the notification action MGMT relay in the event Port Warning By Fiber Check. 
            A value of 'true' (1) indicates that the notification action MGMT relay is 
            allowed to notify the user while the port warning by fiber check.
            A value of 'false'(2) indicates that the notification action MGMT relay is not 
            allowed to notify the user while the port warning by fiber check."
        ::= { porteConfigPortWarningByFiberCheckAction 3 }

    porteConfigPortWarningByFiberCheckPwr1RelayEnable OBJECT-TYPE
        SYNTAX TruthValue
        MAX-ACCESS read-write
        STATUS current
        DESCRIPTION
            "This enables or disables the notification action PWR1 relay in the event Port Warning By Fiber Check. 
            A value of 'true' (1) indicates that the notification action PWR1 relay is 
            allowed to notify the user while the port warning by fiber check.
            A value of 'false'(2) indicates that the notification action PWR1 relay is not 
            allowed to notify the user while the port warning by fiber check."
        ::= { porteConfigPortWarningByFiberCheckAction 4 }

    porteConfigPortWarningByFiberCheckPwr2RelayEnable OBJECT-TYPE
        SYNTAX TruthValue
        MAX-ACCESS read-write
        STATUS current
        DESCRIPTION
            "This enables or disables the notification action PWR2 relay in the event Port Warning By Fiber Check. 
            A value of 'true' (1) indicates that the notification action PWR2 relay is 
            allowed to notify the user while the port warning by fiber check.
            A value of 'false'(2) indicates that the notification action PWR2 relay is not 
            allowed to notify the user while the port warning by fiber check."
        ::= { porteConfigPortWarningByFiberCheckAction 5 }

    porteConfigPortWarningByFiberCheckPortTable OBJECT-TYPE
        SYNTAX SEQUENCE OF PorteConfigPortWarningByFiberCheckPortEntry
        MAX-ACCESS not-accessible
        STATUS current
        DESCRIPTION
            "A table to store the port specific parameters for event Port Warning By Fiber Check registered port. And the parameters can be manipulated 
            by administrators."
        ::= { porteConfigPortWarningByFiberCheck 3 }

    porteConfigPortWarningByFiberCheckPortEntry OBJECT-TYPE
        SYNTAX PorteConfigPortWarningByFiberCheckPortEntry
        MAX-ACCESS not-accessible
        STATUS current
        DESCRIPTION
            "An entry appears in this Port Table represent port information about 
            Port Warning By Fiber Check event"
        INDEX { porteConfigPortWarningByFiberCheckPortNum }
        ::= { porteConfigPortWarningByFiberCheckPortTable 1 }

    PorteConfigPortWarningByFiberCheckPortEntry ::=
        SEQUENCE {
            porteConfigPortWarningByFiberCheckPortNum    Integer32,
            porteConfigPortWarningByFiberCheckPortEnable TruthValue
    }

    porteConfigPortWarningByFiberCheckPortNum OBJECT-TYPE
        SYNTAX Integer32 (1..256)
        MAX-ACCESS read-only
        STATUS current
        DESCRIPTION
            "A unique value, greater than zero, indicating the Port number of 
             port configuration table."
        ::= { porteConfigPortWarningByFiberCheckPortEntry 1 }

    porteConfigPortWarningByFiberCheckPortEnable OBJECT-TYPE
        SYNTAX TruthValue
        MAX-ACCESS read-write
        STATUS current
        DESCRIPTION
            "This parameter when true(1) indicates that a port is enabled 
            the event Port Warning By Fiber Check and false(2) indicates that this event is disabled 
            on the port."
        ::= { porteConfigPortWarningByFiberCheckPortEntry 2 }

-- -------------------------------------------------------------
-- Status group
-- -------------------------------------------------------------

END
