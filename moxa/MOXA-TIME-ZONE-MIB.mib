-- *****************************************************************
-- *  Moxa General (Time) - Time Zone PRIVATE MIB
-- *
-- *  Copyright (c) 2019 by Moxa Inc.
-- *  All rights reserved.
-- *****************************************************************

MOXA-TIME-ZONE-MIB DEFINITIONS ::= BEGIN
    IMPORTS
        MODULE-IDENTITY, OBJECT-TYPE,
        enterprises
            FROM SNMPv2-SMI
        TEXTUAL-CONVENTION
            FROM SNMPv2-TC
        time
            FROM MOXA-GENERAL-MIB;

    mxTimeZone MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines time zone settings"

        REVISION    "202202170000Z"
        DESCRIPTION "update CONTACT-INFO"

        REVISION    "201906300000Z"
        DESCRIPTION "Initial Revision"

        ::= { time 1 }

    moxa               OBJECT IDENTIFIER ::= { enterprises 8691 }
    general            OBJECT IDENTIFIER ::= { moxa 602 }
    time               OBJECT IDENTIFIER ::= { general 3 }

-- -------------------------------------------------------------
-- groups in the MOXA-TIME-ZONE-MIB MIB
-- -------------------------------------------------------------

    -- tzNotification OBJECT IDENTIFIER ::= { mxTimeZone 0 }
    tzConfiguration OBJECT IDENTIFIER ::= { mxTimeZone 1 }
    -- tzStatus OBJECT IDENTIFIER ::= { mxTimeZone 2 }
    -- tzExtensions OBJECT IDENTIFIER ::= { mxTimeZone 3 }

-- -------------------------------------------------------------
-- configuration group
-- -------------------------------------------------------------

    mxTzConfigTimeZone OBJECT-TYPE
        SYNTAX      INTEGER {
            utcMinus1200 (1),
            utcMinus1100 (2),
            utcMinus1000 (3),
            utcMinus0930 (4),
            utcMinus0900 (5),
            utcMinus0800 (6),
            utcMinus0700 (7),
            utcMinus0600 (8),
            utcMinus0500 (9),
            utcMinus0400 (10),
            utcMinus0330 (11),
            utcMinus0300 (12),
            utcMinus0200 (13),
            utcMinus0100 (14),
            utcPlus0000 (15),
            utcPlus0100 (16),
            utcPlus0200 (17),
            utcPlus0300 (18),
            utcPlus0330 (19),
            utcPlus0400 (20),
            utcPlus0430 (21),
            utcPlus0500 (22),
            utcPlus0530 (23),
            utcPlus0545 (24),
            utcPlus0600 (25),
            utcPlus0630 (26),
            utcPlus0700 (27),
            utcPlus0800 (28),
            utcPlus0830 (29),
            utcPlus0845 (30),
            utcPlus0900 (31),
            utcPlus0930 (32),
            utcPlus1000 (33),
            utcPlus1030 (34),
            utcPlus1100 (35),
            utcPlus1200 (36),
            utcPlus1245 (37),
            utcPlus1300 (38),
            utcPlus1400 (39)
        }
        MAX-ACCESS  read-write
        STATUS      current
        DESCRIPTION
                "Time zone setting of device"
        ::= { tzConfiguration 1 }

END
