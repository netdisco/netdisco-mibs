-- ****************************************************************
-- *  Moxa Switching - LLDP PRIVATE MIB
-- *
-- *  Copyright (c) 2019 by Moxa Inc.
-- *  All rights reserved.
-- *****************************************************************

MOXA-LLDP-MIB DEFINITIONS ::= BEGIN
    IMPORTS
        MODULE-IDENTITY, OBJECT-TYPE
            FROM SNMPv2-SMI
        TruthValue
            FROM SNMPv2-TC
        lldpLocPortNum
            FROM LLDP-MIB
        layer2Diagnosic
            FROM MOXA-SWITCHING-MIB;

    mxLldp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa LLDP"

        REVISION    "202202170000Z"
        DESCRIPTION "update CONTACT-INFO"

        REVISION    "201906300000Z"
        DESCRIPTION "Initial Revision"

        ::= { layer2Diagnosic 1 }

-- -------------------------------------------------------------
-- groups in the MOXA-LLDP-MIB MIB
-- -------------------------------------------------------------

  -- lldpNotification          OBJECT IDENTIFIER ::= { mxLldp 0 }
  lldpConfiguration         OBJECT IDENTIFIER ::= { mxLldp 1 }
  -- lldpStatus                OBJECT IDENTIFIER ::= { mxLldp 2 }
  -- lldpExtensions            OBJECT IDENTIFIER ::= { mxLldp 3 }
 
-- -------------------------------------------------------------
-- configuration group
-- -------------------------------------------------------------
  lldpConfigEnable OBJECT-TYPE
      SYNTAX TruthValue
      MAX-ACCESS read-write
      STATUS current
      DESCRIPTION
         "The administrative module status of LLDP module. 
          This enables or disables LLDP in the system. A value of 
          'enabled' (1) indicates that LLDP is enabled in the device
          and can be enabled port-wise. A value of 'disabled' (2) 
          indicates that LLDP is disabled in the device and also
          disabled on all ports.
         
          When LLLDP module status is changed from enabled to disabled, 
          a global timer (instead of port specific timers) is started 
          to ensure the successful transmission of shutdown frame on 
          all ports. Module status change from disabled to enabled is 
          not allowed when the global timer is running (i.e., when disable
          is in progress)."
      ::= { lldpConfiguration 1 }

   lldpConfigLocChassisIdSubtype  OBJECT-TYPE
      SYNTAX      INTEGER { chassiscomp(1), ifalias(2), portcomp(3),
                            macaddr(4), nwaddr(5), ifname(6), local(7) }
      MAX-ACCESS  read-write
      STATUS      current
      DESCRIPTION
         "The type of encoding used to identify the chassis component
      associated with the local system. 
          
      When chassis id subtype is configured as chassiscomp/portcomp/local
      it is mandatory to configure the fsLldpLocChassisId object. 
      If lldpConfigLocChassisId object is not configured, then current value of
      lldpConfigLocChassisId is advertised.
         
      When chassis id subtype is configured as ifalias/macaddr/nwaddr/
      ifname, it is not required to configure lldpConfigLocChassisId object. 
      System specific values are used for setting lldpConfigLocChassisId 
      object."
      REFERENCE
          "IEEE 802.1AB-2005 9.5.2.2"
    ::= { lldpConfiguration 2 }

   lldpConfigLocChassisId  OBJECT-TYPE
      SYNTAX      OCTET STRING (SIZE (1..255))
      MAX-ACCESS  read-write
      STATUS      current
      DESCRIPTION
         "The string value used to identify the chassis component
      associated with the local system. 
         
      Write operation to this object is allowed only when the chassis id 
      subtype is configured as chassiscomp/portcomp/local.

      When chassis id subtype is configured as ifalias/macaddr/nwaddr/ifname,
      system specific values are used and hence write operation to this 
      object is not allowed."
      REFERENCE
         "IEEE 802.1AB-2005 9.5.2.3"
      ::= { lldpConfiguration 3 }

  lldpConfigPortTable OBJECT-TYPE
      SYNTAX SEQUENCE OF LldpConfigPortEntry
      MAX-ACCESS not-accessible
      STATUS current
      DESCRIPTION
          "The port table."
      ::= { lldpConfiguration 4 }

  lldpConfigPortEntry OBJECT-TYPE
      SYNTAX LldpConfigPortEntry
      MAX-ACCESS not-accessible
      STATUS current
      DESCRIPTION
          "The port entry."
      INDEX { lldpLocPortNum }
      ::= { lldpConfigPortTable 1 }

  LldpConfigPortEntry ::=
      SEQUENCE {
          lldpConfigPortIdSubtype
              INTEGER,
          lldpConfigPortId
              OCTET STRING,
          lldpConfigVlanNameTxEnable  
              TruthValue    
      }

  lldpConfigPortIdSubtype OBJECT-TYPE
      SYNTAX         INTEGER {ifalias(1), portcomp(2), macaddr(3), ifname(5), local(7) }
      MAX-ACCESS     read-write
      STATUS         current
      DESCRIPTION
              "The type of port identifier encoding used to identify the port
      component associated with the local port.

      When port id subtype is configured as portcomp/local it is mandatory
      to configure the lldpConfigPortId object. If lldpConfigPortId
      object is not configured then current value of lldpConfigPortId is
      advertised.

      When port id subtype is configured as ifalias/macaddr/nwaddr/ifname it is 
      not required to configure lldpConfigPortId object. 
      System specific values are used for setting lldpConfigPortId object."
      REFERENCE
          "IEEE Std 802.1AB-2005 9.5.3.2" 
      ::= { lldpConfigPortEntry 1 }

  lldpConfigPortId OBJECT-TYPE
      SYNTAX         OCTET STRING (SIZE (1..255))
      MAX-ACCESS     read-write
      STATUS         current
      DESCRIPTION
        "The string value used to identify the port component associated
      with the local port.

      Write operation to this object is allowed only when the port id
      subtype is configured as portcomp/local.

      When port id subtype is configured as ifalias/macaddr/nwaddr/ifname/
      agentcircuitid, system specific values are used and hence write operation to this
      object is not allowed."
      REFERENCE
            "IEEE Std 802.1AB-2005 9.5.3.3"
      ::= { lldpConfigPortEntry 2 }

  lldpConfigVlanNameTxEnable  OBJECT-TYPE
      SYNTAX        TruthValue
      MAX-ACCESS    read-write
      STATUS        current
      DESCRIPTION
         "The boolean value that indicates whether the corresponding
      Local System VLAN name instance will be transmitted on the port.

      The value of this object must be restored from non-volatile
      storage after a re-initialization of the management system."
      REFERENCE 
            "IEEE 802.1AB-2005 10.2.1.1"
      ::= { lldpConfigPortEntry 3 }

END
