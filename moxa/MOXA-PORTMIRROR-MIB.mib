-- ****************************************************************
-- *  Moxa Switching - Port Mirror PRIVATE MIB
-- *
-- *  Copyright (c) 2019 by Moxa Inc.
-- *  All rights reserved.
-- *****************************************************************

MOXA-PORTMIRROR-MIB DEFINITIONS ::= BEGIN
    IMPORTS
        MODULE-IDENTITY, NOTIFICATION-TYPE, OBJECT-TYPE, IpAddress, Integer32
            FROM SNMPv2-SMI
        TEXTUAL-CONVENTION, DateAndTime, MacAddress, DisplayString, TruthValue
            FROM SNMPv2-TC
        layer2Diagnosic
          FROM MOXA-SWITCHING-MIB;

    mxPortMirror MODULE-IDENTITY
        LAST-UPDATED "202206150000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa Port Mirror"

        REVISION    "202206150000Z"
        DESCRIPTION
			"Support RSPAN, source port channel, reflect port mode,
			 Added objects:
                portMirrorRSpanIntmedRole,
                portMirrorRSpanIntmedVlanId,
                portMirrorTableEntryRSpanDestPortList,
                portMirrorSourcePortChannelRxList,
                portMirrorSourcePortChannelTxList,
                portMirrorTableEntryRSpanType,
                portMirrorTableEntryRSpanVlanId,
				portMirrorTableEntryReflectPortMode
             Modified objects:
                portMirrorTableEntryStatus,
                portMirrorSourcePortRxList,
                portMirrorSourcePortTxList"

        REVISION    "202202170000Z"
        DESCRIPTION "update CONTACT-INFO"

        REVISION    "201906300000Z"
        DESCRIPTION "Initial Revision"

        ::= { layer2Diagnosic 5 }

-- -------------------------------------------------------------
-- groups in the MOXA-PORTMIRROR-MIB MIB
-- -------------------------------------------------------------

  -- portMirrorNotification    OBJECT IDENTIFIER ::= { mxPortMirror 0 }
  portMirrorConfiguration   OBJECT IDENTIFIER ::= { mxPortMirror 1 }
  -- portMirrorStatus          OBJECT IDENTIFIER ::= { mxPortMirror 2 }
  -- portMirrorExtensions      OBJECT IDENTIFIER ::= { mxPortMirror 3 }

-- -------------------------------------------------------------
-- configuration group
-- -------------------------------------------------------------
  portMirrorEnable OBJECT-TYPE
      SYNTAX TruthValue
      MAX-ACCESS read-write
      STATUS current
      DESCRIPTION
          "This enable Port Mirror Function."
      ::= { portMirrorConfiguration 1 }

  portMirrorTable OBJECT-TYPE
      SYNTAX SEQUENCE OF PortMirrorEntry
      MAX-ACCESS not-accessible
      STATUS current
      DESCRIPTION
          "The port-mirror table."
      ::= { portMirrorConfiguration 2 }

  portMirrorRSpanIntmedRole OBJECT-TYPE
      SYNTAX TruthValue
      MAX-ACCESS read-write
      STATUS current
      DESCRIPTION
          "This enable Port Mirror RSPAN Intermediate Function."
      ::= { portMirrorConfiguration 3 }

  portMirrorRSpanIntmedVlanId OBJECT-TYPE
      SYNTAX Integer32
      MAX-ACCESS read-write
      STATUS current
      DESCRIPTION
          "RSPAN Intermediate VLAN ID."
      ::= { portMirrorConfiguration 4 }

  portMirrorEntry OBJECT-TYPE
      SYNTAX PortMirrorEntry
      MAX-ACCESS not-accessible
      STATUS current
      DESCRIPTION
          "The port-mirror table entry."
      INDEX { portMirrorTableEntryIndex }
      ::= { portMirrorTable 1 }

  PortMirrorEntry ::=
      SEQUENCE {
          portMirrorTableEntryIndex
              INTEGER,
          portMirrorTableEntryStatus
              INTEGER,
          portMirrorTableEntrySessionID
              Integer32,
		  portMirrorTableEntrySpanDestPort
              Integer32,
          portMirrorSourcePortRxList
              OCTET STRING,
          portMirrorSourcePortTxList
              OCTET STRING,
          portMirrorTableEntryRSpanDestPortList
              OCTET STRING,
	      portMirrorSourcePortChannelRxList
              OCTET STRING,
          portMirrorSourcePortChannelTxList
              OCTET STRING,
		  portMirrorTableEntryRSpanType
              INTEGER,
          portMirrorTableEntryRSpanVlanId
              Integer32,
		  portMirrorTableEntryReflectPortMode
              INTEGER
      }

  portMirrorTableEntryIndex OBJECT-TYPE
     SYNTAX      INTEGER
     MAX-ACCESS  read-only
     STATUS      current
     DESCRIPTION
        "The entry index of the port-mirror table."
     ::= { portMirrorEntry 1 }

  portMirrorTableEntryStatus OBJECT-TYPE
      SYNTAX TruthValue
      MAX-ACCESS read-write
      STATUS current
      DESCRIPTION
          "This object is used to created(1) or deleted(2) Port Mirror Table Entry Function."
      ::= { portMirrorEntry 2 }

  portMirrorTableEntrySessionID OBJECT-TYPE
     SYNTAX      Integer32
     MAX-ACCESS  read-only
     STATUS      current
     DESCRIPTION
        "The session index of the port-mirror table."
     ::= { portMirrorEntry 3 }

  portMirrorTableEntrySpanDestPort OBJECT-TYPE
     SYNTAX      Integer32
     MAX-ACCESS  read-write
     STATUS      current
     DESCRIPTION
        "The destination port of the port-mirror SPAN session."
     ::= { portMirrorEntry 4 }

  portMirrorSourcePortRxList OBJECT-TYPE
     SYNTAX       OCTET STRING (SIZE(0..128))
     MAX-ACCESS   read-write
     STATUS       current
     DESCRIPTION
         "The RX source port(s) of the port-mirror session.
		  Set the hex value of a 1-based port index, e.g. 0x01 for port 1."
    ::= { portMirrorEntry 5 }


  portMirrorSourcePortTxList OBJECT-TYPE
     SYNTAX         OCTET STRING (SIZE(0..128))
     MAX-ACCESS     read-write
     STATUS         current
     DESCRIPTION
        "The TX source port(s) of the port-mirror session.
		 Set the hex value of a 1-based port index, e.g. 0x01 for port 1."
    ::= { portMirrorEntry 6 }

  portMirrorTableEntryRSpanDestPortList OBJECT-TYPE
     SYNTAX      OCTET STRING (SIZE(0..128))
     MAX-ACCESS  read-write
     STATUS      current
     DESCRIPTION
        "The designated port / reflect port / destination port(s) of the port-mirror RSPAN session.
		 Set the hex value of a 1-based port index, e.g. 0x01 for port 1."

    ::= { portMirrorEntry 7 }

  portMirrorSourcePortChannelRxList OBJECT-TYPE
     SYNTAX       OCTET STRING (SIZE(0..128))
     MAX-ACCESS   read-write
     STATUS       current
     DESCRIPTION
         "The RX source port channel(s) of the port-mirror session.
		  Set the hex value of a 1-based port channel index, e.g. 0x01 for port channel 1."
    ::= { portMirrorEntry 8 }


  portMirrorSourcePortChannelTxList OBJECT-TYPE
     SYNTAX         OCTET STRING (SIZE(0..128))
     MAX-ACCESS     read-write
     STATUS         current
     DESCRIPTION
        "The TX source port channel(s) of the port-mirror session.
		 Set the hex value of a 1-based port channel index, e.g. 0x01 for port channel 1."
    ::= { portMirrorEntry 9 }

  portMirrorTableEntryRSpanType OBJECT-TYPE
     SYNTAX      INTEGER
     MAX-ACCESS  read-write
     STATUS      current
     DESCRIPTION
        "The RSPAN type of the port-mirror session."
     ::= { portMirrorEntry 10 }

  portMirrorTableEntryRSpanVlanId OBJECT-TYPE
     SYNTAX      Integer32
     MAX-ACCESS  read-write
     STATUS      current
     DESCRIPTION
        "The RSPAN VLAN ID of the port-mirror session."
     ::= { portMirrorEntry 11 }

  portMirrorTableEntryReflectPortMode OBJECT-TYPE
     SYNTAX      TruthValue
     MAX-ACCESS  read-write
     STATUS      current
     DESCRIPTION
        "This enable reflect port mode of the port-mirror session."
     ::= { portMirrorEntry 12 }

END
