-- *****************************************************************
-- *  Moxa General (Device Security) - UI Service Management PRIVATE MIB
-- *
-- *  Copyright (c) 2019 by Moxa Inc.
-- *  All rights reserved.
-- *****************************************************************

MOXA-UI-SERVICE-MGMT-MIB DEFINITIONS ::= BEGIN
    IMPORTS
        MODULE-IDENTITY, OBJECT-TYPE, Integer32,
        enterprises
            FROM SNMPv2-SMI
        TEXTUAL-CONVENTION, TruthValue
            FROM SNMPv2-TC
        deviceSecurity
            FROM MOXA-GENERAL-MIB;

    mxUiServiceMgmt MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "
            This MIB module defines settings used for UI service
            management
            "

        REVISION    "202202170000Z"
        DESCRIPTION "update CONTACT-INFO"

        REVISION    "201906300000Z"
        DESCRIPTION "Initial Revision"

        ::= { deviceSecurity 1 }

    moxa               OBJECT IDENTIFIER ::= { enterprises 8691 }
    general            OBJECT IDENTIFIER ::= { moxa 602 }
    deviceSecurity     OBJECT IDENTIFIER ::= { general 5 }

-- -------------------------------------------------------------
-- groups in the MOXA-UI-SERVICE-MGMT-MIB MIB
-- -------------------------------------------------------------

    -- usmNotification OBJECT IDENTIFIER ::= { mxUiServiceMgmt 0 }
    usmConfiguration OBJECT IDENTIFIER ::= { mxUiServiceMgmt 1 }
    -- usmStatus OBJECT IDENTIFIER ::= { mxUiServiceMgmt 2 }
    -- usmExtensions OBJECT IDENTIFIER ::= { mxUiServiceMgmt 3 }

-- -------------------------------------------------------------
-- configuration group
-- -------------------------------------------------------------

    mxUsmConfigHttp OBJECT IDENTIFIER ::= { usmConfiguration 1 }

    mxUsmConfigHttpEnable OBJECT-TYPE
        SYNTAX      TruthValue
        MAX-ACCESS  read-write
        STATUS      current
        DESCRIPTION
                "Enable/Disable HTTP service"
        ::= { mxUsmConfigHttp 1 }

    mxUsmConfigHttpPort OBJECT-TYPE
        SYNTAX      Integer32 (1..65535)
        MAX-ACCESS  read-write
        STATUS      current
        DESCRIPTION
                "Service port of HTTP service"
        ::= { mxUsmConfigHttp 2 }

    mxUsmConfigHttps OBJECT IDENTIFIER ::= { usmConfiguration 2 }

    mxUsmConfigHttpsEnable OBJECT-TYPE
        SYNTAX      TruthValue
        MAX-ACCESS  read-write
        STATUS      current
        DESCRIPTION
                "Enable/Disable HTTPS service"
        ::= { mxUsmConfigHttps 1 }

    mxUsmConfigHttpsPort OBJECT-TYPE
        SYNTAX      Integer32 (1..65535)
        MAX-ACCESS  read-write
        STATUS      current
        DESCRIPTION
                "Service port of HTTPS service"
        ::= { mxUsmConfigHttps 2 }

    mxUsmConfigTelnet OBJECT IDENTIFIER ::= { usmConfiguration 3 }

    mxUsmConfigTelnetEnable OBJECT-TYPE
        SYNTAX      TruthValue
        MAX-ACCESS  read-write
        STATUS      current
        DESCRIPTION
                "Enable/Disable Telnet service"
        ::= { mxUsmConfigTelnet 1 }

    mxUsmConfigTelnetPort OBJECT-TYPE
        SYNTAX      Integer32 (1..65535)
        MAX-ACCESS  read-write
        STATUS      current
        DESCRIPTION
                "Service port of Telnet service"
        ::= { mxUsmConfigTelnet 2 }

    mxUsmConfigSsh OBJECT IDENTIFIER ::= { usmConfiguration 4 }

    mxUsmConfigSshEnable OBJECT-TYPE
        SYNTAX      TruthValue
        MAX-ACCESS  read-write
        STATUS      current
        DESCRIPTION
                "Enable/Disable SSH service"
        ::= { mxUsmConfigSsh 1 }

    mxUsmConfigSshPort OBJECT-TYPE
        SYNTAX      Integer32 (1..65535)
        MAX-ACCESS  read-write
        STATUS      current
        DESCRIPTION
                "Service port of SSH service"
        ::= { mxUsmConfigSsh 2 }

    mxUsmConfigSnmp OBJECT IDENTIFIER ::= { usmConfiguration 5 }

    mxUsmConfigSnmpMode OBJECT-TYPE
        SYNTAX      Integer32 (1..3)
        MAX-ACCESS  read-write
        STATUS      current
        DESCRIPTION
                "Enable(1)/Disable(2)/Read-only(3) SNMP service"
        ::= { mxUsmConfigSnmp 1 }

    mxUsmConfigSnmpPort OBJECT-TYPE
        SYNTAX      Integer32 (1..65535)
        MAX-ACCESS  read-write
        STATUS      current
        DESCRIPTION
                "Service port of SNMP service"
        ::= { mxUsmConfigSnmp 2 }

    mxUsmConfigSnmpTransportLayerProtocol OBJECT-TYPE
        SYNTAX      INTEGER {
            UDP (1),
            TCP (2)
        }
        MAX-ACCESS  read-write
        STATUS      current
        DESCRIPTION
                "Transport layer protocol of SNMP service"
        ::= { mxUsmConfigSnmp 3 }

    mxUsmConfigMoxaCommand OBJECT IDENTIFIER ::= { usmConfiguration 6 }

    mxUsmConfigMoxaCommandEnable OBJECT-TYPE
        SYNTAX      TruthValue
        MAX-ACCESS  read-write
        STATUS      current
        DESCRIPTION
                "Enable/Disable Moxa Command service"
        ::= { mxUsmConfigMoxaCommand 1 }

    usmConfigHttpMaxSessions OBJECT-TYPE
        SYNTAX      Integer32 (1..10)
        MAX-ACCESS  read-write
        STATUS      current
        DESCRIPTION
                "Maximum concurrent login sessions through HTTP/HTTPS service"
        ::= { usmConfiguration 7 }

    usmConfigTerminalMaxSessions OBJECT-TYPE
        SYNTAX      Integer32 (1..5)
        MAX-ACCESS  read-write
        STATUS      current
        DESCRIPTION
                "Maximum concurrent login sessions through Telnet/SSH service"
        ::= { usmConfiguration 8 }
END
