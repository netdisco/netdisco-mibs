-- ****************************************************************
-- *  Moxa General (System Management) - Login Policy PRIVATE MIB
-- *
-- *  Copyright (c) 2019 by Moxa Inc.
-- *  All rights reserved.
-- *****************************************************************

MOXA-SYSTEM-LOGIN-POLICY-MIB DEFINITIONS ::= BEGIN
    IMPORTS
        MODULE-IDENTITY, OBJECT-TYPE,
        IpAddress, Unsigned32,
        enterprises                     FROM SNMPv2-SMI

        TEXTUAL-CONVENTION, RowStatus,
        DateAndTime, MacAddress,
        DisplayString, TruthValue       FROM SNMPv2-TC;

    mxSysLoginPolicySvr MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines login policy configuration"

        REVISION    "202202170000Z"
        DESCRIPTION "update CONTACT-INFO"

        REVISION    "201906300000Z"
        DESCRIPTION "Initial Revision"

        ::= { systemManagement 5 }

    moxa               OBJECT IDENTIFIER ::= { enterprises 8691 }
    general            OBJECT IDENTIFIER ::= { moxa 602 }
    systemManagement   OBJECT IDENTIFIER ::= { general 1 }

-- -------------------------------------------------------------
-- groups in the LOGIN POLICY PRIVATE MIB
-- -------------------------------------------------------------

   -- lpNotification  OBJECT IDENTIFIER ::= { mxSysLoginPolicySvr 0 }
   lpConfiguration  OBJECT IDENTIFIER ::= { mxSysLoginPolicySvr 1 }
   -- lpStatus  OBJECT IDENTIFIER ::= { mxSysLoginPolicySvr 2 }
   -- lpExtension  OBJECT IDENTIFIER ::= { mxSysLoginPolicySvr 3 }

-- -------------------------------------------------------------
-- Config group
-- -------------------------------------------------------------

    lpConfigWebLoginMessage OBJECT-TYPE
        SYNTAX      DisplayString
        MAX-ACCESS  read-write
        STATUS      current
        DESCRIPTION
            "Web Login Message."
         ::= { lpConfiguration 1 }

    lpConfigLoginFailureMessage OBJECT-TYPE
        SYNTAX      DisplayString
        MAX-ACCESS  read-write
        STATUS      current
        DESCRIPTION
            "Login Failure Message."
         ::= { lpConfiguration 2 }

    lpConfigEnableFailureLockout OBJECT-TYPE
        SYNTAX      TruthValue
        MAX-ACCESS  read-write
        STATUS      current
        DESCRIPTION
            "Enable Failure Lockout."
         ::= { lpConfiguration 3 }

    lpConfigRetryFailureThreshold OBJECT-TYPE
        SYNTAX      Unsigned32
        MAX-ACCESS  read-write
        STATUS      current
        DESCRIPTION
            "Retry Failure Threshold."
         ::= { lpConfiguration 4 }

    lpConfigFailureLockoutTime OBJECT-TYPE
        SYNTAX      Unsigned32
        MAX-ACCESS  read-write
        STATUS      current
        DESCRIPTION
            "Failure Lockout Time (min)."
         ::= { lpConfiguration 5 }

    lpConfigAutoLogout OBJECT-TYPE
        SYNTAX      Unsigned32
        MAX-ACCESS  read-write
        STATUS      current
        DESCRIPTION
            "Auto Logout (min)."
         ::= { lpConfiguration 6 }

END
