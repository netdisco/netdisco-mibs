-- ****************************************************************
-- *  Moxa General (Event Notification) - TRAP PRIVATE MIB
-- *
-- *  Copyright (c) 2019 by Moxa Inc.
-- *  All rights reserved.
-- *****************************************************************

MOXA-TRAP-CONFIGURATION-MIB DEFINITIONS ::= BEGIN
    IMPORTS
        MODULE-IDENTITY, NOTIFICATION-TYPE, OBJECT-TYPE, IpAddress, Unsigned32,
        enterprises
            FROM SNMPv2-SMI
        TEXTUAL-CONVENTION, DateAndTime, MacAddress, DisplayString, TruthValue, RowStatus
            FROM SNMPv2-TC;

  mxTrapConfig MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines trap notification"

        REVISION    "202202170000Z"
        DESCRIPTION "update CONTACT-INFO"

        REVISION    "201906300000Z"
        DESCRIPTION "Initial Revision"

        ::= { eventNotification 2 }

    moxa                 OBJECT IDENTIFIER ::= { enterprises 8691 }
    general              OBJECT IDENTIFIER ::= { moxa         602 }
    eventNotification    OBJECT IDENTIFIER ::= { general        7 }

-- -------------------------------------------------------------
-- groups in the MOXA-TRAP-CONFIGURATION-MIB MIB
-- -------------------------------------------------------------

    -- trapNotification    OBJECT IDENTIFIER ::= { mxTrapConfig 0 }
    trapConfiguration   OBJECT IDENTIFIER ::= { mxTrapConfig 1 }
    -- trapStatus          OBJECT IDENTIFIER ::= { mxTrapConfig 2 }
    -- trapExtensions      OBJECT IDENTIFIER ::= { mxTrapConfig 3 }

-- -------------------------------------------------------------
-- configuration group
-- -------------------------------------------------------------

    trapConfigInformRetries OBJECT-TYPE
      SYNTAX        INTEGER (1..99)
      MAX-ACCESS    read-write
      STATUS        current
      DESCRIPTION
          "The inform retry times of the SNMP trap host"
      ::= { trapConfiguration 1 }

    trapConfigInformTimeout OBJECT-TYPE
      SYNTAX        INTEGER (1..300)
      MAX-ACCESS    read-write
      STATUS        current
      DESCRIPTION
          "The inform interval of the SNMP trap host"
      ::= { trapConfiguration 2 }

    trapConfigHostTable     OBJECT-TYPE
      SYNTAX        SEQUENCE OF TrapConfigHostEntry
      MAX-ACCESS    not-accessible
      STATUS        current
      DESCRIPTION
          " the SNMP Trap Host Table "
      ::= { trapConfiguration 3 }

    trapConfigHostEntry     OBJECT-TYPE
      SYNTAX        TrapConfigHostEntry
      MAX-ACCESS    not-accessible
      STATUS        current
      DESCRIPTION
          " the SNMP Trap Host Table Entry."
      INDEX { trapConfigHostIndex }
      ::= { trapConfigHostTable 1 }

    TrapConfigHostEntry ::=
      SEQUENCE {
            trapConfigHostIndex
                INTEGER,
            trapConfigHostAddress
                DisplayString,
            trapConfigHostMode
                INTEGER,
            trapConfigHostCommunity
                DisplayString,
            trapConfigHostRowStatus
                RowStatus
      }
    trapConfigHostIndex OBJECT-TYPE
        SYNTAX      INTEGER
        MAX-ACCESS  read-only
        STATUS      current
        DESCRIPTION
            "The index of the SNMP trap host Entry."
         ::= { trapConfigHostEntry 1 }

    trapConfigHostAddress OBJECT-TYPE
      SYNTAX        DisplayString
      MAX-ACCESS    read-create
      STATUS        current
      DESCRIPTION
          "The IP address/Domain name of the SNMP trap host"
      ::= { trapConfigHostEntry 2 }

    trapConfigHostMode OBJECT-TYPE
      SYNTAX        INTEGER
                    {
                        trapv1(1),
                        trapv2c(2),
                        informv2c(3),
                        trapv3(4),
                        informv3(5)
                    }
      MAX-ACCESS    read-create
      STATUS        current
      DESCRIPTION
          "SNMP Trap Version
           Value :
            1 -> trapv1,
            2 -> trapv2c,
            3 -> informv2c
            4 -> trapv3
            5 -> informv3"
      ::= { trapConfigHostEntry 3 }

    trapConfigHostCommunity OBJECT-TYPE
      SYNTAX        DisplayString
      MAX-ACCESS    read-create
      STATUS        current
      DESCRIPTION
          "The community name of the SNMP trap host"
      ::= { trapConfigHostEntry 4 }

    trapConfigHostRowStatus OBJECT-TYPE
        SYNTAX     RowStatus
        MAX-ACCESS read-create
        STATUS     current
        DESCRIPTION
            "This object indicates the status of this entry."
        ::= { trapConfigHostEntry 5 }

END
