-- *****************************************************************
-- *  Moxa General (Network Configuration) - Management IP PRIVATE MIB
-- *
-- *  Copyright (c) 2019 by Moxa Inc.
-- *  All rights reserved.
-- *****************************************************************

MOXA-MANAGEMENT-IP-MIB DEFINITIONS ::= BEGIN
    IMPORTS
        MODULE-IDENTITY, OBJECT-TYPE, IpAddress, Integer32,
        enterprises
            FROM SNMPv2-SMI
        TEXTUAL-CONVENTION, DisplayString
            FROM SNMPv2-TC
        networkConfiguration
            FROM MOXA-GENERAL-MIB;

    mxManagementIp MODULE-IDENTITY
        LAST-UPDATED "202303130000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines IP settings used for device management"

        REVISION    "202303130000Z"
        DESCRIPTION "update mxMiConfigIpv4Mode parameter to support DCP IP setting request"

        REVISION    "202202170000Z"
        DESCRIPTION "update CONTACT-INFO"

        REVISION    "201906300000Z"
        DESCRIPTION "Initial Revision"

        ::= { networkConfiguration 1 }

    moxa               OBJECT IDENTIFIER ::= { enterprises 8691 }
    general            OBJECT IDENTIFIER ::= { moxa 602 }
    networkConfiguration     OBJECT IDENTIFIER ::= { general 2 }

-- -------------------------------------------------------------
-- groups in the MOXA-MANAGEMENT-MIB MIB
-- -------------------------------------------------------------

    -- miNotification  OBJECT IDENTIFIER ::= { mxManagementIp 0 }
    miConfiguration OBJECT IDENTIFIER ::= { mxManagementIp 1 }
    -- miStatus        OBJECT IDENTIFIER ::= { mxManagementIp 2 }
    -- miExtensions     OBJECT IDENTIFIER ::= { mxManagementIp 3 }

-- -------------------------------------------------------------
-- configuration group
-- -------------------------------------------------------------

    mxMiConfigIpv4 OBJECT IDENTIFIER ::= { miConfiguration 1 }

    mxMiConfigIpv4Mode OBJECT-TYPE
        SYNTAX      INTEGER {
            manual (1),
            dhcp (2),
            profinet-dcp (3)
        }
        MAX-ACCESS  read-write
        STATUS      current
        DESCRIPTION
                "Management IP setup mode for IPv4"
        ::= { mxMiConfigIpv4 1 }

    mxMiConfigIpv4Address OBJECT-TYPE
        SYNTAX      IpAddress
        MAX-ACCESS  read-write
        STATUS      current
        DESCRIPTION
                "IPv4 management address"
        ::= { mxMiConfigIpv4 2 }

    mxMiConfigIpv4Netmask OBJECT-TYPE
        SYNTAX      IpAddress
        MAX-ACCESS  read-write
        STATUS      current
        DESCRIPTION
                "IPv4 management netmask"
        ::= { mxMiConfigIpv4 3 }

    mxMiConfigIpv4Gateway OBJECT-TYPE
        SYNTAX      IpAddress
        MAX-ACCESS  read-write
        STATUS      current
        DESCRIPTION
                "IPv4 management gateway"
        ::= { mxMiConfigIpv4 4 }

    mxMiConfigIpv4DnsServerTable OBJECT-TYPE
        SYNTAX      SEQUENCE OF MxMiConfigIpv4DnsServerEntry
        MAX-ACCESS  not-accessible
        STATUS      current
        DESCRIPTION
            "A table of IPv4 DNS servers."
        ::= { mxMiConfigIpv4 5 }

    mxMiConfigIpv4DnsServerEntry OBJECT-TYPE
        SYNTAX        MxMiConfigIpv4DnsServerEntry
        MAX-ACCESS    not-accessible
        STATUS        current
        DESCRIPTION
            "An IPv4 DNS server."
        INDEX        { mxMiConfigIpv4DnsServerIndex }
        ::= { mxMiConfigIpv4DnsServerTable 1 }

    MxMiConfigIpv4DnsServerEntry ::=
        SEQUENCE {
            mxMiConfigIpv4DnsServerIndex      Integer32,
            mxMiConfigIpv4DnsServerAddress    IpAddress
        }

    mxMiConfigIpv4DnsServerIndex OBJECT-TYPE
        SYNTAX      Integer32 (1..2)
        MAX-ACCESS  not-accessible
        STATUS      current
        DESCRIPTION
            "Index of DNS server in table."
        ::= { mxMiConfigIpv4DnsServerEntry 1 }

    mxMiConfigIpv4DnsServerAddress OBJECT-TYPE
        SYNTAX      IpAddress
        MAX-ACCESS  read-write
        STATUS      current
        DESCRIPTION
            "Address of IPv4 DNS server."
        ::= { mxMiConfigIpv4DnsServerEntry 2 }

    mxMiConfigIpv6 OBJECT IDENTIFIER ::= { miConfiguration 2 }

    miConfigIpv6GlobalUnicastAddressPrefix OBJECT-TYPE
        SYNTAX      DisplayString
        MAX-ACCESS  read-write
        STATUS      current
        DESCRIPTION
            "Global unicast prefix of IPv6 management address"
        ::= { mxMiConfigIpv6 1 }

    mxMiConfigIpv6DnsServerTable OBJECT-TYPE
        SYNTAX      SEQUENCE OF MxMiConfigIpv6DnsServerEntry
        MAX-ACCESS  not-accessible
        STATUS      current
        DESCRIPTION
            "A table of IPv6 DNS servers."
        ::= { mxMiConfigIpv6 2 }

    mxMiConfigIpv6DnsServerEntry OBJECT-TYPE
        SYNTAX        MxMiConfigIpv6DnsServerEntry
        MAX-ACCESS    not-accessible
        STATUS        current
        DESCRIPTION
            "An IPv6 DNS server."
        INDEX        { mxMiConfigIpv6DnsServerIndex }
        ::= { mxMiConfigIpv6DnsServerTable 1 }

    MxMiConfigIpv6DnsServerEntry ::=
        SEQUENCE {
            mxMiConfigIpv6DnsServerIndex      Integer32,
            mxMiConfigIpv6DnsServerAddress    DisplayString
        }

    mxMiConfigIpv6DnsServerIndex OBJECT-TYPE
        SYNTAX      Integer32 (1..2)
        MAX-ACCESS  not-accessible
        STATUS      current
        DESCRIPTION
            "Index of DNS server in table."
        ::= { mxMiConfigIpv6DnsServerEntry 1 }

    mxMiConfigIpv6DnsServerAddress OBJECT-TYPE
        SYNTAX      DisplayString
        MAX-ACCESS  read-write
        STATUS      current
        DESCRIPTION
            "Address of IPv6 DNS server."
        ::= { mxMiConfigIpv6DnsServerEntry 2 }

END
