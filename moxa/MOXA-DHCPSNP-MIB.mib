-- ****************************************************************
-- *  Moxa Switching - Dhcp Snooping PRIVATE MIB
-- *
-- *  Copyright (c) 2019 by Moxa Inc.
-- *  All rights reserved.
-- *****************************************************************

MOXA-DHCPSNP-MIB DEFINITIONS ::= BEGIN
    IMPORTS
        MODULE-IDENTITY, NOTIFICATION-TYPE, OBJECT-TYPE, IpAddress, Integer32
            FROM SNMPv2-SMI
        TEXTUAL-CONVENTION, DateAndTime, MacAddress, DisplayString, TruthValue, RowStatus
            FROM SNMPv2-TC
        layer2Security
          FROM MOXA-SWITCHING-MIB;

    mxDhcpSnp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "

        DESCRIPTION
            "The MIB module defines Moxa DHCP Snooping"

        REVISION    "202202170000Z"
        DESCRIPTION "update CONTACT-INFO"

        REVISION    "202106300000Z"
        DESCRIPTION "Initial Revision"

        ::= { layer2Security 11 }

-- -------------------------------------------------------------
-- groups in the MOXA-DHCPSNP-MIB MIB
-- -------------------------------------------------------------

  dhcpSnpNotification      OBJECT IDENTIFIER ::= { mxDhcpSnp 0 }
  dhcpSnpConfiguration     OBJECT IDENTIFIER ::= { mxDhcpSnp 1 }
  dhcpSnpStatus            OBJECT IDENTIFIER ::= { mxDhcpSnp 2 }


-- -------------------------------------------------------------
-- configuration group
-- -------------------------------------------------------------

    dhcpSnpConfigGlobalEnable OBJECT-TYPE
        SYNTAX       TruthValue
        MAX-ACCESS   read-write
        STATUS       current
        DESCRIPTION
            "This object indicates if DHCP Snooping is globally enabled/disabled."
        ::= { dhcpSnpConfiguration 1 }

-- DHCP Snooping VLAN Table Configuration Start

    dhcpSnpConfigVlanTable OBJECT-TYPE
        SYNTAX SEQUENCE OF DhcpSnpConfigVlanEntry
        MAX-ACCESS not-accessible
        STATUS current
        DESCRIPTION
            "The table listing the VLAN table
                 which enabled DHCP Snooping."
        ::= { dhcpSnpConfiguration 2}

    dhcpSnpConfigVlanEntry OBJECT-TYPE
        SYNTAX DhcpSnpConfigVlanEntry
        MAX-ACCESS not-accessible
        STATUS current
        DESCRIPTION
            "Each row instance gives the DHCP snooping status on VLAN for the
             DHCP snooping module."
        INDEX { dhcpSnpConfigIndex }
        ::= { dhcpSnpConfigVlanTable 1 }

    DhcpSnpConfigVlanEntry ::= SEQUENCE {
        dhcpSnpConfigIndex           Integer32,
        dhcpSnpConfigVlanId          Integer32,
        dhcpSnpConfigRowStatus       RowStatus
        }

    dhcpSnpConfigIndex OBJECT-TYPE
        SYNTAX      Integer32 (1..4094)
        MAX-ACCESS  not-accessible
        STATUS      current
        DESCRIPTION
            "Index of VLAN table."
        ::= { dhcpSnpConfigVlanEntry 3 }

    dhcpSnpConfigVlanId OBJECT-TYPE
        SYNTAX Integer32 (1..4094)
        MAX-ACCESS read-write
        STATUS current
        DESCRIPTION
            "Vlan ID of the VLAN to which this table-entry is associated."
        ::= { dhcpSnpConfigVlanEntry 1 }

    dhcpSnpConfigRowStatus OBJECT-TYPE
        SYNTAX      RowStatus
        MAX-ACCESS  read-create
        STATUS      current
        DESCRIPTION
            "The status column used for creating, modifying, and deleting entries of the VLAN table."
        ::= { dhcpSnpConfigVlanEntry 2 }

-- DHCP Snooping VLAN Table Configuration End

-- DHCP Snooping Port Table Configuration Start

    dhcpSnpConfigPortTable OBJECT-TYPE
        SYNTAX SEQUENCE OF DhcpSnpConfigPortEntry
        MAX-ACCESS not-accessible
        STATUS current
        DESCRIPTION
            "A table to store the port specific parameters for DHCP Snooping."
        ::= { dhcpSnpConfiguration 3 }

    dhcpSnpConfigPortEntry OBJECT-TYPE
        SYNTAX DhcpSnpConfigPortEntry
        MAX-ACCESS not-accessible
        STATUS current
        DESCRIPTION
            "An entry appears in this Port Table represent port information about
            Dhcp Snooping Mode."
        INDEX { dhcpSnpConfigPortNum }
        ::= { dhcpSnpConfigPortTable 1 }

    DhcpSnpConfigPortEntry ::=
        SEQUENCE {
            dhcpSnpConfigPortNum
                Integer32,
            dhcpSnpConfigPortStatus
                INTEGER
    }

    dhcpSnpConfigPortNum OBJECT-TYPE
        SYNTAX Integer32 (1..256)
        MAX-ACCESS read-only
        STATUS current
        DESCRIPTION
            "A unique value, greater than zero, indicating the Port number of
             port configuration table."
        ::= { dhcpSnpConfigPortEntry 1 }

    dhcpSnpConfigPortStatus OBJECT-TYPE
        SYNTAX INTEGER {
                    trusted(1),
                    untrusted(2)
                }
        MAX-ACCESS read-write
        STATUS current
        DESCRIPTION
            "The port status value of the DHCP Snooping Port."
        ::= { dhcpSnpConfigPortEntry 2 }

-- DHCP Snooping Port Table Configuration End

-- DHCP Snooping Static Binding Table Configuration Start

    dhcpSnpConfigStaticBindingTable OBJECT-TYPE
        SYNTAX  SEQUENCE OF DhcpSnpConfigStaticBindingEntry
        MAX-ACCESS      not-accessible
        STATUS          current
        DESCRIPTION
            "This table contains the static Host IP configuration
             information."
    ::= { dhcpSnpConfiguration 4}

    dhcpSnpConfigStaticBindingEntry OBJECT-TYPE
        SYNTAX DhcpSnpConfigStaticBindingEntry
        MAX-ACCESS      not-accessible
        STATUS          current
        DESCRIPTION
            "A single entry contains the binding information of a single
             host connected to the system."
        INDEX { dhcpSnpConfigStaticHostIndex }
    ::= { dhcpSnpConfigStaticBindingTable 1 }

    DhcpSnpConfigStaticBindingEntry ::= SEQUENCE {
        dhcpSnpConfigStaticHostIndex       Integer32,
        dhcpSnpConfigStaticHostVlanId      Integer32,
        dhcpSnpConfigStaticHostMac         MacAddress,
        dhcpSnpConfigStaticHostIp          IpAddress,
        dhcpSnpConfigStaticInIfIndex       Integer32,
        dhcpSnpConfigStaticBindingStatus   RowStatus
    }

    dhcpSnpConfigStaticHostIndex OBJECT-TYPE
        SYNTAX      Integer32 (1..32)
        MAX-ACCESS  not-accessible
        STATUS      current
        DESCRIPTION
            "Index of static ip binding in table."
        ::= { dhcpSnpConfigStaticBindingEntry 1 }

    dhcpSnpConfigStaticHostVlanId OBJECT-TYPE
        SYNTAX      Integer32 (1..4094)
        MAX-ACCESS  read-write
        STATUS      current
        DESCRIPTION
            "The VLAN ID to which the host belongs. This is an index of
             the table."
    ::= { dhcpSnpConfigStaticBindingEntry 2 }

    dhcpSnpConfigStaticHostMac OBJECT-TYPE
        SYNTAX      MacAddress
        MAX-ACCESS  read-write
        STATUS      current
        DESCRIPTION
            "MAC address of the Host. This is an index of the table."
    ::= { dhcpSnpConfigStaticBindingEntry 3 }

    dhcpSnpConfigStaticHostIp OBJECT-TYPE
        SYNTAX      IpAddress
        MAX-ACCESS  read-write
        STATUS      current
        DESCRIPTION
            "IP address of the Host."
    ::= { dhcpSnpConfigStaticBindingEntry 4 }

    dhcpSnpConfigStaticInIfIndex OBJECT-TYPE
        SYNTAX      Integer32
        MAX-ACCESS  read-write
        STATUS      current
        DESCRIPTION
            "Indicates the interface to which the host is connected."
    ::= { dhcpSnpConfigStaticBindingEntry 5 }

    dhcpSnpConfigStaticBindingStatus OBJECT-TYPE
        SYNTAX      RowStatus
        MAX-ACCESS  read-create
        STATUS      current
        DESCRIPTION
            "The rowstatus of the binding table entry. All the objects in the
             table must be filled before making the rowstatus as active."
    ::= { dhcpSnpConfigStaticBindingEntry 6 }

-- DHCP Snooping Static Binding Table Configuration End

-- -------------------------------------------------------------
-- Status group
-- -------------------------------------------------------------

-- DHCP Snooping Binding Table Start

    dhcpSnpStatBindingTable OBJECT-TYPE
        SYNTAX  SEQUENCE OF DhcpSnpStatBindingEntry
        MAX-ACCESS      not-accessible
        STATUS          current
        DESCRIPTION
            "This table contains the information about all the hosts connected
             to the system, their MAC Address, VLAN, IP etc."
    ::= { dhcpSnpStatus 1}

    dhcpSnpStatBindingEntry OBJECT-TYPE
        SYNTAX DhcpSnpStatBindingEntry
        MAX-ACCESS      not-accessible
        STATUS          current
        DESCRIPTION
            "A single entry contains the binding information of a single
             host connected to the system."
        INDEX {
                dhcpSnpStatHostVlanId,
                dhcpSnpStatHostMac
              }
    ::= { dhcpSnpStatBindingTable 1 }

    DhcpSnpStatBindingEntry ::= SEQUENCE {
        dhcpSnpStatHostVlanId        Integer32,
        dhcpSnpStatHostMac           MacAddress,
        dhcpSnpStatHostBindingType   INTEGER,
        dhcpSnpStatHostIp            IpAddress,
        dhcpSnpStatHostInIfIndex     Integer32,
        dhcpSnpStatHostRemLeaseTime  Integer32
    }

    dhcpSnpStatHostVlanId OBJECT-TYPE
        SYNTAX      Integer32 (1..4094)
        MAX-ACCESS  read-only
        STATUS      current
        DESCRIPTION
            "The VLAN ID to which the host belongs. This is an index of
             the table."
    ::= { dhcpSnpStatBindingEntry 1 }

    dhcpSnpStatHostMac OBJECT-TYPE
        SYNTAX      MacAddress
        MAX-ACCESS  read-only
        STATUS      current
        DESCRIPTION
            "MAC address of the Host. This is an index of the table."
    ::= { dhcpSnpStatBindingEntry 2 }

    dhcpSnpStatHostBindingType OBJECT-TYPE
        SYNTAX      INTEGER { static (1), dhcp (2)}
        MAX-ACCESS  read-only
        STATUS      current
        DESCRIPTION
            "Specifies whether the entry was configured through static
            or dynamically learnt through DHCP or PPP."
    ::= { dhcpSnpStatBindingEntry 3 }

    dhcpSnpStatHostIp OBJECT-TYPE
        SYNTAX      IpAddress
        MAX-ACCESS  read-only
        STATUS      current
        DESCRIPTION
            "IP address of the Host."
    ::= { dhcpSnpStatBindingEntry 4 }

    dhcpSnpStatHostInIfIndex OBJECT-TYPE
        SYNTAX      Integer32
        MAX-ACCESS  read-only
        STATUS      current
        DESCRIPTION
            "Indicates the interface to which the host is connected."
    ::= { dhcpSnpStatBindingEntry 5 }

    dhcpSnpStatHostRemLeaseTime OBJECT-TYPE
        SYNTAX      Integer32
        MAX-ACCESS  read-only
        STATUS      current
        DESCRIPTION
            "The Remaining lease time in seconds for the (host, IP) binding.
             Applicable only if the fsIpDbBindingType is DHCP."
    ::= { dhcpSnpStatBindingEntry 6 }

-- DHCP Snooping Binding Table End

-- DHCP Snooping Interface Table Start

    dhcpSnpStatInterfaceTable OBJECT-TYPE
        SYNTAX  SEQUENCE OF DhcpSnpStatInterfaceEntry
        MAX-ACCESS      not-accessible
        STATUS          current
        DESCRIPTION
            "This table contains the configuration & statistics collection
            parameters of DHCP snooping on a specific VLAN."
    ::= { dhcpSnpStatus 2}

    dhcpSnpStatInterfaceEntry OBJECT-TYPE
        SYNTAX DhcpSnpStatInterfaceEntry
        MAX-ACCESS      not-accessible
        STATUS          current
        DESCRIPTION
            "Each row instance gives the DHCP snooping status on VLAN and the
         statistics collected in that VLAN for the DHCP snooping module"
        INDEX { dhcpSnpStatInterfaceVlanId }
    ::= { dhcpSnpStatInterfaceTable 1 }

    DhcpSnpStatInterfaceEntry ::= SEQUENCE {
        dhcpSnpStatInterfaceVlanId             Integer32,
        dhcpSnpStatInterfaceNoOfDiscards       Counter32,
        dhcpSnpStatInterfaceMacDiscards        Counter32,
        dhcpSnpStatInterfaceServerDiscards     Counter32
    }

    dhcpSnpStatInterfaceVlanId OBJECT-TYPE
        SYNTAX      Integer32 (1..4094)
        MAX-ACCESS  read-only
        STATUS      current
        DESCRIPTION
            "Vlan ID of the VLAN to which this table-entry is associated."
    ::= { dhcpSnpStatInterfaceEntry 1 }

    dhcpSnpStatInterfaceNoOfDiscards OBJECT-TYPE
        SYNTAX      Counter32
        MAX-ACCESS  read-only
        STATUS      current
        DESCRIPTION
            "Indicates the total number of DHCP packets from hosts dropped
             on this VLAN."
    ::= { dhcpSnpStatInterfaceEntry 2 }

    dhcpSnpStatInterfaceMacDiscards OBJECT-TYPE
        SYNTAX      Counter32
        MAX-ACCESS  read-only
        STATUS      current
        DESCRIPTION
            "Indicates the total number of DHCP packets from hosts dropped
             due to failure in MAC Address verification."
    ::= { dhcpSnpStatInterfaceEntry 3 }

    dhcpSnpStatInterfaceServerDiscards OBJECT-TYPE
        SYNTAX      Counter32
        MAX-ACCESS  read-only
        STATUS      current
        DESCRIPTION
            "Indicates the total number of DHCP packets from hosts dropped
             because they are supposed to be the messages from a server.
             The DHCP packets so dropped will include DHCP ACK, DHCP NAK and
             DHCP OFFERs received from untrusted host ports."
    ::= { dhcpSnpStatInterfaceEntry 4 }

-- DHCP Snooping Interface Table End

-- -------------------------------------------------------------
-- Notification group
-- -------------------------------------------------------------

    dhcpSnpNotifyMacDiscard NOTIFICATION-TYPE
        OBJECTS    { dhcpSnpStatInterfaceVlanId, dhcpSnpStatInterfaceMacDiscards }
        STATUS     current
        DESCRIPTION
            "The dhcpSnpNotifyMacDiscard notification is sent when packet droped by mac
            verification."
        ::= { dhcpSnpNotification 1 }

    dhcpSnpNotifyServerDiscard NOTIFICATION-TYPE
        OBJECTS    { dhcpSnpStatInterfaceVlanId, dhcpSnpStatInterfaceServerDiscards }
        STATUS     current
        DESCRIPTION
            "The dhcpSnpNotifyServerDiscard notification is sent when packet from server
            was droped."
        ::= { dhcpSnpNotification 2 }


END
