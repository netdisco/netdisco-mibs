-- ****************************************************************
-- *  Moxa General (Time) - PTP PRIVATE MIB
-- *
-- *  Copyright (c) 2021 by Moxa Inc.
-- *  All rights reserved.
-- *****************************************************************

MOXA-IEC-61850-9-3-PROFILE-MIB DEFINITIONS ::= BEGIN
    IMPORTS
        MODULE-IDENTITY, NOTIFICATION-TYPE, OBJECT-TYPE, OBJECT-IDENTITY, Gauge32, Unsigned32, Counter32, Counter64, mib-2, Integer32
            FROM SNMPv2-SMI
        TEXTUAL-CONVENTION, DateAndTime, DisplayString, TruthValue, AutonomousType
            FROM SNMPv2-TC
        OBJECT-GROUP, MODULE-COMPLIANCE
            FROM SNMPv2-CONF
        time
            FROM MOXA-GENERAL-MIB
        InterfaceIndexOrZero
            FROM IF-MIB
        PtpClockDomainType, PtpClockIdentity, PtpClockInstanceType, PtpClockIntervalBase2, PtpClockMechanismType, PtpClockPortNumber, PtpClockPortTransportTypeAddress, PtpClockProfileType, PtpClockQualityAccuracyType, PtpClockQualityClassType, PtpClockRoleType, PtpClockStateType, PtpClockTimeInterval, PtpClockTimeSourceType, PtpClockTxModeType, PtpClockType
            FROM PTPBASE-MIB;

    mxIec6185093Profile MODULE-IDENTITY
        LAST-UPDATED "202210190000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa IEC 61850-9-3-2016 Profile"

        REVISION    "202312010000Z"
        DESCRIPTION
            "
            Modified objects:
                iec6185093ConfigClockDefaultDSMaximumStepsRemoved
            "

        REVISION    "202210190000Z"
        DESCRIPTION 
            "
            Modified objects:
                iec6185093StatClockPortRunningState
            "

        REVISION    "202111030000Z"
        DESCRIPTION "Initial Revision"

        ::= { time 5 }

-- -------------------------------------------------------------
-- groups in the MOXA-IEC-61850-9-3-PROFILE-MIB MIB
-- -------------------------------------------------------------
    -- iec6185093Notification       OBJECT IDENTIFIER ::= { mxIec6185093Profile 0 }
    iec6185093Configuration         OBJECT IDENTIFIER ::= { mxIec6185093Profile 1 }
    iec6185093Status                OBJECT IDENTIFIER ::= { mxIec6185093Profile 2 }
    -- iec6185093Extensions         OBJECT IDENTIFIER ::= { mxIec6185093Profile 3 }

-- -------------------------------------------------------------
-- configuration group
-- -------------------------------------------------------------
-----------------------
-- IEC 61850-9-3 2016 -- 
-----------------------
    iec6185093ConfigClock  OBJECT IDENTIFIER
        ::= { iec6185093Configuration 1 }

    iec6185093ConfigClockDefaultDSTable OBJECT-TYPE
        SYNTAX          SEQUENCE OF Iec6185093ConfigClockDefaultDSEntry
        MAX-ACCESS      not-accessible
        STATUS          current
        DESCRIPTION
                "Table of information about the PTP clock defaultDS for
                 all domains."
        ::= { iec6185093ConfigClock 1 }

    iec6185093ConfigClockDefaultDSEntry OBJECT-TYPE
        SYNTAX          Iec6185093ConfigClockDefaultDSEntry
        MAX-ACCESS      not-accessible
        STATUS          current
        DESCRIPTION
                "A table entry that contains information about a single
                 PTP clock defaultDS for a domain."
        INDEX  { iec6185093ConfigClockDefaultDSInstanceIndex }
        ::= { iec6185093ConfigClockDefaultDSTable 1 }

    Iec6185093ConfigClockDefaultDSEntry ::= 
        SEQUENCE {
            iec6185093ConfigClockDefaultDSInstanceIndex       PtpClockInstanceType,
            iec6185093ConfigClockDefaultDSClockType           PtpClockType,
            iec6185093ConfigClockDefaultDSDomainNumber        PtpClockDomainType,
            iec6185093ConfigClockDefaultDSTwoStepFlag         TruthValue,
            iec6185093ConfigClockDefaultDSClockIdentity       PtpClockIdentity,
            iec6185093ConfigClockDefaultDSPriority1           Unsigned32,
            iec6185093ConfigClockDefaultDSPriority2           Unsigned32,
            iec6185093ConfigClockDefaultDSQualityClass        PtpClockQualityClassType,
            iec6185093ConfigClockDefaultDSQualityAccuracy     PtpClockQualityAccuracyType,
            iec6185093ConfigClockDefaultDSMaximumStepsRemoved Unsigned32,
            iec6185093ConfigClockDefaultDSAccuracyAlert       Unsigned32
        }

    iec6185093ConfigClockDefaultDSInstanceIndex OBJECT-TYPE
        SYNTAX          PtpClockInstanceType
        MAX-ACCESS      not-accessible
        STATUS          current
        DESCRIPTION
                "This object specifies the instance of the clock for this clock
                 type in the given domain."
        ::= { iec6185093ConfigClockDefaultDSEntry 1 }

    iec6185093ConfigClockDefaultDSClockType OBJECT-TYPE
        SYNTAX          PtpClockType
        MAX-ACCESS      read-write
        STATUS          current
        DESCRIPTION
                "This object specifies the clock type as defined in the
                 textual convention description."
        ::= { iec6185093ConfigClockDefaultDSEntry 2 }

    iec6185093ConfigClockDefaultDSDomainNumber OBJECT-TYPE
        SYNTAX          PtpClockDomainType
        MAX-ACCESS      read-write
        STATUS          current
        DESCRIPTION
                "This object specifies the domain number used to create a
                 logical group of PTP devices."
        ::= { iec6185093ConfigClockDefaultDSEntry 3 }

    iec6185093ConfigClockDefaultDSTwoStepFlag OBJECT-TYPE
        SYNTAX          TruthValue
        MAX-ACCESS      read-write
        STATUS          current
        DESCRIPTION
                "This object specifies whether the two-step process is used."
        ::= { iec6185093ConfigClockDefaultDSEntry 4 }

    iec6185093ConfigClockDefaultDSClockIdentity OBJECT-TYPE
        SYNTAX          PtpClockIdentity
        MAX-ACCESS      read-only
        STATUS          current
        DESCRIPTION
                "This object specifies the defaultDS clockIdentity member."
        ::= { iec6185093ConfigClockDefaultDSEntry 5 }

    iec6185093ConfigClockDefaultDSPriority1 OBJECT-TYPE
        SYNTAX          Unsigned32 (0..255)
        MAX-ACCESS      read-write
        STATUS          current
        DESCRIPTION
                "This object specifies the defaultDS priority1 member."
        ::= { iec6185093ConfigClockDefaultDSEntry 6 }

    iec6185093ConfigClockDefaultDSPriority2 OBJECT-TYPE
        SYNTAX          Unsigned32 (0..255)
        MAX-ACCESS      read-write
        STATUS          current
        DESCRIPTION
                "This object specifies the defaultDS priority2 member."
        ::= { iec6185093ConfigClockDefaultDSEntry 7 }

    iec6185093ConfigClockDefaultDSQualityClass OBJECT-TYPE
        SYNTAX          PtpClockQualityClassType
        MAX-ACCESS      read-only
        STATUS          current
        DESCRIPTION
                "This object specifies the defaultDS Quality Class."
        ::= { iec6185093ConfigClockDefaultDSEntry 8 }

    iec6185093ConfigClockDefaultDSQualityAccuracy OBJECT-TYPE
        SYNTAX          PtpClockQualityAccuracyType
        MAX-ACCESS      read-only
        STATUS          current
        DESCRIPTION
                "This object specifies the defaultDS Quality Accuracy."
        ::= { iec6185093ConfigClockDefaultDSEntry 9 }

    iec6185093ConfigClockDefaultDSMaximumStepsRemoved OBJECT-TYPE
        SYNTAX          Unsigned32 (2..255)
        MAX-ACCESS      read-write
        STATUS          current
        DESCRIPTION
                "This object specifies the defaultDS Maximum Steps Removed."
        ::= { iec6185093ConfigClockDefaultDSEntry 10 }

    iec6185093ConfigClockDefaultDSAccuracyAlert OBJECT-TYPE
        SYNTAX          Unsigned32 (50..250000000)
        MAX-ACCESS      read-write
        STATUS          current
        DESCRIPTION
                "This object specifies the defaultDS Accuracy Alert."
        ::= { iec6185093ConfigClockDefaultDSEntry 11 }

    iec6185093ConfigClockPortDSTable OBJECT-TYPE
        SYNTAX          SEQUENCE OF Iec6185093ConfigClockPortDSEntry
        MAX-ACCESS      not-accessible
        STATUS          current
        DESCRIPTION
                "Table of information about the clock's portDS for a
                 particular domain."
        ::= { iec6185093ConfigClock 2 }

    iec6185093ConfigClockPortDSEntry OBJECT-TYPE
        SYNTAX          Iec6185093ConfigClockPortDSEntry
        MAX-ACCESS      not-accessible
        STATUS          current
        DESCRIPTION
                "A table entry that contains portDS information for
                 a single clock port."
        INDEX { iec6185093ConfigClockPortDSPortNumberIndex }
        ::= { iec6185093ConfigClockPortDSTable 1 }

    Iec6185093ConfigClockPortDSEntry ::= 
        SEQUENCE {
            iec6185093ConfigClockPortDSPortNumberIndex      PtpClockPortNumber,
            iec6185093ConfigClockPortDSPortIdentity         OCTET STRING,
            iec6185093ConfigClockPortDSlogAnnouncementInterval PtpClockIntervalBase2,
            iec6185093ConfigClockPortDSAnnounceRctTimeout   Integer32,
            iec6185093ConfigClockPortDSlogSyncInterval      PtpClockIntervalBase2,
            iec6185093ConfigClockPortDSMinDelayReqInterval  Integer32,
            iec6185093ConfigClockPortDSPeerDelayReqInterval Integer32,
            iec6185093ConfigClockPortDSDelayMech            PtpClockMechanismType,
            iec6185093ConfigClockPortDSEnabled              TruthValue 
        }

    iec6185093ConfigClockPortDSPortNumberIndex OBJECT-TYPE
        SYNTAX          PtpClockPortNumber
        MAX-ACCESS      not-accessible
        STATUS          current
        DESCRIPTION
                "This object specifies the PTP portNumber associated with this
                 PTP port."
        ::= { iec6185093ConfigClockPortDSEntry 1 }

    iec6185093ConfigClockPortDSPortIdentity OBJECT-TYPE
        SYNTAX          OCTET STRING(SIZE(1..256))
        MAX-ACCESS      read-only
        STATUS          current
        DESCRIPTION
                "This object specifies the PTP clock port Identity."
        ::= { iec6185093ConfigClockPortDSEntry 2 }

    iec6185093ConfigClockPortDSlogAnnouncementInterval OBJECT-TYPE
        SYNTAX          PtpClockIntervalBase2
        UNITS           "Time Interval"
        MAX-ACCESS      read-only
        STATUS          current
        DESCRIPTION
                "This object specifies the Announce message transmission
                 interval associated with this clock port."
        ::= { iec6185093ConfigClockPortDSEntry 3 }

    iec6185093ConfigClockPortDSAnnounceRctTimeout OBJECT-TYPE
        SYNTAX          Integer32
        MAX-ACCESS      read-only
        STATUS          current
        DESCRIPTION
                "This object specifies the Announce receipt timeout associated
                 with this clock port."
        ::= { iec6185093ConfigClockPortDSEntry 4 }

    iec6185093ConfigClockPortDSlogSyncInterval OBJECT-TYPE
        SYNTAX          PtpClockIntervalBase2
        UNITS           "Time Interval"
        MAX-ACCESS      read-only
        STATUS          current
        DESCRIPTION
                "This object specifies the Sync message transmission interval."
        ::= { iec6185093ConfigClockPortDSEntry 5 }

    iec6185093ConfigClockPortDSMinDelayReqInterval OBJECT-TYPE
        SYNTAX          Integer32
        MAX-ACCESS      read-only
        STATUS          current
        DESCRIPTION
                "This object specifies the Delay_Req message transmission
                 interval."
        ::= { iec6185093ConfigClockPortDSEntry 6 }

    iec6185093ConfigClockPortDSPeerDelayReqInterval OBJECT-TYPE
        SYNTAX          Integer32
        MAX-ACCESS      read-only
        STATUS          current
        DESCRIPTION
                "This object specifies the Pdelay_Req message transmission
                 interval."
        ::= { iec6185093ConfigClockPortDSEntry 7 }

    iec6185093ConfigClockPortDSDelayMech OBJECT-TYPE
        SYNTAX          PtpClockMechanismType
        MAX-ACCESS      read-only
        STATUS          current
        DESCRIPTION
                "This object specifies the delay mechanism used.  If the clock
                 is an end-to-end clock, the value is e2e; if the
                 clock is a peer to-peer clock, the value is p2p."
        ::= { iec6185093ConfigClockPortDSEntry 8 }

    iec6185093ConfigClockPortDSEnabled OBJECT-TYPE
        SYNTAX          TruthValue
        MAX-ACCESS      read-write
        STATUS          current
        DESCRIPTION
                "True if port is enabled."
        DEFVAL { false }
        ::= { iec6185093ConfigClockPortDSEntry 9 }

    iec6185093ConfigTransportType OBJECT-TYPE
        SYNTAX  INTEGER {
                    udpipv4 (1),
                    udpipv6 (2),
                    ieee8023 (3),
                    devicenet (4),
                    controlnet (5),
                    profitnet (6),
                    ieee8021 (7),
                    unknown (65534)
                }
        MAX-ACCESS read-only
        STATUS     current 
        DESCRIPTION
                "This denotes the type of the interface. PTP port bears a seperate 
                 meaning than the one that are normally defined in interface mibs.
                 PTP can run over physical interfaces, VLAN identifiers or IVR
                 interfaces. Hence this object needs to be configured before making
                 this particular row as ACTIVE.
                 Only values UDP/IPv4, UDP/IPv6, IEEE802.3 are supported. IEEE8021 
                 corresponds to layer 2 Vlan."
        ::= { iec6185093ConfigClock 3 }

-- -------------------------------------------------------------
-- status group
-- -------------------------------------------------------------
---------------
-- IEC 61850-9-3 2016 -- 
---------------

    iec6185093StatClock  OBJECT IDENTIFIER
        ::= { iec6185093Status 1 }

    iec6185093StatClockCurrentDSTable OBJECT-TYPE
        SYNTAX          SEQUENCE OF Iec6185093StatClockCurrentDSEntry
        MAX-ACCESS      not-accessible
        STATUS          current
        DESCRIPTION
                "Table of information about the PTP clock currentDS for
                 all domains."
        ::= { iec6185093StatClock 1 }

    iec6185093StatClockCurrentDSEntry OBJECT-TYPE
        SYNTAX          Iec6185093StatClockCurrentDSEntry
        MAX-ACCESS      not-accessible
        STATUS          current
        DESCRIPTION
                "A table entry that contains information about a single
                 PTP clock currentDS for a domain."
        REFERENCE
                "Section 8.2.2 ('currentDS data set member
                 specifications') of [IEEE-1588-2008]"
        INDEX { iec6185093StatClockCurrentDSInstanceIndex }
        ::= { iec6185093StatClockCurrentDSTable 1 }

    Iec6185093StatClockCurrentDSEntry ::=
        SEQUENCE {
            iec6185093StatClockCurrentDSInstanceIndex    PtpClockInstanceType,
            iec6185093StatClockCurrentDSStepsRemoved     Unsigned32,
            iec6185093StatClockCurrentDSOffsetFromMaster PtpClockTimeInterval,
            iec6185093StatClockCurrentDSMeanPathDelay    PtpClockTimeInterval,
            iec6185093StatClockCurrentDSSyncStatus       Unsigned32,
            iec6185093StatClockCurrentDSSlavePort        Integer32,
            iec6185093StatClockCurrentDSClockTime        DisplayString
        }

    iec6185093StatClockCurrentDSInstanceIndex OBJECT-TYPE
        SYNTAX          PtpClockInstanceType
        MAX-ACCESS      not-accessible
        STATUS          current
        DESCRIPTION
                "This object specifies the instance of the clock for this clock
                 type in the given domain."
        ::= { iec6185093StatClockCurrentDSEntry 1 }

    iec6185093StatClockCurrentDSStepsRemoved OBJECT-TYPE
        SYNTAX          Unsigned32
        UNITS           "Steps"
        MAX-ACCESS      read-only
        STATUS          current
        DESCRIPTION
                "The current clock dataset stepsRemoved value.

                 This object specifies the distance measured by the number of
                 boundary clocks between the local clock and the foreign master
                 as indicated in the stepsRemoved field of Announce messages."
        REFERENCE
                "Section 8.2.2.2 ('stepsRemoved') of [IEEE-1588-2008]"
        ::= { iec6185093StatClockCurrentDSEntry 2 }

    iec6185093StatClockCurrentDSOffsetFromMaster OBJECT-TYPE
        SYNTAX          PtpClockTimeInterval
        UNITS           "Time Interval"
        MAX-ACCESS      read-only
        STATUS          current
        DESCRIPTION
                "This object specifies the current clock dataset ClockOffset
                 value.  The value of the computation of the offset in time
                 between a slave and a master clock."
        REFERENCE
                "Section 8.2.2.3 ('currentDS.offsetFromMaster')
                 of [IEEE-1588-2008]"
        ::= { iec6185093StatClockCurrentDSEntry 3 }

    iec6185093StatClockCurrentDSMeanPathDelay OBJECT-TYPE
        SYNTAX          PtpClockTimeInterval
        UNITS           "Time Interval"
        MAX-ACCESS      read-only
        STATUS          current
        DESCRIPTION
                "This object specifies the current clock dataset
                 MeanPathDelay value.

                 The mean path delay between a pair of ports as measured by the
                 delay request-response mechanism."
        REFERENCE
                "Section 8.2.2.4 ('currentDS.meanPathDelay')
                 of [IEEE-1588-2008]"
        ::= { iec6185093StatClockCurrentDSEntry 4 }


    iec6185093StatClockCurrentDSSyncStatus OBJECT-TYPE
        SYNTAX          Unsigned32
        MAX-ACCESS      read-only
        STATUS          current
        DESCRIPTION
                "A value of 'DISABLED' (0) indicates that the ptp function is 
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 1 }
        ::= { iec6185093StatClockCurrentDSEntry 5 }

    iec6185093StatClockCurrentDSSlavePort OBJECT-TYPE
        SYNTAX          Integer32(1..255)
        MAX-ACCESS      read-only
        STATUS          current
        DESCRIPTION
                "Indicate the port which is in the SLAVE state."
        ::= { iec6185093StatClockCurrentDSEntry 6 }

    iec6185093StatClockCurrentDSClockTime OBJECT-TYPE
        SYNTAX          DisplayString
        MAX-ACCESS      read-only
        STATUS          current
        DESCRIPTION
                "Indicate the PTP Clock Time."
        ::= { iec6185093StatClockCurrentDSEntry 7 }

    iec6185093StatClockParentDSTable OBJECT-TYPE
        SYNTAX          SEQUENCE OF Iec6185093StatClockParentDSEntry
        MAX-ACCESS      not-accessible
        STATUS          current
        DESCRIPTION
                "Table of information about the PTP clock parentDS for
                 all domains."
        ::= { iec6185093StatClock 2 }

    iec6185093StatClockParentDSEntry OBJECT-TYPE
        SYNTAX          Iec6185093StatClockParentDSEntry
        MAX-ACCESS      not-accessible
        STATUS          current
        DESCRIPTION
                "A table entry that contains information about a single
                 PTP clock parentDS for a domain."
        REFERENCE
                "Section 8.2.3 ('parentDS data set member specifications') of
                 [IEEE-1588-2008]"
        INDEX { iec6185093StatClockParentDSInstanceIndex }
        ::= { iec6185093StatClockParentDSTable 1 }

    Iec6185093StatClockParentDSEntry ::=
        SEQUENCE {
            iec6185093StatClockParentDSInstanceIndex          PtpClockInstanceType,
            iec6185093StatClockParentDSParentPortIdentity     OCTET STRING,
            iec6185093StatClockParentDSGMClockIdentity        PtpClockIdentity,
            iec6185093StatClockParentDSGMClockPriority1       Unsigned32,
            iec6185093StatClockParentDSGMClockPriority2       Unsigned32,
            iec6185093StatClockParentDSGMClockQualityClass    PtpClockQualityClassType,
            iec6185093StatClockParentDSGMClockQualityAccuracy PtpClockQualityAccuracyType,
            iec6185093StatClockParentDSParentPortNumber       PtpClockPortNumber
        }

    iec6185093StatClockParentDSInstanceIndex OBJECT-TYPE
        SYNTAX          PtpClockInstanceType
        MAX-ACCESS      not-accessible
        STATUS          current
        DESCRIPTION
                "This object specifies the instance of the clock for this clock
                 type in the given domain."
        ::= { iec6185093StatClockParentDSEntry 1 }

    iec6185093StatClockParentDSParentPortIdentity OBJECT-TYPE
        SYNTAX          OCTET STRING(SIZE(1..256))
        MAX-ACCESS      read-only
        STATUS          current
        DESCRIPTION
                "This object specifies the value of portIdentity of the port on
                 the master that issues the Sync messages used in synchronizing
                 this clock."
        REFERENCE
                "Section 8.2.3.2 ('parentDS.parentPortIdentity') of
                 [IEEE-1588-2008]"
        ::= { iec6185093StatClockParentDSEntry 2 }

    iec6185093StatClockParentDSGMClockIdentity OBJECT-TYPE
        SYNTAX          PtpClockIdentity
        MAX-ACCESS      read-only
        STATUS          current
        DESCRIPTION
                "This object specifies the parentDS grandmaster clock
                 identity."
        REFERENCE
                "Section 8.2.3.6 ('parentDS.grandmasterIdentity') of
                 [IEEE-1588-2008]"
        ::= { iec6185093StatClockParentDSEntry 3 }

    iec6185093StatClockParentDSGMClockPriority1 OBJECT-TYPE
        SYNTAX          Unsigned32
        MAX-ACCESS      read-only
        STATUS          current
        DESCRIPTION
                "This object specifies the parentDS grandmaster clock
                 priority1."
        REFERENCE
                "Section 8.2.3.8 ('parentDS.grandmasterPriority1') of
                 [IEEE-1588-2008]"
        ::= { iec6185093StatClockParentDSEntry 4 }

    iec6185093StatClockParentDSGMClockPriority2 OBJECT-TYPE
        SYNTAX          Unsigned32
        MAX-ACCESS      read-only
        STATUS          current
        DESCRIPTION
                "This object specifies the parentDS grandmaster clock
                 priority2."
        REFERENCE
                "Section 8.2.3.9 ('parentDS.grandmasterPriority2') of
                 [IEEE-1588-2008]"
        ::= { iec6185093StatClockParentDSEntry 5 }

    iec6185093StatClockParentDSGMClockQualityClass OBJECT-TYPE
        SYNTAX          PtpClockQualityClassType
        MAX-ACCESS      read-only
        STATUS          current
        DESCRIPTION
                "This object specifies the parentDS grandmaster clock
                 quality class."
        REFERENCE
                "Section 8.2.3.7 ('parentDS.grandmasterClockQuality') of
                 [IEEE-1588-2008]"
        ::= { iec6185093StatClockParentDSEntry 6 }

    iec6185093StatClockParentDSGMClockQualityAccuracy OBJECT-TYPE
        SYNTAX          PtpClockQualityAccuracyType
        MAX-ACCESS      read-only
        STATUS          current
        DESCRIPTION
                "This object specifies the parentDS grandmaster clock
                 quality accuracy."
        REFERENCE
                "Section 8.2.3.7 ('parentDS.grandmasterClockQuality') of
                 [IEEE-1588-2008]"
        ::= { iec6185093StatClockParentDSEntry 7 }

    iec6185093StatClockParentDSParentPortNumber OBJECT-TYPE
        SYNTAX          PtpClockPortNumber
        MAX-ACCESS      read-only
        STATUS          current
        DESCRIPTION
                "This object specifies the parentDS PTP portNumber"
        ::= { iec6185093StatClockParentDSEntry 8 }

    iec6185093StatClockPortRunningTable OBJECT-TYPE
        SYNTAX          SEQUENCE OF Iec6185093StatClockPortRunningEntry
        MAX-ACCESS      not-accessible
        STATUS          current
        DESCRIPTION
                "Table of information about the clock ports running datasets for
                 a particular domain."
        ::= { iec6185093StatClock 3 }

    iec6185093StatClockPortRunningEntry OBJECT-TYPE
        SYNTAX          Iec6185093StatClockPortRunningEntry
        MAX-ACCESS      not-accessible
        STATUS          current
        DESCRIPTION
                "A table entry that contains running dataset information
                 about a single clock port."
        INDEX { iec6185093StatClockPortRunningPortNumberIndex }
        ::= { iec6185093StatClockPortRunningTable 1 }

    Iec6185093StatClockPortRunningEntry ::=
        SEQUENCE {
            iec6185093StatClockPortRunningPortNumberIndex    PtpClockPortNumber,
            iec6185093StatClockPortRunningState              INTEGER,
            iec6185093StatClockPortRunningPeerMeanPathDelay  PtpClockTimeInterval
        }

    iec6185093StatClockPortRunningPortNumberIndex OBJECT-TYPE
        SYNTAX          PtpClockPortNumber
        MAX-ACCESS      not-accessible
        STATUS          current
        DESCRIPTION
                "This object specifies the PTP portNumber associated with this
                 clock port."
        ::= { iec6185093StatClockPortRunningEntry 1 }

    iec6185093StatClockPortRunningState OBJECT-TYPE
        SYNTAX          INTEGER  {
                            initializing(1),
                            faulty(2),
                            disabled(3),
                            listening(4),
                            preMaster(5),
                            master(6),
                            passive(7),
                            uncalibrated(8),
                            slave(9),
                            TransmittingSynchronized(10),
                            ReceivingSynchronized (11)
                        }
        MAX-ACCESS      read-only
        STATUS          current
        DESCRIPTION
                "This object specifies the port state returned by PTP engine:

                initializing
                faulty
                disabled
                listening
                preMaster
                master
                passive
                uncalibrated
                slave
                TransmittingSynchronized
                ReceivingSynchronized       "
        ::= { iec6185093StatClockPortRunningEntry 2 }

    iec6185093StatClockPortRunningPeerMeanPathDelay OBJECT-TYPE
        SYNTAX          PtpClockTimeInterval
        UNITS           "Time Interval"
        MAX-ACCESS      read-only
        STATUS          current
        DESCRIPTION
                "This object specifies the peer meanPathDelay."
        ::= { iec6185093StatClockPortRunningEntry 3 }

END
