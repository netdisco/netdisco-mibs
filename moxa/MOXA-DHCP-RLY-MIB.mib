-- ****************************************************************
-- *  Moxa General (Network Configuration) - Dhcp Relay PRIVATE MIB
-- *
-- *  Copyright (c) 2021 by Moxa Inc.
-- *  All rights reserved.
-- *****************************************************************

MOXA-DHCP-RLY-MIB DEFINITIONS ::= BEGIN
    IMPORTS
        MODULE-IDENTITY, NOTIFICATION-TYPE,
        enterprises, OBJECT-TYPE, IpAddress, Integer32
            FROM SNMPv2-SMI
        TEXTUAL-CONVENTION, DateAndTime, MacAddress, DisplayString, TruthValue, RowStatus
            FROM SNMPv2-TC
        InetAddressIPv4
            FROM INET-ADDRESS-MIB
	    networkConfiguration
            FROM MOXA-GENERAL-MIB;

    mxDhcpRelay MODULE-IDENTITY
        LAST-UPDATED "202109030000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "

        DESCRIPTION
            "The MIB module defines Moxa DHCP Relay"

        REVISION    "202109030000Z"
        DESCRIPTION "Initial Revision"

        ::= { networkConfiguration 3 }

    moxa                 OBJECT IDENTIFIER ::= { enterprises 8691 }
    general              OBJECT IDENTIFIER ::= { moxa 602 }
    networkConfiguration OBJECT IDENTIFIER ::= { general 2 }

-- -------------------------------------------------------------
-- groups in the MOXA-DHCP-RLY-MIB MIB
-- -------------------------------------------------------------

  dhcpRelay                OBJECT IDENTIFIER ::= { mxDhcpRelay 1 }

-- -------------------------------------------------------------
-- DHCP Relay Global Config
-- -------------------------------------------------------------

    dhcpRelayGlobalEnable OBJECT-TYPE
        SYNTAX       TruthValue
        MAX-ACCESS   read-write
        STATUS       current
        DESCRIPTION
            "The relay status "
        ::= { dhcpRelay 1 }

    dhcpOp82RemoteIdType OBJECT-TYPE
        SYNTAX INTEGER {
                    ip(0),
                    mac(1),
                    client-id(2),
                    other(3)
                }

        MAX-ACCESS   read-write
        STATUS       current
        DESCRIPTION
            "The type of remote-id."
        ::= { dhcpRelay 2 }

    dhcpOp82RemoteIdValue OBJECT-TYPE
        SYNTAX       DisplayString
        MAX-ACCESS   read-write
        STATUS       current
        DESCRIPTION
            "The manual string of remote-id."
        ::= { dhcpRelay 3 }

-- DHCP Relay Server Table Configuration Start

    dhcpRelayServerTable   OBJECT-TYPE
        SYNTAX SEQUENCE OF DhcpRelayServerEntry
        MAX-ACCESS not-accessible
        STATUS current
        DESCRIPTION
            "This table contains the IP addresses of the DHCP Server
        to which the Relay Agent needs to forward the packets from
        the client. This object becomes active only when
        dhcpRelayServersOnly is enabled."
        ::= { dhcpRelay 4 }

    dhcpRelayServerEntry OBJECT-TYPE
        SYNTAX DhcpRelayServerEntry
        MAX-ACCESS not-accessible
        STATUS current
        DESCRIPTION
            "The entry of DHCP server"
        INDEX { dhcpRelayServerIpIndex }
        ::= { dhcpRelayServerTable 1 }


    DhcpRelayServerEntry ::=
        SEQUENCE {
            dhcpRelayServerIpIndex
                Integer32,
            dhcpRelayServerIpAddress
                InetAddressIPv4
        }

    dhcpRelayServerIpIndex OBJECT-TYPE
        SYNTAX     Integer32 (1..4)
        MAX-ACCESS read-only
        STATUS     current
        DESCRIPTION
            "The index of the DHCP server."
        ::= { dhcpRelayServerEntry 1 }

    dhcpRelayServerIpAddress OBJECT-TYPE
        SYNTAX     InetAddressIPv4
        MAX-ACCESS read-write
        STATUS     current
        DESCRIPTION
            "The IP Address of the DHCP server."
        ::=  { dhcpRelayServerEntry 2 }


-- DHCP Relay Server IP Address Table Configuration End

-- -------------------------------------------------------------
-- DHCP Relay Interface Config
-- -------------------------------------------------------------

    dhcpRelayPortTable OBJECT-TYPE
        SYNTAX SEQUENCE OF DhcpRelayPortEntry
        MAX-ACCESS not-accessible
        STATUS current
        DESCRIPTION
            "A table to store the port specific parameters for DHCP relay."
        ::= { dhcpRelay 5 }

    dhcpRelayPortEntry OBJECT-TYPE
        SYNTAX DhcpRelayPortEntry
        MAX-ACCESS not-accessible
        STATUS current
        DESCRIPTION
            "An entry appears in this Port Table represent port information about
            Dhcp Relay."
        INDEX { dhcpRelayPortNum }
        ::= { dhcpRelayPortTable 1 }

    DhcpRelayPortEntry ::=
        SEQUENCE {
            dhcpRelayPortNum
                Integer32,
            dhcpRelayPortEnable
                TruthValue,
            dhcpOp82PortEnable
                TruthValue,
            dhcpRelayPortTrust
                TruthValue
        }

    dhcpRelayPortNum OBJECT-TYPE
        SYNTAX     Integer32 (1..256)
        MAX-ACCESS read-only
        STATUS     current
        DESCRIPTION
            "A unique value, greater than zero, indicating the Port number of
             port configuration table."
        ::= { dhcpRelayPortEntry 1 }

    dhcpRelayPortEnable OBJECT-TYPE
        SYNTAX     TruthValue
        MAX-ACCESS read-write
        STATUS     current
        DESCRIPTION
            "This parameter when true(1) indicates that a port is relay enabled
            and false(2) indicates that this feature is disabled on the port."
        ::= { dhcpRelayPortEntry 2 }

    dhcpOp82PortEnable OBJECT-TYPE
        SYNTAX     TruthValue
        MAX-ACCESS read-write
        STATUS     current
        DESCRIPTION
            "This parameter when true(1) indicates that a port is option82 enabled
            and false(2) indicates that this feature is disabled on the port."
        ::= { dhcpRelayPortEntry 3 }

    dhcpRelayPortTrust OBJECT-TYPE
        SYNTAX     TruthValue
        MAX-ACCESS read-write
        STATUS     current
        DESCRIPTION
            "This parameter when true(1) indicates that a port is relay trusted mode
            and false(2) indicates that a port is relay untrusted mode ."
        ::= { dhcpRelayPortEntry 4 }

END
