-- *****************************************************************
-- *  Moxa General (Time) - Time Setting PRIVATE MIB
-- *
-- *  Copyright (c) 2019 by Moxa Inc.
-- *  All rights reserved.
-- *****************************************************************

MOXA-TIME-SETTING-MIB DEFINITIONS ::= BEGIN
    IMPORTS
        MODULE-IDENTITY, OBJECT-TYPE,
        enterprises
            FROM SNMPv2-SMI
        TEXTUAL-CONVENTION, TruthValue, DisplayString, RowStatus
            FROM SNMPv2-TC
        time
            FROM MOXA-GENERAL-MIB;

    mxTimeSetting MODULE-IDENTITY
        LAST-UPDATED "202204140000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines time settings for device"

        REVISION    "202204120000Z"
        DESCRIPTION "Redesign daylight saving time"

        REVISION    "202202170000Z"
        DESCRIPTION "update CONTACT-INFO"

        REVISION    "202109290000Z"
        DESCRIPTION "Add a ptp option in mxTsConfigClockSource"

        REVISION    "201906300000Z"
        DESCRIPTION "Initial Revision"

        ::= { time 2 }

    moxa                OBJECT IDENTIFIER ::= { enterprises 8691 }
    general             OBJECT IDENTIFIER ::= { moxa 602 }
    time                OBJECT IDENTIFIER ::= { general 3 }

-- -------------------------------------------------------------
-- groups in the MOXA-TIME-SETTING-MIB MIB
-- -------------------------------------------------------------

    -- tsNotification OBJECT IDENTIFIER ::= { mxTimeSetting 0 }
    tsConfiguration OBJECT IDENTIFIER ::= { mxTimeSetting 1 }
    -- tsStatus OBJECT IDENTIFIER ::= { mxTimeSetting 2 }
    -- tsExtensions OBJECT IDENTIFIER ::= { mxTimeSetting 3 }

-- -------------------------------------------------------------
-- configuration group
-- -------------------------------------------------------------

    -- -------------------------------------------------------------
    -- Daylight Saving
    -- -------------------------------------------------------------
    mxTsConfigDaylightSaving OBJECT IDENTIFIER ::= { tsConfiguration 1 }

    mxTsConfigDaylightSavingEnable OBJECT-TYPE
        SYNTAX      TruthValue
        MAX-ACCESS  read-write
        STATUS      current
        DESCRIPTION
                "Enable/Disable daylight saving time"
        ::= { mxTsConfigDaylightSaving 1 }


    

    -- Daylight Saving Offset
    mxTsConfigDaylightSavingOffset OBJECT-TYPE
        SYNTAX      INTEGER (0..1439)
        MAX-ACCESS  read-write
        STATUS      current
        DESCRIPTION
                "Offset of start daylight saving time in minutes"
        ::= { mxTsConfigDaylightSaving 4 }

    -- Daylight Saving Start
    mxTsConfigDSTRecurringStartDate OBJECT IDENTIFIER ::= { mxTsConfigDaylightSaving 5 }

    mxTsConfigDSTRecurringStartDateMonth OBJECT-TYPE
        SYNTAX      INTEGER {
            Jan (1),
            Feb (2),
            Mar (3),
            Apr (4),
            May (5),
            Jun (6),
            Jul (7),
            Aug (8),
            Sep (9),
            Oct (10),
            Nov (11),
            Dec (12)
        }
        MAX-ACCESS  read-write
        STATUS      current
        DESCRIPTION
                "Month of date to start daylight saving time"
        ::= { mxTsConfigDSTRecurringStartDate 1 }

    mxTsConfigDSTRecurringStartDateWeek OBJECT-TYPE
        SYNTAX      INTEGER {
            1st (1),
            2nd (2),
            3rd (3),
            4th (4),
            last (5)
        }
        MAX-ACCESS  read-write
        STATUS      current
        DESCRIPTION
                "Week of date to start daylight saving time"
        ::= { mxTsConfigDSTRecurringStartDate 2 }

    mxTsConfigDSTRecurringStartDateDay OBJECT-TYPE
        SYNTAX      INTEGER {
            Mon (1),
            Tue (2),
            Wed (3),
            Thu (4),
            Fri (5),
            Sat (6),
            Sun (7),
        }
        MAX-ACCESS  read-write
        STATUS      current
        DESCRIPTION
                "Day of date to start daylight saving time"
        ::= { mxTsConfigDSTRecurringStartDate 3 }

    mxTsConfigDSTRecurringStartDateHour OBJECT-TYPE
        SYNTAX      INTEGER (0..23)
        MAX-ACCESS  read-write
        STATUS      current
        DESCRIPTION
                "Hour of date to start daylight saving time"
        ::= { mxTsConfigDSTRecurringStartDate 4 }

    mxTsConfigDSTRecurringStartDateMinute OBJECT-TYPE
        SYNTAX      INTEGER (0..59)
        MAX-ACCESS  read-write
        STATUS      current
        DESCRIPTION
                "Minute of date to start daylight saving time"
        ::= { mxTsConfigDSTRecurringStartDate 5 }


    -- Daylight Saving End
    mxTsConfigDSTRecurringEndDate OBJECT IDENTIFIER ::= { mxTsConfigDaylightSaving 6 }

    mxTsConfigDSTRecurringEndDateMonth OBJECT-TYPE
        SYNTAX      INTEGER {
            Jan (1),
            Feb (2),
            Mar (3),
            Apr (4),
            May (5),
            Jun (6),
            Jul (7),
            Aug (8),
            Sep (9),
            Oct (10),
            Nov (11),
            Dec (12)
        }
        MAX-ACCESS  read-write
        STATUS      current
        DESCRIPTION
                "Month of date to start daylight saving time"
        ::= { mxTsConfigDSTRecurringEndDate 1 }

    mxTsConfigDSTRecurringEndDateWeek OBJECT-TYPE
        SYNTAX      INTEGER {
            1st (1),
            2nd (2),
            3rd (3),
            4th (4),
            last (5)
        }
        MAX-ACCESS  read-write
        STATUS      current
        DESCRIPTION
                "Week of date to start daylight saving time"
        ::= { mxTsConfigDSTRecurringEndDate 2 }

    mxTsConfigDSTRecurringEndDateDay OBJECT-TYPE
        SYNTAX      INTEGER {
            Mon (1),
            Tue (2),
            Wed (3),
            Thu (4),
            Fri (5),
            Sat (6),
            Sun (7),
        }
        MAX-ACCESS  read-write
        STATUS      current
        DESCRIPTION
                "Year of date to start daylight saving time"
        ::= { mxTsConfigDSTRecurringEndDate 3 }

    mxTsConfigDSTRecurringEndDateHour OBJECT-TYPE
        SYNTAX      INTEGER (0..23)
        MAX-ACCESS  read-write
        STATUS      current
        DESCRIPTION
                "Hour of date to start daylight saving time"
        ::= { mxTsConfigDSTRecurringEndDate 4 }

    mxTsConfigDSTRecurringEndDateMinute OBJECT-TYPE
        SYNTAX      INTEGER (0..59)
        MAX-ACCESS  read-write
        STATUS      current
        DESCRIPTION
                "Minute of date to start daylight saving time"
        ::= { mxTsConfigDSTRecurringEndDate 5 }

    -- -------------------------------------------------------------
    -- Clock Source
    -- -------------------------------------------------------------
    mxTsConfigClockSource OBJECT-TYPE
        SYNTAX      INTEGER {
            local (1),
            ntp (2),
            sntp (3),
            ptp (4)
        }
        MAX-ACCESS  read-write
        STATUS      current
        DESCRIPTION
                "Source of system clock"
        ::= { tsConfiguration 2 }


    -- -------------------------------------------------------------
    -- NTP Settings
    -- -------------------------------------------------------------
    mxTsConfigNtp OBJECT IDENTIFIER ::= { tsConfiguration 3 }


    -- Authentication Key Table
    mxTsConfigNtpAuthenticationKeyTable OBJECT-TYPE
        SYNTAX      SEQUENCE OF MxTsConfigNtpAuthenticationKeyEntry
        MAX-ACCESS  not-accessible
        STATUS      current
        DESCRIPTION
            "A table of NTP authentication keys."
        ::= { mxTsConfigNtp 1 }

    mxTsConfigNtpAuthenticationKeyEntry OBJECT-TYPE
        SYNTAX        MxTsConfigNtpAuthenticationKeyEntry
        MAX-ACCESS    not-accessible
        STATUS        current
        DESCRIPTION
            "A NTP authentication key."
        INDEX        { mxTsConfigNtpAuthenticationKeyIndex }
        ::= { mxTsConfigNtpAuthenticationKeyTable 1 }

    MxTsConfigNtpAuthenticationKeyEntry ::=
        SEQUENCE {
            mxTsConfigNtpAuthenticationKeyIndex     INTEGER,
            mxTsConfigNtpAuthenticationKeyId        INTEGER,
            mxTsConfigNtpAuthenticationKeyType      INTEGER,
            mxTsConfigNtpAuthenticationKeyString    DisplayString,
            mxTsConfigNtpAuthenticationKeyRowStatus RowStatus
        }

    mxTsConfigNtpAuthenticationKeyIndex OBJECT-TYPE
        SYNTAX      INTEGER (1..10)
        MAX-ACCESS  not-accessible
        STATUS      current
        DESCRIPTION
            "Index of authentication key in table."
        ::= { mxTsConfigNtpAuthenticationKeyEntry 1 }

    mxTsConfigNtpAuthenticationKeyId OBJECT-TYPE
        SYNTAX      INTEGER (1..65535)
        MAX-ACCESS  read-write
        STATUS      current
        DESCRIPTION
            "ID of authentication key."
        ::= { mxTsConfigNtpAuthenticationKeyEntry 2 }

    mxTsConfigNtpAuthenticationKeyType OBJECT-TYPE
        SYNTAX      INTEGER {
            md5 (1)
        }
        MAX-ACCESS  read-write
        STATUS      current
        DESCRIPTION
            "Type of authentication key."
        ::= { mxTsConfigNtpAuthenticationKeyEntry 3 }

    mxTsConfigNtpAuthenticationKeyString OBJECT-TYPE
        SYNTAX      DisplayString (SIZE(0..32))
        MAX-ACCESS  read-write
        STATUS      current
        DESCRIPTION
            "Authentication key."
        ::= { mxTsConfigNtpAuthenticationKeyEntry 4 }

    mxTsConfigNtpAuthenticationKeyRowStatus OBJECT-TYPE
        SYNTAX      RowStatus
        MAX-ACCESS  read-write
        STATUS      current
        DESCRIPTION
            "RowStatus for authentication key row."
        ::= { mxTsConfigNtpAuthenticationKeyEntry 5 }


    -- NTP Client Setting
    mxTsConfigNtpClientTable OBJECT-TYPE
        SYNTAX      SEQUENCE OF MxTsConfigNtpClientEntry
        MAX-ACCESS  not-accessible
        STATUS      current
        DESCRIPTION
            "A table of NTP client settings."
        ::= { mxTsConfigNtp 2 }

    mxTsConfigNtpClientEntry OBJECT-TYPE
        SYNTAX        MxTsConfigNtpClientEntry
        MAX-ACCESS    not-accessible
        STATUS        current
        DESCRIPTION
            "An NTP client setting."
        INDEX        { mxTsConfigNtpClientIndex }
        ::= { mxTsConfigNtpClientTable 1 }

    MxTsConfigNtpClientEntry ::=
        SEQUENCE {
            mxTsConfigNtpClientIndex                    INTEGER,
            mxTsConfigNtpClientServerAddress            DisplayString,
            mxTsConfigNtpClientEnableAuthentication     TruthValue,
            mxTsConfigNtpClientKeyId                    INTEGER
        }

    mxTsConfigNtpClientIndex OBJECT-TYPE
        SYNTAX      INTEGER (1..2)
        MAX-ACCESS  not-accessible
        STATUS      current
        DESCRIPTION
            "Index of NTP client setting in table."
        ::= { mxTsConfigNtpClientEntry 1 }

    mxTsConfigNtpClientServerAddress OBJECT-TYPE
        SYNTAX      DisplayString (SIZE(0..60))
        MAX-ACCESS  read-write
        STATUS      current
        DESCRIPTION
            "Address of NTP server."
        ::= { mxTsConfigNtpClientEntry 2 }

    mxTsConfigNtpClientEnableAuthentication OBJECT-TYPE
        SYNTAX      TruthValue
        MAX-ACCESS  read-write
        STATUS      current
        DESCRIPTION
            "Enable authentication with NTP server."
        ::= { mxTsConfigNtpClientEntry 3 }

    mxTsConfigNtpClientKeyId OBJECT-TYPE
        SYNTAX      INTEGER (1..65535)
        MAX-ACCESS  read-write
        STATUS      current
        DESCRIPTION
            "ID of key for authentication with NTP server."
        ::= { mxTsConfigNtpClientEntry 4 }

    -- NTP Server Setting
    mxTsConfigNtpServer OBJECT IDENTIFIER ::= { mxTsConfigNtp 3 }

    mxTsConfigNtpServerEnable OBJECT-TYPE
        SYNTAX      TruthValue
        MAX-ACCESS  read-write
        STATUS      current
        DESCRIPTION
                "Enable/Disable NTP server"
        ::= { mxTsConfigNtpServer 1 }

    mxTsConfigNtpServerAuthentication OBJECT-TYPE
        SYNTAX      TruthValue
        MAX-ACCESS  read-write
        STATUS      current
        DESCRIPTION
                "Enable/Disable NTP server authentication"
        ::= { mxTsConfigNtpServer 2 }


    -- -------------------------------------------------------------
    -- SNTP Setting
    -- -------------------------------------------------------------
    mxTsConfigSntp OBJECT IDENTIFIER ::= { tsConfiguration 4 }


    -- SNTP Client Setting
    mxTsConfigSntpClientTable OBJECT-TYPE
        SYNTAX      SEQUENCE OF MxTsConfigSntpClientEntry
        MAX-ACCESS  not-accessible
        STATUS      current
        DESCRIPTION
            "A table of NTP client settings."
        ::= { mxTsConfigSntp 1 }

    mxTsConfigSntpClientEntry OBJECT-TYPE
        SYNTAX        MxTsConfigSntpClientEntry
        MAX-ACCESS    not-accessible
        STATUS        current
        DESCRIPTION
            "An SNTP client setting."
        INDEX        { mxTsConfigSntpClientIndex }
        ::= { mxTsConfigSntpClientTable 1 }

    MxTsConfigSntpClientEntry ::=
        SEQUENCE {
            mxTsConfigSntpClientIndex                   INTEGER,
            mxTsConfigSntpClientServerAddress           DisplayString
        }

    mxTsConfigSntpClientIndex OBJECT-TYPE
        SYNTAX      INTEGER (1..2)
        MAX-ACCESS  not-accessible
        STATUS      current
        DESCRIPTION
            "Index of SNTP client setting in table."
        ::= { mxTsConfigSntpClientEntry 1 }

    mxTsConfigSntpClientServerAddress OBJECT-TYPE
        SYNTAX      DisplayString (SIZE(0..60))
        MAX-ACCESS  read-write
        STATUS      current
        DESCRIPTION
            "Address of SNTP server."
        ::= { mxTsConfigSntpClientEntry 2 }

END
