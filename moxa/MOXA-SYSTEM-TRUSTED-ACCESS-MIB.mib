-- ****************************************************************
-- *  Moxa General (System Management) Feature - Trusted Access PRIVATE MIB
-- *
-- *  Copyright (c) 2019 by Moxa Inc.
-- *  All rights reserved.
-- *****************************************************************

MOXA-SYSTEM-TRUSTED-ACCESS-MIB DEFINITIONS ::= BEGIN
    IMPORTS
        MODULE-IDENTITY, OBJECT-TYPE,
        IpAddress, Unsigned32,
        enterprises                     FROM SNMPv2-SMI

        TEXTUAL-CONVENTION, RowStatus,
        DateAndTime, MacAddress,
        DisplayString, TruthValue       FROM SNMPv2-TC;

    mxSysTrustAccessSvr MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines trusted access configuration"


        REVISION    "202202170000Z"
        DESCRIPTION "update CONTACT-INFO"

        REVISION    "201906300000Z"
        DESCRIPTION "Initial Revision"

        ::= { systemManagement 4 }

    moxa              OBJECT IDENTIFIER ::= { enterprises 8691 }
    general           OBJECT IDENTIFIER ::= { moxa 602 }
    systemManagement  OBJECT IDENTIFIER ::= { general 1 }

-- -------------------------------------------------------------
-- groups in the TRUSTED ACCESS PRIVATE MIB
-- -------------------------------------------------------------

   -- taNotification  OBJECT IDENTIFIER ::= { mxSysTrustAccessSvr 0 }
   taConfiguration  OBJECT IDENTIFIER ::= { mxSysTrustAccessSvr 1 }
   -- taStatus  OBJECT IDENTIFIER ::= { mxSysTrustAccessSvr 2 }
   -- taExtension  OBJECT IDENTIFIER ::= { mxSysTrustAccessSvr 3 }

-- -------------------------------------------------------------
-- Config group
-- -------------------------------------------------------------

    taConfigEnableTrustedAccess OBJECT-TYPE
        SYNTAX      TruthValue
        MAX-ACCESS  read-write
        STATUS      current
        DESCRIPTION
            "Enable of trusted access."
         ::= { taConfiguration 1 }

    taConfigTrustedAccessTable OBJECT-TYPE
        SYNTAX      SEQUENCE OF TaConfigTrustedAccessEntry
        MAX-ACCESS  not-accessible
        STATUS      current
        DESCRIPTION
            "A table for the configuration of trusted access."
        ::= { taConfiguration 2 }

    taConfigTrustedAccessEntry OBJECT-TYPE
        SYNTAX      TaConfigTrustedAccessEntry
        MAX-ACCESS  not-accessible
        STATUS      current
        DESCRIPTION
            "An entry for the configuration of a trusted access."
        INDEX { entryIndex }
        ::= { taConfigTrustedAccessTable 1 }

    TaConfigTrustedAccessEntry ::=
        SEQUENCE {
            entryIndex      Unsigned32,
            entryIpAddress  IpAddress,
            entryNetmask    IpAddress,
            entryRowStatus  RowStatus
        }

    entryIndex OBJECT-TYPE
        SYNTAX      Unsigned32
        MAX-ACCESS  read-only
        STATUS      current
        DESCRIPTION
            "The index of the trusted access entry."
         ::= { taConfigTrustedAccessEntry 1 }

    entryIpAddress OBJECT-TYPE
        SYNTAX      IpAddress
        MAX-ACCESS  read-create
        STATUS      current
        DESCRIPTION
            "IP address of the trusted access entry."
         ::= { taConfigTrustedAccessEntry 2 }

    entryNetmask OBJECT-TYPE
        SYNTAX      IpAddress
        MAX-ACCESS  read-create
        STATUS      current
        DESCRIPTION
            "Network mask address of the trusted access entry."
         ::= { taConfigTrustedAccessEntry 3 }
    entryRowStatus OBJECT-TYPE
        SYNTAX      RowStatus
        MAX-ACCESS  read-create
        STATUS      current
        DESCRIPTION
            "The status column used for creating, modifying, and deleting entries of the IP-Port binding pool."
         ::= { taConfigTrustedAccessEntry 4 }
END
