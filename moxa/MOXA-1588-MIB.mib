-- ****************************************************************
-- *  Moxa General (Time) - PTP PRIVATE MIB
-- *
-- *  Copyright (c) 2021 by Moxa Inc.
-- *  All rights reserved.
-- *****************************************************************

MOXA-1588-MIB DEFINITIONS ::= BEGIN
    IMPORTS
        MODULE-IDENTITY, NOTIFICATION-TYPE, OBJECT-TYPE, OBJECT-IDENTITY, Gauge32, Unsigned32, Counter32, Counter64, mib-2, Integer32
            FROM SNMPv2-SMI
        TEXTUAL-CONVENTION, DateAndTime, DisplayString, TruthValue, AutonomousType
            FROM SNMPv2-TC
        OBJECT-GROUP, MODULE-COMPLIANCE
            FROM SNMPv2-CONF
        time
            FROM MOXA-GENERAL-MIB
        InterfaceIndexOrZero
            FROM IF-MIB
        PtpClockDomainType, PtpClockIdentity, PtpClockInstanceType, PtpClockIntervalBase2, PtpClockMechanismType, PtpClockPortNumber, PtpClockPortTransportTypeAddress, PtpClockProfileType, PtpClockQualityAccuracyType, PtpClockQualityClassType, PtpClockRoleType, PtpClockStateType, PtpClockTimeInterval, PtpClockTimeSourceType, PtpClockTxModeType, PtpClockType
            FROM PTPBASE-MIB;

    mx1588 MODULE-IDENTITY
        LAST-UPDATED "202210190000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa 1588 Default Profile"

        REVISION    "202312010000Z"
        DESCRIPTION
            "
            Modified objects:
                ieee1588ConfigClockDefaultDSMaximumStepsRemoved
            "

        REVISION    "202210190000Z"
        DESCRIPTION 
            "
            Modified objects:
                ieee1588StatClockPortRunningState
            "

        REVISION    "202103090000Z"
        DESCRIPTION
            "
            Removed objects:
                ieee1588ConfigClockType,
                ieee1588ConfigTransportType,
                ieee1588ConfigClockDefaultDSSlaveOnly,
                ieee1588ConfigClockDefaultDSQualityOffset,
                ieee1588ConfigClockDefaultDSVlanId,
                ieee1588ConfigClockPortDSName,
                ieee1588ClockPortDSPeerMeanPathDelay,
                ieee1588ConfigClockPortDSGrantDuration,
                ieee1588ConfigClockPortDSPTPVersion,
                ieee1588StatSystem,
                ieee1588StatConformance,
                ieee1588StatSystemEntry,
                Ieee1588StatSystemDomainEntry,
                ieee1588StatClockParentDSParentStats,
                ieee1588StatClockParentDSOffset,
                ieee1588StatClockParentDSClockPhChRate,
                ieee1588StatClockParentDSGMClockQualityOffset,
                ieee1588StatClockRunningEntry,
                ieee1588StatClockTimePropertiesDSEntry,
                ieee1588StatClockTransDefaultDSEntry,
                ieee1588StatClockPortEntry,
                ieee1588StatClockPortRunningName,
                ieee1588StatClockPortRunningRole,
                ieee1588StatClockPortRunningInterfaceIndex,
                ieee1588StatClockPortRunningTransport,
                ieee1588StatClockPortRunningEncapsulationType,
                ieee1588StatClockPortRunningTxMode,
                ieee1588StatClockPortRunningRxMode,
                ieee1588StatClockPortRunningPacketsReceived,
                ieee1588StatClockPortRunningPacketsSent,
                ieee1588StatClockPortTransDSEntry,
                ieee1588StatClockPortAssociateEntry
            Added objects:
                ieee1588ConfigClockDefaultDSMaximumStepsRemoved,
                ieee1588ConfigClockDefaultDSAccuracyAlert,
                ieee1588StatClockCurrentDSSyncStatus,
                ieee1588StatClockCurrentDSSlavePort,
                ieee1588StatClockCurrentDSClockTime,
                ieee1588StatClockParentDSParentPortNumber,
                ieee1588StatClockPortRunningPeerMeanPathDelay
            Modified objects:
                ieee1588ConfigClockDefaultDSClockIdentity,
                ieee1588ConfigClockPortDSPortIdentity
            "

        REVISION    "201905280000Z"
        DESCRIPTION "Initial Revision"

        ::= { time 4 }

-- -------------------------------------------------------------
-- groups in the MOXA-1588-MIB MIB
-- -------------------------------------------------------------
    -- ieee1588Notification       OBJECT IDENTIFIER ::= { mx1588 0 }
    ieee1588Configuration         OBJECT IDENTIFIER ::= { mx1588 1 }
    ieee1588Status                OBJECT IDENTIFIER ::= { mx1588 2 }
    -- ieee1588Extensions         OBJECT IDENTIFIER ::= { mx1588 3 }

-- -------------------------------------------------------------
-- configuration group
-- -------------------------------------------------------------
---------------
-- IEEE 1588 --
---------------
    ieee1588ConfigClock  OBJECT IDENTIFIER
        ::= { ieee1588Configuration 1 }

    ieee1588ConfigClockDefaultDSTable OBJECT-TYPE
        SYNTAX          SEQUENCE OF Ieee1588ConfigClockDefaultDSEntry
        MAX-ACCESS      not-accessible
        STATUS          current
        DESCRIPTION
                "Table of information about the PTP clock defaultDS for
                 all domains."
        ::= { ieee1588ConfigClock 1 }

    ieee1588ConfigClockDefaultDSEntry OBJECT-TYPE
        SYNTAX          Ieee1588ConfigClockDefaultDSEntry
        MAX-ACCESS      not-accessible
        STATUS          current
        DESCRIPTION
                "A table entry that contains information about a single
                 PTP clock defaultDS for a domain."
        INDEX  { ieee1588ConfigClockDefaultDSInstanceIndex }
        ::= { ieee1588ConfigClockDefaultDSTable 1 }

    Ieee1588ConfigClockDefaultDSEntry ::=
        SEQUENCE {
            ieee1588ConfigClockDefaultDSInstanceIndex       PtpClockInstanceType,
            ieee1588ConfigClockDefaultDSClockType           PtpClockType,
            ieee1588ConfigClockDefaultDSDomainNumber        PtpClockDomainType,
            ieee1588ConfigClockDefaultDSTwoStepFlag         TruthValue,
            ieee1588ConfigClockDefaultDSClockIdentity       PtpClockIdentity,
            ieee1588ConfigClockDefaultDSPriority1           Unsigned32,
            ieee1588ConfigClockDefaultDSPriority2           Unsigned32,
            ieee1588ConfigClockDefaultDSQualityClass        PtpClockQualityClassType,
            ieee1588ConfigClockDefaultDSQualityAccuracy     PtpClockQualityAccuracyType,
            ieee1588ConfigClockDefaultDSMaximumStepsRemoved Unsigned32,
            ieee1588ConfigClockDefaultDSAccuracyAlert       Unsigned32
        }

    ieee1588ConfigClockDefaultDSInstanceIndex OBJECT-TYPE
        SYNTAX          PtpClockInstanceType
        MAX-ACCESS      not-accessible
        STATUS          current
        DESCRIPTION
                "This object specifies the instance of the clock for this clock
                 type in the given domain."
        ::= { ieee1588ConfigClockDefaultDSEntry 1 }

    ieee1588ConfigClockDefaultDSClockType OBJECT-TYPE
        SYNTAX          PtpClockType
        MAX-ACCESS      read-write
        STATUS          current
        DESCRIPTION
                "This object specifies the clock type as defined in the
                 textual convention description."
        ::= { ieee1588ConfigClockDefaultDSEntry 2 }

    ieee1588ConfigClockDefaultDSDomainNumber OBJECT-TYPE
        SYNTAX          PtpClockDomainType
        MAX-ACCESS      read-write
        STATUS          current
        DESCRIPTION
                "This object specifies the domain number used to create a
                 logical group of PTP devices."
        ::= { ieee1588ConfigClockDefaultDSEntry 3 }

    ieee1588ConfigClockDefaultDSTwoStepFlag OBJECT-TYPE
        SYNTAX          TruthValue
        MAX-ACCESS      read-write
        STATUS          current
        DESCRIPTION
                "This object specifies whether the two-step process is used."
        ::= { ieee1588ConfigClockDefaultDSEntry 4 }

    ieee1588ConfigClockDefaultDSClockIdentity OBJECT-TYPE
        SYNTAX          PtpClockIdentity
        MAX-ACCESS      read-only
        STATUS          current
        DESCRIPTION
                "This object specifies the defaultDS clockIdentity member."
        ::= { ieee1588ConfigClockDefaultDSEntry 5 }

    ieee1588ConfigClockDefaultDSPriority1 OBJECT-TYPE
        SYNTAX          Unsigned32 (0..255)
        MAX-ACCESS      read-write
        STATUS          current
        DESCRIPTION
                "This object specifies the defaultDS priority1 member."
        ::= { ieee1588ConfigClockDefaultDSEntry 6 }

    ieee1588ConfigClockDefaultDSPriority2 OBJECT-TYPE
        SYNTAX          Unsigned32 (0..255)
        MAX-ACCESS      read-write
        STATUS          current
        DESCRIPTION
                "This object specifies the defaultDS priority2 member."
        ::= { ieee1588ConfigClockDefaultDSEntry 7 }

    ieee1588ConfigClockDefaultDSQualityClass OBJECT-TYPE
        SYNTAX          PtpClockQualityClassType
        MAX-ACCESS      read-only
        STATUS          current
        DESCRIPTION
                "This object specifies the defaultDS Quality Class."
        ::= { ieee1588ConfigClockDefaultDSEntry 8 }

    ieee1588ConfigClockDefaultDSQualityAccuracy OBJECT-TYPE
        SYNTAX          PtpClockQualityAccuracyType
        MAX-ACCESS      read-only
        STATUS          current
        DESCRIPTION
                "This object specifies the defaultDS Quality Accuracy."
        ::= { ieee1588ConfigClockDefaultDSEntry 9 }

    ieee1588ConfigClockDefaultDSMaximumStepsRemoved OBJECT-TYPE
        SYNTAX          Unsigned32 (2..255)
        MAX-ACCESS      read-write
        STATUS          current
        DESCRIPTION
                "This object specifies the defaultDS Maximum Steps Removed."
        ::= { ieee1588ConfigClockDefaultDSEntry 10 }

    ieee1588ConfigClockDefaultDSAccuracyAlert OBJECT-TYPE
        SYNTAX          Unsigned32 (50..250000000)
        MAX-ACCESS      read-write
        STATUS          current
        DESCRIPTION
                "This object specifies the defaultDS Accuracy Alert."
        ::= { ieee1588ConfigClockDefaultDSEntry 11 }

    ieee1588ConfigClockPortDSTable OBJECT-TYPE
        SYNTAX          SEQUENCE OF Ieee1588ConfigClockPortDSEntry
        MAX-ACCESS      not-accessible
        STATUS          current
        DESCRIPTION
                "Table of information about the clock's portDS for a
                 particular domain."
        ::= { ieee1588ConfigClock 2 }

    ieee1588ConfigClockPortDSEntry OBJECT-TYPE
        SYNTAX          Ieee1588ConfigClockPortDSEntry
        MAX-ACCESS      not-accessible
        STATUS          current
        DESCRIPTION
                "A table entry that contains portDS information for
                 a single clock port."
        INDEX { ieee1588ConfigClockPortDSPortNumberIndex }
        ::= { ieee1588ConfigClockPortDSTable 1 }

    Ieee1588ConfigClockPortDSEntry ::=
        SEQUENCE {
            ieee1588ConfigClockPortDSPortNumberIndex      PtpClockPortNumber,
            ieee1588ConfigClockPortDSPortIdentity         OCTET STRING,
            ieee1588ConfigClockPortDSlogAnnouncementInterval PtpClockIntervalBase2,
            ieee1588ConfigClockPortDSAnnounceRctTimeout   Integer32,
            ieee1588ConfigClockPortDSlogSyncInterval      PtpClockIntervalBase2,
            ieee1588ConfigClockPortDSMinDelayReqInterval  Integer32,
            ieee1588ConfigClockPortDSPeerDelayReqInterval Integer32,
            ieee1588ConfigClockPortDSDelayMech            PtpClockMechanismType,
            ieee1588ConfigClockPortDSEnabled              TruthValue
        }

    ieee1588ConfigClockPortDSPortNumberIndex OBJECT-TYPE
        SYNTAX          PtpClockPortNumber
        MAX-ACCESS      not-accessible
        STATUS          current
        DESCRIPTION
                "This object specifies the PTP portNumber associated with this
                 PTP port."
        ::= { ieee1588ConfigClockPortDSEntry 1 }

    ieee1588ConfigClockPortDSPortIdentity OBJECT-TYPE
        SYNTAX          OCTET STRING(SIZE(1..256))
        MAX-ACCESS      read-only
        STATUS          current
        DESCRIPTION
                "This object specifies the PTP clock port Identity."
        ::= { ieee1588ConfigClockPortDSEntry 2 }

    ieee1588ConfigClockPortDSlogAnnouncementInterval OBJECT-TYPE
        SYNTAX          PtpClockIntervalBase2
        UNITS           "Time Interval"
        MAX-ACCESS      read-write
        STATUS          current
        DESCRIPTION
                "This object specifies the Announce message transmission
                 interval associated with this clock port."
        ::= { ieee1588ConfigClockPortDSEntry 3 }

    ieee1588ConfigClockPortDSAnnounceRctTimeout OBJECT-TYPE
        SYNTAX          Integer32
        MAX-ACCESS      read-write
        STATUS          current
        DESCRIPTION
                "This object specifies the Announce receipt timeout associated
                 with this clock port."
        ::= { ieee1588ConfigClockPortDSEntry 4 }

    ieee1588ConfigClockPortDSlogSyncInterval OBJECT-TYPE
        SYNTAX          PtpClockIntervalBase2
        UNITS           "Time Interval"
        MAX-ACCESS      read-write
        STATUS          current
        DESCRIPTION
                "This object specifies the Sync message transmission interval."
        ::= { ieee1588ConfigClockPortDSEntry 5 }

    ieee1588ConfigClockPortDSMinDelayReqInterval OBJECT-TYPE
        SYNTAX          Integer32
        MAX-ACCESS      read-write
        STATUS          current
        DESCRIPTION
                "This object specifies the Delay_Req message transmission
                 interval."
        ::= { ieee1588ConfigClockPortDSEntry 6 }

    ieee1588ConfigClockPortDSPeerDelayReqInterval OBJECT-TYPE
        SYNTAX          Integer32
        MAX-ACCESS      read-write
        STATUS          current
        DESCRIPTION
                "This object specifies the Pdelay_Req message transmission
                 interval."
        ::= { ieee1588ConfigClockPortDSEntry 7 }

    ieee1588ConfigClockPortDSDelayMech OBJECT-TYPE
        SYNTAX          PtpClockMechanismType
        MAX-ACCESS      read-write
        STATUS          current
        DESCRIPTION
                "This object specifies the delay mechanism used.  If the clock
                 is an end-to-end clock, the value is e2e; if the
                 clock is a peer to-peer clock, the value is p2p."
        ::= { ieee1588ConfigClockPortDSEntry 8 }

    ieee1588ConfigClockPortDSEnabled OBJECT-TYPE
        SYNTAX          TruthValue
        MAX-ACCESS      read-write
        STATUS          current
        DESCRIPTION
                "True if port is enabled."
        DEFVAL { false }
        ::= { ieee1588ConfigClockPortDSEntry 9 }

    ieee1588ConfigTransportType OBJECT-TYPE
        SYNTAX  INTEGER {
                    udpipv4 (1),
                    udpipv6 (2),
                    ieee8023 (3),
                    devicenet (4),
                    controlnet (5),
                    profitnet (6),
                    ieee8021 (7),
                    unknown (65534)
                }
        MAX-ACCESS read-write
        STATUS     current
        DESCRIPTION
                "This denotes the type of the interface. PTP port bears a seperate
                 meaning than the one that are normally defined in interface mibs.
                 PTP can run over physical interfaces, VLAN identifiers or IVR
                 interfaces. Hence this object needs to be configured before making
                 this particular row as ACTIVE.
                 Only values UDP/IPv4, UDP/IPv6, IEEE802.3 are supported. IEEE8021
                 corresponds to layer 2 Vlan."
        ::= { ieee1588ConfigClock 3 }

-- -------------------------------------------------------------
-- status group
-- -------------------------------------------------------------
---------------
-- IEEE 1588 --
---------------

    ieee1588StatClock  OBJECT IDENTIFIER
        ::= { ieee1588Status 1 }

    ieee1588StatClockCurrentDSTable OBJECT-TYPE
        SYNTAX          SEQUENCE OF Ieee1588StatClockCurrentDSEntry
        MAX-ACCESS      not-accessible
        STATUS          current
        DESCRIPTION
                "Table of information about the PTP clock currentDS for
                 all domains."
        ::= { ieee1588StatClock 1 }

    ieee1588StatClockCurrentDSEntry OBJECT-TYPE
        SYNTAX          Ieee1588StatClockCurrentDSEntry
        MAX-ACCESS      not-accessible
        STATUS          current
        DESCRIPTION
                "A table entry that contains information about a single
                 PTP clock currentDS for a domain."
        REFERENCE
                "Section 8.2.2 ('currentDS data set member
                 specifications') of [IEEE-1588-2008]"
        INDEX { ieee1588StatClockCurrentDSInstanceIndex }
        ::= { ieee1588StatClockCurrentDSTable 1 }

    Ieee1588StatClockCurrentDSEntry ::=
        SEQUENCE {
            ieee1588StatClockCurrentDSInstanceIndex    PtpClockInstanceType,
            ieee1588StatClockCurrentDSStepsRemoved     Unsigned32,
            ieee1588StatClockCurrentDSOffsetFromMaster PtpClockTimeInterval,
            ieee1588StatClockCurrentDSMeanPathDelay    PtpClockTimeInterval,
            ieee1588StatClockCurrentDSSyncStatus       Unsigned32,
            ieee1588StatClockCurrentDSSlavePort        Integer32,
            ieee1588StatClockCurrentDSClockTime        DisplayString
        }

    ieee1588StatClockCurrentDSInstanceIndex OBJECT-TYPE
        SYNTAX          PtpClockInstanceType
        MAX-ACCESS      not-accessible
        STATUS          current
        DESCRIPTION
                "This object specifies the instance of the clock for this clock
                 type in the given domain."
        ::= { ieee1588StatClockCurrentDSEntry 1 }

    ieee1588StatClockCurrentDSStepsRemoved OBJECT-TYPE
        SYNTAX          Unsigned32
        UNITS           "Steps"
        MAX-ACCESS      read-only
        STATUS          current
        DESCRIPTION
                "The current clock dataset stepsRemoved value.

                 This object specifies the distance measured by the number of
                 boundary clocks between the local clock and the foreign master
                 as indicated in the stepsRemoved field of Announce messages."
        REFERENCE
                "Section 8.2.2.2 ('stepsRemoved') of [IEEE-1588-2008]"
        ::= { ieee1588StatClockCurrentDSEntry 2 }

    ieee1588StatClockCurrentDSOffsetFromMaster OBJECT-TYPE
        SYNTAX          PtpClockTimeInterval
        UNITS           "Time Interval"
        MAX-ACCESS      read-only
        STATUS          current
        DESCRIPTION
                "This object specifies the current clock dataset ClockOffset
                 value.  The value of the computation of the offset in time
                 between a slave and a master clock."
        REFERENCE
                "Section 8.2.2.3 ('currentDS.offsetFromMaster')
                 of [IEEE-1588-2008]"
        ::= { ieee1588StatClockCurrentDSEntry 3 }

    ieee1588StatClockCurrentDSMeanPathDelay OBJECT-TYPE
        SYNTAX          PtpClockTimeInterval
        UNITS           "Time Interval"
        MAX-ACCESS      read-only
        STATUS          current
        DESCRIPTION
                "This object specifies the current clock dataset
                 MeanPathDelay value.

                 The mean path delay between a pair of ports as measured by the
                 delay request-response mechanism."
        REFERENCE
                "Section 8.2.2.4 ('currentDS.meanPathDelay')
                 of [IEEE-1588-2008]"
        ::= { ieee1588StatClockCurrentDSEntry 4 }


    ieee1588StatClockCurrentDSSyncStatus OBJECT-TYPE
        SYNTAX          Unsigned32
        MAX-ACCESS      read-only
        STATUS          current
        DESCRIPTION
                "A value of 'DISABLED' (0) indicates that the ptp function is
                 disabled. A value of 'FREERUN' (1) indicates that the device
                 is selected to be master. A value of 'SYNCING' (2) indicates
                 that the device is selected to be slave and is synchronizing
                 to grandmaster. A value of 'LOCKED' (3) indicates that the
                 device is synchronized to the grandmaster. A value of
                 'INITIALIZING' (4) indicates that the ptp function is
                 initializing."
        DEFVAL { 1 }
        ::= { ieee1588StatClockCurrentDSEntry 5 }

    ieee1588StatClockCurrentDSSlavePort OBJECT-TYPE
        SYNTAX          Integer32(1..255)
        MAX-ACCESS      read-only
        STATUS          current
        DESCRIPTION
                "Indicate the port which is in the SLAVE state."
        ::= { ieee1588StatClockCurrentDSEntry 6 }

    ieee1588StatClockCurrentDSClockTime OBJECT-TYPE
        SYNTAX          DisplayString
        MAX-ACCESS      read-only
        STATUS          current
        DESCRIPTION
                "Indicate the PTP Clock Time."
        ::= { ieee1588StatClockCurrentDSEntry 7 }

    ieee1588StatClockParentDSTable OBJECT-TYPE
        SYNTAX          SEQUENCE OF Ieee1588StatClockParentDSEntry
        MAX-ACCESS      not-accessible
        STATUS          current
        DESCRIPTION
                "Table of information about the PTP clock parentDS for
                 all domains."
        ::= { ieee1588StatClock 2 }

    ieee1588StatClockParentDSEntry OBJECT-TYPE
        SYNTAX          Ieee1588StatClockParentDSEntry
        MAX-ACCESS      not-accessible
        STATUS          current
        DESCRIPTION
                "A table entry that contains information about a single
                 PTP clock parentDS for a domain."
        REFERENCE
                "Section 8.2.3 ('parentDS data set member specifications') of
                 [IEEE-1588-2008]"
        INDEX { ieee1588StatClockParentDSInstanceIndex }
        ::= { ieee1588StatClockParentDSTable 1 }

    Ieee1588StatClockParentDSEntry ::=
        SEQUENCE {
            ieee1588StatClockParentDSInstanceIndex          PtpClockInstanceType,
            ieee1588StatClockParentDSParentPortIdentity     OCTET STRING,
            ieee1588StatClockParentDSGMClockIdentity        PtpClockIdentity,
            ieee1588StatClockParentDSGMClockPriority1       Unsigned32,
            ieee1588StatClockParentDSGMClockPriority2       Unsigned32,
            ieee1588StatClockParentDSGMClockQualityClass    PtpClockQualityClassType,
            ieee1588StatClockParentDSGMClockQualityAccuracy PtpClockQualityAccuracyType,
            ieee1588StatClockParentDSParentPortNumber       PtpClockPortNumber
        }

    ieee1588StatClockParentDSInstanceIndex OBJECT-TYPE
        SYNTAX          PtpClockInstanceType
        MAX-ACCESS      not-accessible
        STATUS          current
        DESCRIPTION
                "This object specifies the instance of the clock for this clock
                 type in the given domain."
        ::= { ieee1588StatClockParentDSEntry 1 }

    ieee1588StatClockParentDSParentPortIdentity OBJECT-TYPE
        SYNTAX          OCTET STRING(SIZE(1..256))
        MAX-ACCESS      read-only
        STATUS          current
        DESCRIPTION
                "This object specifies the value of portIdentity of the port on
                 the master that issues the Sync messages used in synchronizing
                 this clock."
        REFERENCE
                "Section 8.2.3.2 ('parentDS.parentPortIdentity') of
                 [IEEE-1588-2008]"
        ::= { ieee1588StatClockParentDSEntry 2 }

    ieee1588StatClockParentDSGMClockIdentity OBJECT-TYPE
        SYNTAX          PtpClockIdentity
        MAX-ACCESS      read-only
        STATUS          current
        DESCRIPTION
                "This object specifies the parentDS grandmaster clock
                 identity."
        REFERENCE
                "Section 8.2.3.6 ('parentDS.grandmasterIdentity') of
                 [IEEE-1588-2008]"
        ::= { ieee1588StatClockParentDSEntry 3 }

    ieee1588StatClockParentDSGMClockPriority1 OBJECT-TYPE
        SYNTAX          Unsigned32
        MAX-ACCESS      read-only
        STATUS          current
        DESCRIPTION
                "This object specifies the parentDS grandmaster clock
                 priority1."
        REFERENCE
                "Section 8.2.3.8 ('parentDS.grandmasterPriority1') of
                 [IEEE-1588-2008]"
        ::= { ieee1588StatClockParentDSEntry 4 }

    ieee1588StatClockParentDSGMClockPriority2 OBJECT-TYPE
        SYNTAX          Unsigned32
        MAX-ACCESS      read-only
        STATUS          current
        DESCRIPTION
                "This object specifies the parentDS grandmaster clock
                 priority2."
        REFERENCE
                "Section 8.2.3.9 ('parentDS.grandmasterPriority2') of
                 [IEEE-1588-2008]"
        ::= { ieee1588StatClockParentDSEntry 5 }

    ieee1588StatClockParentDSGMClockQualityClass OBJECT-TYPE
        SYNTAX          PtpClockQualityClassType
        MAX-ACCESS      read-only
        STATUS          current
        DESCRIPTION
                "This object specifies the parentDS grandmaster clock
                 quality class."
        REFERENCE
                "Section 8.2.3.7 ('parentDS.grandmasterClockQuality') of
                 [IEEE-1588-2008]"
        ::= { ieee1588StatClockParentDSEntry 6 }

    ieee1588StatClockParentDSGMClockQualityAccuracy OBJECT-TYPE
        SYNTAX          PtpClockQualityAccuracyType
        MAX-ACCESS      read-only
        STATUS          current
        DESCRIPTION
                "This object specifies the parentDS grandmaster clock
                 quality accuracy."
        REFERENCE
                "Section 8.2.3.7 ('parentDS.grandmasterClockQuality') of
                 [IEEE-1588-2008]"
        ::= { ieee1588StatClockParentDSEntry 7 }

    ieee1588StatClockParentDSParentPortNumber OBJECT-TYPE
        SYNTAX          PtpClockPortNumber
        MAX-ACCESS      read-only
        STATUS          current
        DESCRIPTION
                "This object specifies the parentDS PTP portNumber"
        ::= { ieee1588StatClockParentDSEntry 8 }

    ieee1588StatClockPortRunningTable OBJECT-TYPE
        SYNTAX          SEQUENCE OF Ieee1588StatClockPortRunningEntry
        MAX-ACCESS      not-accessible
        STATUS          current
        DESCRIPTION
                "Table of information about the clock ports running datasets for
                 a particular domain."
        ::= { ieee1588StatClock 3 }

    ieee1588StatClockPortRunningEntry OBJECT-TYPE
        SYNTAX          Ieee1588StatClockPortRunningEntry
        MAX-ACCESS      not-accessible
        STATUS          current
        DESCRIPTION
                "A table entry that contains running dataset information
                 about a single clock port."
        INDEX { ieee1588StatClockPortRunningPortNumberIndex }
        ::= { ieee1588StatClockPortRunningTable 1 }

    Ieee1588StatClockPortRunningEntry ::=
        SEQUENCE {
            ieee1588StatClockPortRunningPortNumberIndex    PtpClockPortNumber,
            ieee1588StatClockPortRunningState              INTEGER,
            ieee1588StatClockPortRunningPeerMeanPathDelay  PtpClockTimeInterval
        }

    ieee1588StatClockPortRunningPortNumberIndex OBJECT-TYPE
        SYNTAX          PtpClockPortNumber
        MAX-ACCESS      not-accessible
        STATUS          current
        DESCRIPTION
                "This object specifies the PTP portNumber associated with this
                 clock port."
        ::= { ieee1588StatClockPortRunningEntry 1 }

    ieee1588StatClockPortRunningState OBJECT-TYPE
        SYNTAX          INTEGER  {
                            initializing(1),
                            faulty(2),
                            disabled(3),
                            listening(4),
                            preMaster(5),
                            master(6),
                            passive(7),
                            uncalibrated(8),
                            slave(9),
                            TransmittingSynchronized(10),
                            ReceivingSynchronized (11)
                        }
        MAX-ACCESS      read-only
        STATUS          current
        DESCRIPTION
                "This object specifies the port state returned by PTP engine:

                initializing
                faulty
                disabled
                listening
                preMaster
                master
                passive
                uncalibrated
                slave
                TransmittingSynchronized
                ReceivingSynchronized       "
        ::= { ieee1588StatClockPortRunningEntry 2 }

    ieee1588StatClockPortRunningPeerMeanPathDelay OBJECT-TYPE
        SYNTAX          PtpClockTimeInterval
        UNITS           "Time Interval"
        MAX-ACCESS      read-only
        STATUS          current
        DESCRIPTION
                "This object specifies the peer meanPathDelay."
        ::= { ieee1588StatClockPortRunningEntry 3 }

END
