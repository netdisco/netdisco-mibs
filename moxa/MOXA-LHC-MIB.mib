-- ****************************************************************
-- *  Moxa Switching - LHC PRIVATE MIB
-- *
-- *  Copyright (c) 2019 by Moxa Inc.
-- *  All rights reserved.
-- *****************************************************************

MOXA-LHC-MIB DEFINITIONS ::= BEGIN
    IMPORTS
        MODULE-IDENTITY, NOTIFICATION-TYPE, OBJECT-TYPE, Integer32
            FROM SNMPv2-SMI
        TEXTUAL-CONVENTION, DateAndTime, MacAddress, DisplayString, TruthValue
            FROM SNMPv2-TC
        basicLayer2
          FROM MOXA-SWITCHING-MIB;

    mxLhc MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa Link Healthy Check"

        REVISION    "202202170000Z"
        DESCRIPTION "update CONTACT-INFO"

        REVISION    "201906300000Z"
        DESCRIPTION "Initial Revision"

        ::= { basicLayer2 8 }

-- -------------------------------------------------------------
-- groups in the MOXA-LHC-MIB MIB
-- -------------------------------------------------------------

  lhcNotification    OBJECT IDENTIFIER ::= { mxLhc 0 }
  -- lhcConfiguration   OBJECT IDENTIFIER ::= { mxLhc 1 }
  lhcStatus          OBJECT IDENTIFIER ::= { mxLhc 2 }
  -- lhcExtensions      OBJECT IDENTIFIER ::= { mxLhc 3 }

-- -------------------------------------------------------------
-- configuration group
-- -------------------------------------------------------------

-- -------------------------------------------------------------
-- status group
-- -------------------------------------------------------------

    lhcStatusFailPortNum OBJECT-TYPE
        SYNTAX      Integer32 (1..256)
        MAX-ACCESS  accessible-for-notify
        STATUS      current
        DESCRIPTION
            "The port number which lhcStatusFailTrap notification is sent from."
        ::= { lhcStatus 1 }

-- -------------------------------------------------------------
-- notification group
-- -------------------------------------------------------------

    lhcStatusFailTrap NOTIFICATION-TYPE
        OBJECTS    { lhcStatusFailPortNum }
        STATUS     current
        DESCRIPTION
            "The Link Healthy Check Fail."
        ::= { lhcNotification 1 }

END
