-- ****************************************************************
-- *  Moxa Product - Product Information PRIVATE MIB
-- *
-- *  Copyright (c) 2019 by Moxa Inc.
-- *  All rights reserved.
-- *****************************************************************

MOXA-PRODUCT-INFO-MIB DEFINITIONS ::= BEGIN
    IMPORTS
        enterprises, MODULE-IDENTITY, NOTIFICATION-TYPE, OBJECT-TYPE, IpAddress, Unsigned32
            FROM SNMPv2-SMI
        TEXTUAL-CONVENTION, DisplayString, TruthValue
            FROM SNMPv2-TC;

    mxProductInfo MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa product information"

        REVISION    "202202170000Z"
        DESCRIPTION "update CONTACT-INFO"

        REVISION    "202109290000Z"
        DESCRIPTION
            "Add product series:
             EDS series, TSN series, MDS4XGS series, RKS series, TM series"

        REVISION    "201906300000Z"
        DESCRIPTION "Initial Revision"

        ::= { product 1 }

    moxa                OBJECT IDENTIFIER ::= { enterprises 8691 }
    product             OBJECT IDENTIFIER ::= { moxa 600         }

-- -------------------------------------------------------------
-- groups in the MOXA-PRODUCT-INFO-MIB MIB
-- -------------------------------------------------------------

mxSwitchMDS OBJECT IDENTIFIER ::= { mxProductInfo 1 }
mxSwitchEDS OBJECT IDENTIFIER ::= { mxProductInfo 2 }
mxSwitchTSN OBJECT IDENTIFIER ::= { mxProductInfo 4 }
mxSwitchMDS4XGS OBJECT IDENTIFIER ::= { mxProductInfo 5 }
mxSwitchRKS OBJECT IDENTIFIER ::= { mxProductInfo 6 }
mxSwitchTM  OBJECT IDENTIFIER ::= { mxProductInfo 7 }

-- -------------------------------------------------------------
-- groups in the MOXA-MDS-Switch
-- -------------------------------------------------------------

mdsG4012           OBJECT IDENTIFIER ::= { mxSwitchMDS 1 }
mdsG4020           OBJECT IDENTIFIER ::= { mxSwitchMDS 2 }
mdsG4028           OBJECT IDENTIFIER ::= { mxSwitchMDS 3 }
mdsG4012-L3        OBJECT IDENTIFIER ::= { mxSwitchMDS 4 }
mdsG4020-L3        OBJECT IDENTIFIER ::= { mxSwitchMDS 5 }
mdsG4028-L3        OBJECT IDENTIFIER ::= { mxSwitchMDS 6 }

-- -------------------------------------------------------------
-- groups in the MOXA-EDS-Switch
-- -------------------------------------------------------------

eds4008                 OBJECT IDENTIFIER ::= { mxSwitchEDS 1 }
eds4008-2MSC            OBJECT IDENTIFIER ::= { mxSwitchEDS 2 }
eds4008-2MST            OBJECT IDENTIFIER ::= { mxSwitchEDS 3 }
eds4008-2SSC            OBJECT IDENTIFIER ::= { mxSwitchEDS 4 }
eds4008-2GT-2GS         OBJECT IDENTIFIER ::= { mxSwitchEDS 5 }
eds4008-4P-2GT-2GS      OBJECT IDENTIFIER ::= { mxSwitchEDS 6 }
edsG4008                OBJECT IDENTIFIER ::= { mxSwitchEDS 7 }
eds4009-3MSC            OBJECT IDENTIFIER ::= { mxSwitchEDS 8 }
eds4009-3MST            OBJECT IDENTIFIER ::= { mxSwitchEDS 9 }
eds4009-3SSC            OBJECT IDENTIFIER ::= { mxSwitchEDS 10 }
eds4012-4GS             OBJECT IDENTIFIER ::= { mxSwitchEDS 11 }
eds4012-4GC             OBJECT IDENTIFIER ::= { mxSwitchEDS 12 }
eds4012-4GS-HV-T        OBJECT IDENTIFIER ::= { mxSwitchEDS 13 }
eds4012-4GC-HV-T        OBJECT IDENTIFIER ::= { mxSwitchEDS 14 }
eds4012-8P-4GS          OBJECT IDENTIFIER ::= { mxSwitchEDS 15 }
edsG4012-4GC            OBJECT IDENTIFIER ::= { mxSwitchEDS 16 }
edsG4012-8P-4QGS        OBJECT IDENTIFIER ::= { mxSwitchEDS 17 }
eds4014-4GS-2QGS        OBJECT IDENTIFIER ::= { mxSwitchEDS 18 }
eds4014-4GS-2QGS-HV-T   OBJECT IDENTIFIER ::= { mxSwitchEDS 19 }
edsG4014-6QGS           OBJECT IDENTIFIER ::= { mxSwitchEDS 20 }
edsG4014-4QGS-2XGS      OBJECT IDENTIFIER ::= { mxSwitchEDS 21 }

-- -------------------------------------------------------------
-- groups in the MOXA-TSN-Switch
-- -------------------------------------------------------------

tsnG5004 OBJECT IDENTIFIER ::= { mxSwitchTSN 1 }
tsnG5008 OBJECT IDENTIFIER ::= { mxSwitchTSN 2 }

-- -------------------------------------------------------------
-- groups in the MOXA-RKS-Switch
-- -------------------------------------------------------------
rksG4028-4GT-HV         OBJECT IDENTIFIER ::= { mxSwitchRKS 1 }
rksG4028-4GT-2HV        OBJECT IDENTIFIER ::= { mxSwitchRKS 2 }
rksG4028-4GS-HV         OBJECT IDENTIFIER ::= { mxSwitchRKS 3 }
rksG4028-4GS-2HV        OBJECT IDENTIFIER ::= { mxSwitchRKS 4 }
rksG4028-4GT-LV         OBJECT IDENTIFIER ::= { mxSwitchRKS 5 }
rksG4028-4GT-2LV        OBJECT IDENTIFIER ::= { mxSwitchRKS 6 }
rksG4028-4GS-LV         OBJECT IDENTIFIER ::= { mxSwitchRKS 7 }
rksG4028-4GS-2LV        OBJECT IDENTIFIER ::= { mxSwitchRKS 8 }
rksG4028-PoE-4GS-HV     OBJECT IDENTIFIER ::= { mxSwitchRKS 9 }
rksG4028-PoE-4GS-2HV    OBJECT IDENTIFIER ::= { mxSwitchRKS 10 }
rksG4028-PoE-4GS-LV     OBJECT IDENTIFIER ::= { mxSwitchRKS 11 }
rksG4028-PoE-4GS-2LV    OBJECT IDENTIFIER ::= { mxSwitchRKS 12 }
rksG4028-L3-4GT-HV      OBJECT IDENTIFIER ::= { mxSwitchRKS 13 }
rksG4028-L3-4GT-2HV     OBJECT IDENTIFIER ::= { mxSwitchRKS 14 }
rksG4028-L3-4GS-HV      OBJECT IDENTIFIER ::= { mxSwitchRKS 15 }
rksG4028-L3-4GS-2HV     OBJECT IDENTIFIER ::= { mxSwitchRKS 16 }
rksG4028-L3-4GT-LV      OBJECT IDENTIFIER ::= { mxSwitchRKS 17 }
rksG4028-L3-4GT-2LV     OBJECT IDENTIFIER ::= { mxSwitchRKS 18 }
rksG4028-L3-4GS-LV      OBJECT IDENTIFIER ::= { mxSwitchRKS 19 }
rksG4028-L3-4GS-2LV     OBJECT IDENTIFIER ::= { mxSwitchRKS 20 }
rksG4028-L3-PoE-4GS-HV  OBJECT IDENTIFIER ::= { mxSwitchRKS 21 }
rksG4028-L3-PoE-4GS-2HV OBJECT IDENTIFIER ::= { mxSwitchRKS 22 }
rksG4028-L3-PoE-4GS-LV  OBJECT IDENTIFIER ::= { mxSwitchRKS 23 }
rksG4028-L3-PoE-4GS-2LV OBJECT IDENTIFIER ::= { mxSwitchRKS 24 }

-- -------------------------------------------------------------
-- groups in the MOXA-MDS-4XGS-Switch
-- -------------------------------------------------------------
mdsG4012-4XGS           OBJECT IDENTIFIER ::= { mxSwitchMDS4XGS 1 }
mdsG4020-4XGS           OBJECT IDENTIFIER ::= { mxSwitchMDS4XGS 2 }
mdsG4028-4XGS           OBJECT IDENTIFIER ::= { mxSwitchMDS4XGS 3 }
mdsG4012-L3-4XGS        OBJECT IDENTIFIER ::= { mxSwitchMDS4XGS 4 }
mdsG4020-L3-4XGS        OBJECT IDENTIFIER ::= { mxSwitchMDS4XGS 5 }
mdsG4028-L3-4XGS        OBJECT IDENTIFIER ::= { mxSwitchMDS4XGS 6 }

-- -------------------------------------------------------------
-- groups in the MOXA-TM-Switch
-- -------------------------------------------------------------
tmG1508  OBJECT IDENTIFIER ::= { mxSwitchTM 1 }

END
