-- ****************************************************************
-- *  Moxa General (Event Notification) - EMAIL PRIVATE MIB
-- *
-- *  Copyright (c) 2019 by Moxa Inc.
-- *  All rights reserved.
-- *****************************************************************

MOXA-EMAIL-CONFIGURATION-MIB DEFINITIONS ::= BEGIN
    IMPORTS
        MODULE-IDENTITY, OBJECT-TYPE, IpAddress, Unsigned32, enterprises
            FROM SNMPv2-SMI
        TEXTUAL-CONVENTION, DateAndTime, MacAddress, DisplayString, TruthValue
            --FROM SNMPv2-TC
            FROM SNMPv2-TC;

    mxEmailConfig MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines email configuration"

        REVISION    "202202170000Z"
        DESCRIPTION "update CONTACT-INFO"

        REVISION    "201906300000Z"
        DESCRIPTION "Initial Revision"

        ::= { eventNotification 3 }

    moxa               OBJECT IDENTIFIER ::= { enterprises 8691 }
    general            OBJECT IDENTIFIER ::= { moxa 602 }
    eventNotification  OBJECT IDENTIFIER ::= { general 7 }

-- -------------------------------------------------------------
-- groups in the SYSTEM UTILIZATION PRIVATE MIB
-- -------------------------------------------------------------

   -- ecNotification  OBJECT IDENTIFIER ::= { mxEmailConfig 0 }
   ecConfiguration  OBJECT IDENTIFIER ::= { mxEmailConfig 1 }
   -- ecStatus  OBJECT IDENTIFIER ::= { mxEmailConfig 2 }
   -- ecExtensions  OBJECT IDENTIFIER ::= { mxEmailConfig 3 }

-- -------------------------------------------------------------
-- Configuration group
-- -------------------------------------------------------------

    ecConfigServerAddress OBJECT-TYPE
        SYNTAX      IpAddress
        MAX-ACCESS  read-write
        STATUS      current
        DESCRIPTION
            "Email Server Address."
         ::= { ecConfiguration 1 }

    ecConfigServerPort OBJECT-TYPE
        SYNTAX      Unsigned32
        MAX-ACCESS  read-write
        STATUS      current
        DESCRIPTION
            "Email Server Port."
         ::= { ecConfiguration 2 }

    ecConfigUserName OBJECT-TYPE
        SYNTAX      DisplayString
        MAX-ACCESS  read-write
        STATUS      current
        DESCRIPTION
            "Email User Name."
         ::= { ecConfiguration 3 }

    ecConfigPassword OBJECT-TYPE
        SYNTAX      DisplayString
        MAX-ACCESS  read-write
        STATUS      current
        DESCRIPTION
            "Email User Password."
         ::= { ecConfiguration 4 }

    ecConfigSenderAddress OBJECT-TYPE
        SYNTAX      DisplayString
        MAX-ACCESS  read-write
        STATUS      current
        DESCRIPTION
            "Sender Address."
         ::= { ecConfiguration 5 }

    ecConfigEnableTLS OBJECT-TYPE
        SYNTAX      TruthValue
        MAX-ACCESS  read-write
        STATUS      current
        DESCRIPTION
            "Enable TLS."
         ::= { ecConfiguration 6 }

    ecConfigRecipientEmailAddr1 OBJECT-TYPE
        SYNTAX      DisplayString
        MAX-ACCESS  read-write
        STATUS      current
        DESCRIPTION
            "Recipient Email Address 1."
         ::= { ecConfiguration 7 }

    ecConfigRecipientEmailAddr2 OBJECT-TYPE
        SYNTAX      DisplayString
        MAX-ACCESS  read-write
        STATUS      current
        DESCRIPTION
            "Recipient Email Address 2."
         ::= { ecConfiguration 8 }

    ecConfigRecipientEmailAddr3 OBJECT-TYPE
        SYNTAX      DisplayString
        MAX-ACCESS  read-write
        STATUS      current
        DESCRIPTION
            "Recipient Email Address 3."
         ::= { ecConfiguration 9 }

    ecConfigRecipientEmailAddr4 OBJECT-TYPE
        SYNTAX      DisplayString
        MAX-ACCESS  read-write
        STATUS      current
        DESCRIPTION
            "Recipient Email Address 4."
         ::= { ecConfiguration 10 }

    ecConfigRecipientEmailAddr5 OBJECT-TYPE
        SYNTAX      DisplayString
        MAX-ACCESS  read-write
        STATUS      current
        DESCRIPTION
            "Recipient Email Address 5."
         ::= { ecConfiguration 11 }

END
