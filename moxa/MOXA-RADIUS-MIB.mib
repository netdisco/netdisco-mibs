-- ****************************************************************
-- *  Moxa Switching - Radius PRIVATE MIB
-- *
-- *  Copyright (c) 2019 by Moxa Inc.
-- *  All rights reserved.
-- *****************************************************************

MOXA-RADIUS-MIB DEFINITIONS ::= BEGIN
    IMPORTS
        MODULE-IDENTITY, NOTIFICATION-TYPE, OBJECT-TYPE, IpAddress, Integer32
            FROM SNMPv2-SMI
        TEXTUAL-CONVENTION, DateAndTime, MacAddress, DisplayString, TruthValue, RowStatus
            FROM SNMPv2-TC
        layer2Security
          FROM MOXA-SWITCHING-MIB;

    mxRadius MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa Radius Server for DOT.1X"

        REVISION    "202202170000Z"
        DESCRIPTION "update CONTACT-INFO"

        REVISION    "201906300000Z"
        DESCRIPTION "Initial Revision"

        ::= { layer2Security 9 }

-- -------------------------------------------------------------
-- groups in the MOXA-RADIUS-MIB MIB
-- -------------------------------------------------------------

  -- radiusNotification      OBJECT IDENTIFIER ::= { mxRadius 0 }
  radiusConfiguration     OBJECT IDENTIFIER ::= { mxRadius 1 }
  -- radiusStatus            OBJECT IDENTIFIER ::= { mxRadius 2 }
  -- radiusExtensions        OBJECT IDENTIFIER ::= { mxRadius 3 }


-- -------------------------------------------------------------
-- configuration group
-- -------------------------------------------------------------

-- Radius Server Table Configuration Start

    radiusConfigRadiusServerTable OBJECT-TYPE
        SYNTAX SEQUENCE OF RadiusConfigRadiusServerEntry
        MAX-ACCESS not-accessible
        STATUS current
        DESCRIPTION
            "The table listing the RADIUS servers with
                 which the client shares a secret."
        ::= { radiusConfiguration 1}

    radiusConfigRadiusServerEntry OBJECT-TYPE
        SYNTAX RadiusConfigRadiusServerEntry
        MAX-ACCESS not-accessible
        STATUS current
        DESCRIPTION
            "An entry representing a RADIUS server
                 with which the client shares a secret."
        INDEX { radiusConfigServerNum }
        ::= { radiusConfigRadiusServerTable 1 }

    RadiusConfigRadiusServerEntry ::=
        SEQUENCE {
           radiusConfigServerNum
                Integer32,
           radiusConfigServerIPAddress
                IpAddress,
           radiusConfigSharedKey
                DisplayString,
           radiusConfigAuthPort
                Integer32,
           radiusConfigPrimary
                IpAddress,
           radiusConfigTimeout
                Integer32,
           radiusConfigRetransmit
                Integer32,
           radiusConfigRadRowStatus
                RowStatus
        }

	radiusConfigServerNum OBJECT-TYPE
        SYNTAX Integer32 (1..2)
        MAX-ACCESS not-accessible
        STATUS current
        DESCRIPTION
            "A unique value, greater than zero, indicating the Server number of
             radius server table."
        ::= { radiusConfigRadiusServerEntry 1 }

    radiusConfigServerIPAddress OBJECT-TYPE
        SYNTAX IpAddress
        MAX-ACCESS read-create
        STATUS current
        DESCRIPTION
            "The IP address of the RADIUS server
            referred to in this table entry."
        ::= { radiusConfigRadiusServerEntry 2 }

    radiusConfigSharedKey OBJECT-TYPE
        SYNTAX DisplayString
        MAX-ACCESS read-create
        STATUS current
        DESCRIPTION
            "The secret string which is shared between Server and Client."
        ::= { radiusConfigRadiusServerEntry 3 }

    radiusConfigAuthPort OBJECT-TYPE
        SYNTAX Integer32 (1..65535)
        MAX-ACCESS read-create
        STATUS current
        DESCRIPTION
            "To indicate Auth port in which the Radius Server entry place."
        ::= { radiusConfigRadiusServerEntry 4 }

	radiusConfigPrimary OBJECT-TYPE
        SYNTAX IpAddress
        MAX-ACCESS read-create
        STATUS current
        DESCRIPTION
            "This parameter when true(1) indicates that this is the primary
			 Server, and false(2) indicates that this is not."
        ::= { radiusConfigRadiusServerEntry 5 }

    radiusConfigTimeout OBJECT-TYPE
        SYNTAX Integer32 (1..120)
        MAX-ACCESS read-create
        STATUS current
        DESCRIPTION
            "The maximum time within which the server has to respond for a
			 request from the client. All of the retry times cannot exceeds
             Dot1x server timeout value.
             Note: All of the retry times = Timeout * (Retransmit + 1).
             Recommend value: 5"
        ::= { radiusConfigRadiusServerEntry 6 }

	radiusConfigRetransmit OBJECT-TYPE
        SYNTAX Integer32 (1..254)
        MAX-ACCESS read-create
        STATUS current
        DESCRIPTION
            "The allowed maximum no. of trials to be tried by a client to get
			 response from the server for a request. All of the retry times
             cannot exceeds Dot1x server timeout value.
             Note: All of the retry times = Timeout * (Retransmit + 1).
             Recommend value: 1"
        ::= { radiusConfigRadiusServerEntry 7 }

	radiusConfigRadRowStatus OBJECT-TYPE
        SYNTAX      RowStatus
        MAX-ACCESS  read-create
        STATUS      current
        DESCRIPTION
            "The status column used for creating, modifying, and deleting entries of the RADIUS Server."
        ::= { radiusConfigRadiusServerEntry 8 }

--------------------------------------------
-- Radius Server Table Configuration End --
--------------------------------------------

END
