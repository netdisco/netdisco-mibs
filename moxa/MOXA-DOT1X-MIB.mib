-- ****************************************************************
-- *  Moxa Switching - Dot1x PRIVATE MIB
-- *
-- *  Copyright (c) 2019 by Moxa Inc.
-- *  All rights reserved.
-- *****************************************************************

MOXA-DOT1X-MIB DEFINITIONS ::= BEGIN
    IMPORTS
        MODULE-IDENTITY, NOTIFICATION-TYPE, OBJECT-TYPE, IpAddress, Integer32
            FROM SNMPv2-SMI
        TEXTUAL-CONVENTION, DateAndTime, MacAddress, DisplayString, TruthValue, RowStatus
            FROM SNMPv2-TC
        layer2Security
          FROM MOXA-SWITCHING-MIB;

    mxDot1x   MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa Dot1x"

        REVISION    "202202170000Z"
        DESCRIPTION "update CONTACT-INFO"

        REVISION    "201906300000Z"
        DESCRIPTION    "Initial Revision"

        ::= { layer2Security 5 }

-- -------------------------------------------------------------
-- groups in the MOXA-DOT1X-MIB MIB 
-- -------------------------------------------------------------

  dot1xNotification      OBJECT IDENTIFIER ::= { mxDot1x 0 }
  dot1xConfiguration     OBJECT IDENTIFIER ::= { mxDot1x 1 }
  dot1xStatus            OBJECT IDENTIFIER ::= { mxDot1x 2 }
  -- dot1xExtensions        OBJECT IDENTIFIER ::= { mxDot1x 3 }


-- -------------------------------------------------------------
-- configuration group
-- -------------------------------------------------------------

    dot1xConfigGlobalEnable OBJECT-TYPE
        SYNTAX       TruthValue
        MAX-ACCESS   read-write
        STATUS       current
        DESCRIPTION
            "This object indicates if DOT1X is globally enabled/disabled."
        ::= { dot1xConfiguration 1 }

    dot1xConfigAAAAuthMode OBJECT-TYPE
        SYNTAX      INTEGER {
                        radius(1),
                        local(2)
                    }
        MAX-ACCESS  read-write
        STATUS      current
        DESCRIPTION
            "This object is used to configure for the choice of  
              local or radius authentication server to be used by 
              the authenticator for its authentication services."
        ::= { dot1xConfiguration 2 }

-- Port Table Configuration Start

    dot1xConfigPortTable OBJECT-TYPE
        SYNTAX SEQUENCE OF Dot1xConfigPortEntry
        MAX-ACCESS not-accessible
        STATUS current
        DESCRIPTION
            "A table to store the port specific parameters for DOT1X 
            like max-Req, portControl, etc. And the parameters can be manipulated 
            by administrators."
        ::= { dot1xConfiguration 3 }

    dot1xConfigPortEntry OBJECT-TYPE
        SYNTAX Dot1xConfigPortEntry
        MAX-ACCESS not-accessible
        STATUS current
        DESCRIPTION
            "An entry appears in this Port Table represent port information about 
            Dot1x Mode."
        INDEX { dot1xConfigPortNum }
        ::= { dot1xConfigPortTable 1 }

    Dot1xConfigPortEntry ::=
        SEQUENCE {
            dot1xConfigPortReauthenticate
                TruthValue,
            dot1xConfigPortNum
                Integer32,
            dot1xConfigEnable
                TruthValue,
            dot1xConfigPortControl
                INTEGER,
            dot1xConfigMaxReq
                Integer32,
            dot1xConfigQuietPeriod
                Integer32,
            dot1xConfigAuthReAuthEnable
                TruthValue,
            dot1xConfigReauthPeriod
                Integer32,
            dot1xConfigServerTimeout
                Integer32,
            dot1xConfigSuppTimeout
                Integer32,
            dot1xConfigTxPeriod
                Integer32
    }

    dot1xConfigPortReauthenticate OBJECT-TYPE
        SYNTAX TruthValue
        MAX-ACCESS read-write
        STATUS current
        DESCRIPTION
            "The reauthentication control for this port. Setting 
               this attribute TRUE causes the Authenticator PAE state 
               machine for the Port to reauthenticate the Supplicant. 
               Setting this attribute FALSE has no effect. 
               This attribute always returns FALSE when it is read."
        ::= { dot1xConfigPortEntry 1 }

    dot1xConfigPortNum OBJECT-TYPE
        SYNTAX Integer32 (1..256)
        MAX-ACCESS read-only
        STATUS current
        DESCRIPTION
            "A unique value, greater than zero, indicating the Port number of 
             port configuration table."
        ::= { dot1xConfigPortEntry 2 }

    dot1xConfigEnable OBJECT-TYPE
        SYNTAX TruthValue
        MAX-ACCESS read-write
        STATUS current
        DESCRIPTION
            "This parameter when true(1) indicates that a port is dot1x enabled 
            and false(2) indicates that this feature is disabled 
            on the port."
        ::= { dot1xConfigPortEntry 3 }

    dot1xConfigPortControl OBJECT-TYPE
        SYNTAX INTEGER {
                    forceUnauthorized(1), 
                    auto(2), 
                    forceAuthorized(3)
                }
        MAX-ACCESS read-write
        STATUS current
        DESCRIPTION
            "The control values of the Authenticator PAE controlled 
             Port."
        ::= { dot1xConfigPortEntry 4 }

    dot1xConfigMaxReq OBJECT-TYPE
        SYNTAX Integer32 (1..10)
        MAX-ACCESS read-write
        STATUS current
        DESCRIPTION
            "The value of the maxReq constant currently in use by 
            the Backend Authentication state machine."
        ::= { dot1xConfigPortEntry 5 }

    dot1xConfigQuietPeriod OBJECT-TYPE
        SYNTAX Integer32 (0..65535)
        MAX-ACCESS read-write
        STATUS current
        DESCRIPTION
            "The value, in seconds, of the quietPeriod constant 
            currently in use by the Authenticator PAE state 
            machine."
        ::= { dot1xConfigPortEntry 6 }

    dot1xConfigAuthReAuthEnable OBJECT-TYPE
        SYNTAX TruthValue
        MAX-ACCESS read-write
        STATUS current
        DESCRIPTION
            "The enable/disable control used by the Reauthentication 
               Timer state machine"
        ::= { dot1xConfigPortEntry 7 }

    dot1xConfigReauthPeriod OBJECT-TYPE
        SYNTAX Integer32 (1..65535)
        MAX-ACCESS read-write
        STATUS current
        DESCRIPTION
            "The value, in seconds, of the reAuthPeriod constant 
            currently in use by the Reauthentication Timer state 
            machine."
        ::= { dot1xConfigPortEntry 8 }

    dot1xConfigServerTimeout OBJECT-TYPE
        SYNTAX Integer32 (1..65535)
        MAX-ACCESS read-write
        STATUS current
        DESCRIPTION
            "The value, in seconds, of the serverTimeout constant 
            currently in use by the Backend Authentication state 
            machine."
        ::= { dot1xConfigPortEntry 9 }

    dot1xConfigSuppTimeout OBJECT-TYPE
        SYNTAX Integer32 (1..65535)
        MAX-ACCESS read-write
        STATUS current
        DESCRIPTION
            "The value, in seconds, of the suppTimeout constant 
            currently in use by the Backend Authentication state 
            machine."
        ::= { dot1xConfigPortEntry 10 }

    dot1xConfigTxPeriod OBJECT-TYPE
        SYNTAX Integer32 (1..65535)
        MAX-ACCESS read-write
        STATUS current
        DESCRIPTION
            "The value, in seconds, of the txPeriod constant 
            currently in use by the Authenticator PAE state 
            machine."
        ::= { dot1xConfigPortEntry 11 }

-- Port  Table Configuration End

-- -------------------------------------------------------------
-- Status group
-- -------------------------------------------------------------

----------------
-- Port Table --
----------------

    dot1xStatPortTable OBJECT-TYPE
        SYNTAX SEQUENCE OF Dot1xStatPortEntry
        MAX-ACCESS not-accessible
        STATUS current
        DESCRIPTION
            "The port status table."
        ::= { dot1xStatus 1 }

    dot1xStatPortEntry OBJECT-TYPE
        SYNTAX Dot1xStatPortEntry
        MAX-ACCESS not-accessible
        STATUS current
        DESCRIPTION
            "The port status table entry."
        INDEX { dot1xStatPortNum }
        ::= { dot1xStatPortTable 1 }

    Dot1xStatPortEntry ::=
        SEQUENCE {
           dot1xStatPortNum
                Integer32,
           dot1xStatPortStatus
                INTEGER,
           dot1xStatLastEapolFrameSource 
                MacAddress
        }

    dot1xStatPortNum OBJECT-TYPE
        SYNTAX Integer32 (1..256)
        MAX-ACCESS read-only 
        STATUS current
        DESCRIPTION
            "The value of this object uniquely identifies this port table entry."
        ::= { dot1xStatPortEntry 1 }

    dot1xStatPortStatus OBJECT-TYPE
        SYNTAX INTEGER {
                        authorized (1),
                        unauthorized (2)
                    } 
        MAX-ACCESS read-only
        STATUS current
        DESCRIPTION
            "The value of the port status."
        ::= { dot1xStatPortEntry 2 }

    dot1xStatLastEapolFrameSource       OBJECT-TYPE 
            SYNTAX        MacAddress 
            MAX-ACCESS    read-only 
            STATUS        current 
            DESCRIPTION 
               "The source MAC address carried in the 
               most recently received EAPOL frame." 
            ::= { dot1xStatPortEntry 3 }

----------------
-- Local Database Table --
----------------

    dot1xStatLocalDatabaseTable OBJECT-TYPE
        SYNTAX SEQUENCE OF Dot1xStatLocalDatabaseEntry
        MAX-ACCESS not-accessible
        STATUS current
        DESCRIPTION
            "This table contains authentication related user 
            configuration information maintained by DOT1X 
            local authentication server."
        ::= { dot1xStatus 2}

    dot1xStatLocalDatabaseEntry OBJECT-TYPE
        SYNTAX Dot1xStatLocalDatabaseEntry
        MAX-ACCESS not-accessible
        STATUS current
        DESCRIPTION
            "Each entry contains User name and Password
            of the user seeking authentication."
        INDEX { dot1xStatLocalDatabaseNum }
        ::= { dot1xStatLocalDatabaseTable 1 }

    Dot1xStatLocalDatabaseEntry ::=
        SEQUENCE {
           dot1xStatLocalDatabaseNum
                Integer32,
           dot1xStatLocalDatabaseUsername
                OCTET STRING,
           dot1xStatLocalDatabasePassword
                OCTET STRING
        }

    dot1xStatLocalDatabaseNum OBJECT-TYPE
        SYNTAX Integer32 (1..64)
        MAX-ACCESS    read-only 
        STATUS current
        DESCRIPTION
            "A unique value, greater than zero, indicating the Entry number of 
             local database table."
        ::= { dot1xStatLocalDatabaseEntry 1 }

    dot1xStatLocalDatabaseUsername OBJECT-TYPE
        SYNTAX OCTET STRING (SIZE(1..20))
        MAX-ACCESS    read-only 
        STATUS current
        DESCRIPTION
            "Identity of the user seeking authentication. A string 
            of not more than 20 printable characters."
        ::= { dot1xStatLocalDatabaseEntry 2 }

    dot1xStatLocalDatabasePassword OBJECT-TYPE
        SYNTAX OCTET STRING (SIZE(1..20))
        MAX-ACCESS    read-only 
        STATUS current
        DESCRIPTION
            "The secret password of the user. A string of not 
            more than 20 printable characters.
           
            When read, this always returns a String 
            of length zero."
        ::= { dot1xStatLocalDatabaseEntry 3 }


--------------------------------------------
-- Local Database Table Configuration End --
--------------------------------------------
-- -------------------------------------------------------------
-- Notification group
-- -------------------------------------------------------------
    dot1xNotifyAuthFail NOTIFICATION-TYPE
        OBJECTS { dot1xStatPortNum, dot1xStatLastEapolFrameSource}
        STATUS current
        DESCRIPTION
            "The dot1xNotifyAuthFail notification is sent when authentication failure 
            occurs."
        ::= { dot1xNotification 1 }


END
