-- ****************************************************************
-- *  Moxa Switching - Loop Protection PRIVATE MIB
-- *
-- *  Copyright (c) 2020 by Moxa Inc.
-- *  All rights reserved.
-- *****************************************************************

MOXA-LOOP-PROTECT-MIB DEFINITIONS ::= BEGIN
    IMPORTS
        MODULE-IDENTITY, NOTIFICATION-TYPE, OBJECT-TYPE, IpAddress, Integer32
            FROM SNMPv2-SMI
        TEXTUAL-CONVENTION, DateAndTime, MacAddress, DisplayString, TruthValue, RowStatus
            FROM SNMPv2-TC
        layer2Security
            FROM MOXA-SWITCHING-MIB;

    mxLp MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa Loop Protection"

        REVISION    "202202170000Z"
        DESCRIPTION "update CONTACT-INFO"

        REVISION    "202011040000Z"
        DESCRIPTION "Initial Revision"

        ::= { layer2Security 10 }

-- -------------------------------------------------------------
-- groups in the MOXA-LOOP-PROTECT-MIB MIB
-- -------------------------------------------------------------

    -- lpNotification   OBJECT IDENTIFIER ::= { mxLp 0 }
    lpConfiguration     OBJECT IDENTIFIER ::= { mxLp 1 }
    lpStatus            OBJECT IDENTIFIER ::= { mxLp 2 }
    -- lpExtensions     OBJECT IDENTIFIER ::= { mxLp 3 }


-- -------------------------------------------------------------
-- configuration group
-- -------------------------------------------------------------

    lpConfigGlobalEnable OBJECT-TYPE
        SYNTAX       TruthValue
        MAX-ACCESS   read-write
        STATUS       current
        DESCRIPTION
            "This object indicates if LOOP-PROTECT is globally enabled/disabled."
        ::= { lpConfiguration 1 }

    lpConfigDetectInterval OBJECT-TYPE
        SYNTAX Integer32 (1..30)
        MAX-ACCESS   read-write
        STATUS       current
        DESCRIPTION
            "This object indicates the intervals in seconds for sending detection packet."
        ::= { lpConfiguration 2 }

-- -------------------------------------------------------------
-- status group
-- -------------------------------------------------------------

    lpStatPortTable OBJECT-TYPE
        SYNTAX SEQUENCE OF LpStatPortEntry
        MAX-ACCESS not-accessible
        STATUS current
        DESCRIPTION
            "The port status table."
        ::= { lpStatus 1 }

    lpStatPortEntry OBJECT-TYPE
        SYNTAX LpStatPortEntry
        MAX-ACCESS not-accessible
        STATUS current
        DESCRIPTION
            "The port status entry."
        INDEX { lpStatPortIndex }
        ::= { lpStatPortTable 1 }

    LpStatPortEntry ::=
        SEQUENCE {
            lpStatPortIndex
                Integer32,
            lpStatStatus
                Integer32,
            lpStatPeerPort
                Integer32
        }

    lpStatPortIndex OBJECT-TYPE
        SYNTAX Integer32 (1..65535)
        MAX-ACCESS not-accessible
        STATUS current
        DESCRIPTION
            "The port index."
        ::= { lpStatPortEntry 1 }

    lpStatStatus OBJECT-TYPE
        SYNTAX INTEGER {
            normal(1),
            looping(2)
        }
        MAX-ACCESS read-only
        STATUS current
        DESCRIPTION
            "The status of the port."
        ::= { lpStatPortEntry 2 }

    lpStatPeerPort OBJECT-TYPE
        SYNTAX Integer32 (1..65535)
        MAX-ACCESS read-only
        STATUS current
        DESCRIPTION
            "The peer-port index of the port."
        ::= { lpStatPortEntry 3 }

END
