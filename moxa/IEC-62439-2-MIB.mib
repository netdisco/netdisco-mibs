-- ***********************************************************************
-- Monitoring MIB definitions
-- ***********************************************************************

IEC-62439-2-MIB DEFINITIONS::= BEGIN

-- ***********************************************************************
-- Imports
-- ***********************************************************************
IMPORTS
        MODULE-IDENTITY,
        OBJECT-IDENTITY,
        OBJECT-TYPE,
        TimeTicks,
        Counter32,
        Unsigned32,
        Integer32 FROM SNMPv2-SMI
        OBJECT-GROUP,
        MODULE-COMPLIANCE FROM SNMPv2-CONF
        TEXTUAL-CONVENTION,
        DisplayString FROM SNMPv2-TC;
-- ***********************************************************************
-- Root OID
-- ***********************************************************************
iec62439 MODULE-IDENTITY
    LAST-UPDATED "201405090000Z" -- May 09, 2014
    ORGANIZATION "IEC/SC 65C"
    CONTACT-INFO "
                International Electrotechnical Commission
                IEC Central Office
                3, rue de Varembe
                P.O. Box 131
                CH ? 1211 GENEVA 20
                Switzerland
                Phone: +41 22 919 02 11
                Fax: +41 22 919 03 00
                email: info@iec.ch
                "
    DESCRIPTION "
                This MIB module defines the Network Management interfaces
                for the Redundancy Protocols defined by the IEC
                standard 62439.
                This definitions specify the pure monitoring variant
                of a SNMP entity. If the SNMP entity also contains
                management functionality, then IEC 62439 management MIB
                definitions shall be used instead of this MIB module.
                "
    REVISION "201405090000Z" -- May 09, 2014
    DESCRIPTION "
                Manager (auto) support has been added in mrpDomainAdminRole.
                Interconnection functionality added.
                Units of mrpDomainRoundTripDelayMax and mrpDomainRoundTripDelayMin
                have been corrected to milliseconds.
                mrpDomainOperRole and mrpDomainAdminRole data type have been set
                to INTEGER.
                Missing constructs in import area have been added.
                Module identity block has been put on top.
                "
    REVISION "200811100000Z" -- November 10, 2008
    DESCRIPTION "
                The undefined use of the value 'badValue' for objects
                of the optional 'mrpDomainDiagGroup' has been removed
                from DESCRIPTION clause at the objects concerned.
                The role dependency of the objects 'mrpDomainState' and
                'mrpDomainError' in the DESCRIPTION clause removed.
                "
    REVISION "200811100000Z" -- November 10, 2008
    DESCRIPTION "
                Separation of IEC 62439 into a suite of documents
                This MIB applies to IEC 62439-2, no change in functionality
                "
    REVISION "200708240000Z" -- August 24, 2007
    DESCRIPTION "
                Final Draft Proposal version of the Network Management
                interface for the Media Redundancy Protocol (MRP) with
                the division in pure Monitoring functionality and in
                additional management functionality.
                "
::= { iso std(0) 62439 }
-- ***********************************************************************
-- Declaration of IEC62439UuidType
-- ***********************************************************************
IEC62439UuidType ::= TEXTUAL-CONVENTION
    STATUS current
    DESCRIPTION "
                The IEC 61158-5-10 defines the structure of
                the UUID as a data type numeric
                identifier 1025.
                "
SYNTAX OCTET STRING (SIZE (16))
-- ***********************************************************************
-- Redundancy Protocols
-- ***********************************************************************
mrp     OBJECT IDENTIFIER::= { iec62439 1 }
prp     OBJECT IDENTIFIER::= { iec62439 2 }
crp     OBJECT IDENTIFIER::= { iec62439 3 }
brp     OBJECT IDENTIFIER::= { iec62439 4 }

-- ***********************************************************************
-- objects groups of redundancy object identifiers
-- ***********************************************************************
mrpObjects          OBJECT IDENTIFIER ::= { mrp 1 }
mrpNotifications    OBJECT IDENTIFIER ::= { mrp 2 }
mrpConformance      OBJECT IDENTIFIER ::= { mrp 3 }

-- ***********************************************************************
-- Objects of the MRP Network Management
-- ***********************************************************************
mrpDomainTable OBJECT-TYPE
    SYNTAX SEQUENCE OF MrpDomainEntry
    MAX-ACCESS not-accessible
    STATUS current
    DESCRIPTION "
                Every entry in this table contains information about
                a Media Redundancy Protocol (MRP) domain.
                Entries cannot be created or deleted via SNMP
                operations.
                "
::= { mrpObjects 1 }

mrpDomainEntry OBJECT-TYPE
    SYNTAX MrpDomainEntry
    MAX-ACCESS not-accessible
    STATUS current
    DESCRIPTION "An entry in the mrpDomainTable."
    INDEX { mrpDomainIndex }
::= { mrpDomainTable 1 }

MrpDomainEntry::= SEQUENCE {
                mrpDomainIndex                  Unsigned32,
                mrpDomainID                     IEC62439UuidType,
                mrpDomainName                   DisplayString,
                mrpDomainAdminRole              INTEGER,
                mrpDomainOperRole               INTEGER,
                mrpDomainRingPort1              Integer32,
                mrpDomainRingPort1State         INTEGER,
                mrpDomainRingPort2              Integer32,
                mrpDomainRingPort2State         INTEGER,
                mrpDomainState                  BITS,
                mrpDomainError                  BITS,
                mrpDomainBlocked                INTEGER,
                mrpDomainVlanId                 Unsigned32,
                mrpDomainManagerPriority        INTEGER,
                mrpDomainRingOpenCount          Counter32,
                mrpDomainLastRingOpenChange     TimeTicks,
                mrpDomainRoundTripDelayMax      Unsigned32,
                mrpDomainRoundTripDelayMin      Unsigned32,
                mrpDomainResetRoundTripDelays   INTEGER,
                mrpDomainMRMReactOnLinkChange   INTEGER
                }

mrpDomainIndex OBJECT-TYPE
    SYNTAX      Unsigned32
    MAX-ACCESS  not-accessible
    STATUS      current
    DESCRIPTION "The index of the entry"
    ::= { mrpDomainEntry 1 }

mrpDomainID OBJECT-TYPE
    SYNTAX      IEC62439UuidType
    MAX-ACCESS  read-only
    STATUS      current
    DESCRIPTION "
                Universally unique identifier belongs to the MRP domain
                which represents a ring.
                "
    ::= { mrpDomainEntry 2 }

mrpDomainName OBJECT-TYPE
    SYNTAX      DisplayString
    MAX-ACCESS  read-only
    STATUS      current
    DESCRIPTION "
                A logical name for the MRP domain to ease the
                management of MRP domains.
                "
    ::= { mrpDomainEntry 3 }

mrpDomainAdminRole OBJECT-TYPE
    SYNTAX      INTEGER {
                    disable(0),
                    client(1),
                    manager(2),
                    managerAutoComp(3),
                    managerAuto(4)
                }
    MAX-ACCESS  read-write
    STATUS      current
    DESCRIPTION "
                Control the MRP behavior of the system per domain.
                If the value is set to disable(0) the MRP entity of
                this domain shall be disabled.
                If the value is set to client(1) the entity shall be set
                to the role of a Media Redundancy Client (MRC).
                If the value is set to manager(2) the entity shall be
                set to the role of a Media Redundancy Manager (MRM).
                If the value is set to managerAutoComp(3) the entity shall be
                set to the role of a Media Redundancy Manager Auto (MRA)
                complying to Annex A.
                If the value is set to managerAuto(4) the entity shall be
                set to the role of a Media Redundancy Manager Auto (MRA) not
                supporting Annex A.
                The factory settings are recommended to adjust the
                value of this object to the client(1) capability of the
                component, or, if supported, to the managerAutoComp(3)
                or managerAuto(4) capability,
                in order to prevent multiple managers are
                in ring (the order of the capabilities are not
                necessarily conform to the order of the object values
                here).
                If the agent restricts the write access, no matter what
                reason, it shall reject write requests by responding
                with 'badValue'.
                "
    ::= { mrpDomainEntry 4 }

mrpDomainOperRole OBJECT-TYPE
    SYNTAX      INTEGER {
                    disable(0),
                    client(1),
                    manager(2),
                    managerAutoComp(3),
                    managerAuto(4)
                    }
    MAX-ACCESS  read-only
    STATUS      current
    DESCRIPTION "
                The operational role of an MRP entity per domain.
                A value of disabled(0) signals that the entity doesn't
                work (whatever reason).
                A value of client(1) signals that the entity is in a
                client role.
                A value of manager(2) signals that the entity is the
                manager of this MRP domain.
                A value of managerAutoComp(3) signals that the entity is
                in automanager role complying to Annex A.
                A value of managerAuto(4) signals that the entity is in
                automanager role not supporting Annex A.
                "
    ::= { mrpDomainEntry 5 }

mrpDomainRingPort1 OBJECT-TYPE
    SYNTAX      Integer32
    MAX-ACCESS  read-only
    STATUS      current
    DESCRIPTION "
                The ifIndex of the layer 2 interface which is used
                as ring port 1.
                "
    ::= { mrpDomainEntry 6 }

mrpDomainRingPort1State OBJECT-TYPE
    SYNTAX      INTEGER {
                    disabled(1),
                    blocked(2),
                    forwarding(3),
                    not-connected(4)
                    }
    MAX-ACCESS  read-only
    STATUS      current
    DESCRIPTION "
                Operational state of the first Ring-Port.
                disabled(1) indicates that all frames are dropped.
                blocked(2) indicates that all frames are dropped except
                - MRP topology change frames and MRP test frames from
                a MRM,
                - MRP link change frames from an MRC,
                - MRP interconnection topology change from a MIM,
                - MRP interconnection link change from a MIC,
                - frames from other protocols that also define to pass
                blocked(2) ports.
                forwarding(3) indicates that all frames are passed through
                according to the forwarding behavior
                of IEEE 802.1D.
                not-connected(4) indicates that the port has no link.
                "
    ::= { mrpDomainEntry 7 }

mrpDomainRingPort2 OBJECT-TYPE
    SYNTAX      Integer32
    MAX-ACCESS  read-only
    STATUS      current
    DESCRIPTION "
                The ifIndex of the layer 2 interface which is
                used as ring port 2.
                "
    ::= { mrpDomainEntry 8 }

mrpDomainRingPort2State OBJECT-TYPE
    SYNTAX      INTEGER {
                    disabled(1),
                    blocked(2),
                    forwarding(3),
                    not-connected(4)
                    }
    MAX-ACCESS  read-only
    STATUS      current
    DESCRIPTION "
                Operational state of the second Ring-Port.
                disabled(1) indicates that all frames are dropped.
                blocked(2) indicates that all frames are dropped except
                - MRP topology change frames and MRP test frames from
                a MRM,
                - MRP link change frames from an MRC,
                - MRP interconnection topology change from a MIM,
                - MRP interconnection link change from a MIC,
                - frames from other protocols that also define to pass
                blocked(2) ports.
                forwarding(3) indicates that all frames are passed through
                according to the forwarding behavior
                of IEEE 802.1D.
                not-connected(4) indicates that the port has no link.
                "
    ::= { mrpDomainEntry 9 }

mrpDomainState OBJECT-TYPE
    SYNTAX      BITS {
                    disabled(0),
                    undefined(1),
                    ringOpen(2),
                    reserved(3)
                    }
    MAX-ACCESS  read-only
    STATUS  current
    DESCRIPTION "
                Operational status of the MRP entity.
                disabled(0) - MRP switched off. All higher bits are invalid
                and shall be reset.
                undefined(1) - Value is not valid.
                All higher bits are invalid and shall be reset.
                ringOpen(2) - MRP ring redundancy lost
                All higher bits are invalid and shall be reset.
                reserved(3) - reserved for further extensions.
                "
    ::= { mrpDomainEntry 10 }

mrpDomainError OBJECT-TYPE
    SYNTAX      BITS {
                    noError(0),
                    invalidVlanId(1),
                    invalid(2),
                    multipleMRM(3),
                    singleSideReceive(4)
                    }
    MAX-ACCESS  read-only
    STATUS      current
    DESCRIPTION "
                If the device couldn't switch to the desired administrative state
                (thus the value of 'mrpDomainState' is not the expected one),
                this value provides the reason. Otherwise the bit noError(0) is set.
                noError(0) - the operational state of the device is confom
                to administrative state.
                All higher bits are invalid and shall be reset.
                invalidVlanId(1) - the assigned VLAN ID is not permitted .
                invalid (2) - Value is not valid.
                All higher bits are invalid and shall be reset.
                multipleMRM(3) - multiple active managers in ring domain.
                singleSideReceive(4) - the test frames of an MRM
                have been seen, but only on one port.
                "
    ::= { mrpDomainEntry 11 }

mrpDomainBlocked OBJECT-TYPE
    SYNTAX      INTEGER {
                    enabled(1),
                    disabled(2)
                    }
    MAX-ACCESS  read-only
    STATUS      current
    DESCRIPTION "
                The entity supports blocked ring ports.
                Shows whether a mrp domain requires the support of the
                BLOCKED port state at ring ports.
                The manager of a mrp domain decides whether this support
                is required.
                Set to enabled the manager demands that all clients
                shall support the blocked attribute also set to enabled.
                If mrpDomainBlocked is set disabled at the manager,
                then the value of mrpDomainBlocked can be arbitrary
                at the clients.
                enabled(1) client: supports ring ports whose port state can be
                blocked.
                manager: works only with clients supporting blocked
                ring ports.
                disabled(2) client: no support of blocked ring ports.
                manager: Work with clients supporting blocked ring
                ports and with clients not supporting
                blocked ring ports.
                "
    ::= { mrpDomainEntry 12 }

mrpDomainVlanId OBJECT-TYPE
    SYNTAX      Unsigned32
    MAX-ACCESS  read-only
    STATUS      current
    DESCRIPTION "
                The VLAN ID assigned to the MRP protocol.
                The VLAN ID only is in use when the bit invalidVlanId
                is not set in mrpDomainError.
                If value is set to 0 no VLAN is assigned.
                The invalidVlanId shall be set to 0 (no Error).
                "
    ::= { mrpDomainEntry 13 }

-- ***********************************************************************
-- Objects of the MRP Network Management for manager role
-- ***********************************************************************
mrpDomainManagerPriority OBJECT-TYPE
    SYNTAX      INTEGER (0..65535)
    MAX-ACCESS  read-only
    STATUS      current
    DESCRIPTION "
                The priority of this MRP entity. If the device is
                client only, the value of this object shall be ignored
                by the MRP entity. Only the four most significant bits
                shall be used, the bits 0 to 11 are reserved. The
                smaller value has the higher priority.
                "
    ::= { mrpDomainEntry 14 }

mrpDomainRingOpenCount OBJECT-TYPE
    SYNTAX      Counter32
    MAX-ACCESS  read-only
    STATUS      current
    DESCRIPTION "
                Counter for ring-state changes to open.
                "
    ::= { mrpDomainEntry 15 }

mrpDomainLastRingOpenChange OBJECT-TYPE
    SYNTAX      TimeTicks
    MAX-ACCESS  read-only
    STATUS      current
    DESCRIPTION "
                Timeticks since last change of ring-state
                to ring open.
                "
    ::= { mrpDomainEntry 16 }

mrpDomainRoundTripDelayMax OBJECT-TYPE
    SYNTAX      Unsigned32
    UNITS       "milliseconds"
    MAX-ACCESS  read-only
    STATUS      current
    DESCRIPTION "
                The max. Round-Trip-Delay (in milliseconds)
                which was measured since startup.
                "
    ::= { mrpDomainEntry 17 }

mrpDomainRoundTripDelayMin OBJECT-TYPE
    SYNTAX      Unsigned32
    UNITS       "milliseconds"
    MAX-ACCESS  read-only
    STATUS      current
    DESCRIPTION "
                The min. Round-Trip-Delay (in milliseconds)
                which was measured since startup.
                "
    ::= { mrpDomainEntry 18 }

mrpDomainResetRoundTripDelays OBJECT-TYPE
    SYNTAX      INTEGER {
                    resetDelays(1)
                    }
    MAX-ACCESS  read-write
    STATUS      current
    DESCRIPTION "
                A write request with resetDelays(1) shall reset
                the values of mrpDomainRoundTripDelayMax and
                mrpDomainRoundTripDelayMin to zero at the
                same time.
                "
    ::= { mrpDomainEntry 19 }

mrpDomainMRMReactOnLinkChange OBJECT-TYPE
    SYNTAX      INTEGER {
                    enabled(1),
                    disabled(2)
                    }
    MAX-ACCESS  read-only
    STATUS      current
    DESCRIPTION "
                Tells whether the MRM reacts on link down MRP link change
                frames.
                enabled(1) indicates that the MRM reacts immediately on link down MRP
                link change frames.
                disabled(2) indicates that the MRM does not react on
                link down MRP link change frames.
                "
    ::= { mrpDomainEntry 20 }

-- ***********************************************************************
-- Objects of the Media redundancy Interconnection
-- ***********************************************************************
mrpInterconnectionTable OBJECT-TYPE
    SYNTAX      SEQUENCE OF MrpInterconnectionEntry
    MAX-ACCESS  not-accessible
    STATUS      current
    DESCRIPTION "
                Every entry in this table contains information about
                a Media redundancy Interconnection domain.
                Entries cannot be created or deleted via SNMP
                operations.
                "
    ::= { mrpObjects 2 }

mrpInterconnectionEntry OBJECT-TYPE
    SYNTAX      MrpInterconnectionEntry
    MAX-ACCESS  not-accessible
    STATUS      current
    DESCRIPTION "An entry in the mrpInterconnectionTable."
    INDEX { mrpInterconnectionID }
    ::= { mrpInterconnectionTable 1 }

MrpInterconnectionEntry::= SEQUENCE {
        mrpInterconnectionID                    Unsigned32,
        mrpInterconnectionName                  DisplayString,
        mrpInterconnectionPort                  Integer32,
        mrpInterconnectionPortState             INTEGER,
        mrpInterconnectionVlanId                Unsigned32,
        mrpInterconnectionMode                  INTEGER,
        mrpInterconnectionAdminRole             INTEGER,
        mrpInterconnectionOperRole              INTEGER,
        mrpInterconnectionState                 INTEGER,
        mrpInterconnectionError                 BITS,
        mrpInterconnectionOpenCount             Counter32,
        mrpInterconnectionLastOpenChange        TimeTicks,
        mrpInterconnectionPeerMAC               OCTET STRING,
        mrpInterconnectionOwnMRMMAC             OCTET STRING,
        mrpInterconnectionPeerMRMMAC            OCTET STRING,
        mrpInterconnectionPeerRingDomainUUID    IEC62439UuidType
        }

mrpInterconnectionID OBJECT-TYPE
    SYNTAX      Unsigned32
    MAX-ACCESS  not-accessible
    STATUS      current
    DESCRIPTION "The index of the entry"
    ::= { mrpInterconnectionEntry 1 }

mrpInterconnectionName OBJECT-TYPE
    SYNTAX      DisplayString
    MAX-ACCESS  read-only
    STATUS      current
    DESCRIPTION "
                A logical name for the Media redundancy Interconnection domain to
                ease the management of Media redundancy Interconnection domains.
                "
    ::= { mrpInterconnectionEntry 2 }

mrpInterconnectionPort OBJECT-TYPE
    SYNTAX      Integer32
    MAX-ACCESS  read-only
    STATUS      current
    DESCRIPTION "
                The ifIndex of the layer 2 interface which is used
                as interconnection port.
                "
    ::= { mrpInterconnectionEntry 3 }

mrpInterconnectionPortState OBJECT-TYPE
    SYNTAX      INTEGER {
                    disabled(1),
                    blocked(2),
                    forwarding(3),
                    notConnected(4)
                    }
    MAX-ACCESS  read-only
    STATUS      current
    DESCRIPTION "
                Operational state of the Interconnection port.
                disabled(1) indicates that all frames are dropped.
                blocked(2) indicates that all frames are dropped except
                - MRP Interconnection topology change frames,
                - MRP Interconnection test frames,
                - MRP Interconnection link change frames,
                - MRP Interconnection link status poll frames,
                - frames from other protocols that also define to pass
                blocked(2) ports.
                forwarding(3) indicates that all frames are passed through
                according to the forwarding behavior of IEEE 802.1D.
                notConnected(4) indicates that the port has no link.
                "
    ::= { mrpInterconnectionEntry 4 }

mrpInterconnectionVlanId OBJECT-TYPE
    SYNTAX      Unsigned32
    MAX-ACCESS  read-only
    STATUS      current
    DESCRIPTION "
                The VLAN ID assigned to the MRP Interconnection protocol.
                The VLAN ID only is in use when mrpInterconnectionError
                does not signal invalidVlanId.
                If value is set to 0 no VLAN is assigned.
                "
    ::= { mrpInterconnectionEntry 5 }

mrpInterconnectionMode OBJECT-TYPE
    SYNTAX      INTEGER {
                    undefined(1),
                    lcMode(2),
                    rcMode(3)
                    }
    MAX-ACCESS  read-write
    STATUS      current
    DESCRIPTION "
                Control the MRP Interconnection mode.
                The value undefined(1) signals that the interconnection mode is
                neither set to lcMode(2) nor to rcMode(3).
                If the value is set to lcMode(2) the device in Media redundancy
                Interconnection Manager (MIM) role is using the link check mode to
                detect open or closed interconnection links.
                If the value is set to rcMode(3) the device in Media redundancy
                Interconnection Manager (MIM) role is using the ring check mode to
                detect open or closed interconnection links.
                The factory settings are recommended to adjust the
                value of this object to the lcMode(2) capability.
                If the agent restricts the write access, no matter what
                reason, it shall reject write requests by responding
                with 'badValue'.
                "
    ::= { mrpInterconnectionEntry 6 }

mrpInterconnectionAdminRole OBJECT-TYPE
    SYNTAX      INTEGER {
                    disable(0),
                    client(1),
                    manager(2)
                    }
    MAX-ACCESS  read-write
    STATUS      current
    DESCRIPTION "
                Control the MRP Interconnection behavior of the system per
                Media redundancy Interconnection domain.
                If the value is set to disable(0) the MRP Interconnection
                entity of this domain shall be disabled.
                If the value is set to client(1) the entity shall be set
                to the role of a Media redundancy Interconnection Client (MIC).
                If the value is set to manager(2) the entity shall be set
                to the role of a Media redundancy Interconnection Manager (MIM).
                The factory settings are recommended to adjust the
                value of this object to the client(1) capability of the
                component in order to prevent multiple managers are
                in the interconnection (the order of the capabilities are not
                necessarily conform to the order of the object values
                here).
                If the agent restricts the write access, no matter what
                reason, it shall reject write requests by responding
                with 'badValue'.
                "
    ::= { mrpInterconnectionEntry 7 }

mrpInterconnectionOperRole OBJECT-TYPE
    SYNTAX      INTEGER {
                    disable(0),
                    client(1),
                    manager(2)
                    }
    MAX-ACCESS  read-only
    STATUS      current
    DESCRIPTION "
                The operational role of an MRP Interconnection entity
                per Media redundancy Interconnection domain.
                A value of disabled(0) signals that the entity doesn't
                work (whatever reason).
                A value of client(1) signals that the entity is in a
                Media redundancy Interconnection Client role.
                A value of manager(2) signals that the entity is the
                manager of this Media redundancy Interconnection domain.
                "
    ::= { mrpInterconnectionEntry 8 }

mrpInterconnectionState OBJECT-TYPE
    SYNTAX      INTEGER {
                    disable(0),
                    undefined(1),
                    interconnOpen(2),
                    interconnClosed(3)
                    }
    MAX-ACCESS  read-only
    STATUS      current
    DESCRIPTION "
                Operational status of the MRP Interconnection entity.
                disable(0) - The entity is disabled.
                undefined(1) - Value is not valid.
                interconnOpen(2) - MRP Interconnection redundancy lost of this Media
                redundancy Interconnection domain.
                interconnClosed(3) - MRP Interconnection redundancy available of this Media
                redundancy Interconnection domain.
                "
    ::= { mrpInterconnectionEntry 9 }

mrpInterconnectionError OBJECT-TYPE
    SYNTAX      BITS {
                    noError(0),
                    invalidVlanId(1)
                    }
    MAX-ACCESS  read-only
    STATUS      current
    DESCRIPTION "
                Configuration status of the MRP Interconnection entity.
                noError(0) - no configuration error detected.
                invalidVlanId(1) - the assigned VLAN ID is not permitted.
                "
    ::= { mrpInterconnectionEntry 10 }

mrpInterconnectionOpenCount OBJECT-TYPE
    SYNTAX      Counter32
    MAX-ACCESS  read-only
    STATUS      current
    DESCRIPTION "
                Counter for MRP Interconnection state changes to
                interconnOpen.
                "
    ::= { mrpInterconnectionEntry 11 }

mrpInterconnectionLastOpenChange OBJECT-TYPE
    SYNTAX      TimeTicks
    MAX-ACCESS  read-only
    STATUS      current
    DESCRIPTION "
                Timeticks since last change of
                mrpInterconnectionState to interconnOpen.
                "
    ::= { mrpInterconnectionEntry 12 }

mrpInterconnectionPeerMAC OBJECT-TYPE
    SYNTAX      OCTET STRING
    MAX-ACCESS  read-only
    STATUS      current
    DESCRIPTION "
                Device-MAC-Address of the devices interconnection peer, connected
                to the devices interlink port. This variable contains
                the MAC-Address contained in the media link check frame received at the
                interconnection port.
                "
    ::= { mrpInterconnectionEntry 13 }

mrpInterconnectionOwnMRMMAC OBJECT-TYPE
    SYNTAX      OCTET STRING
    MAX-ACCESS  read-only
    STATUS      current
    DESCRIPTION "
                The device-MAC-Address of the devices ring manager (MRM).
                This variable contains the MAC-Address extracted from the
                periodically received MRP_Test frame sent by the ring manager.
                If the ring managers MAC-Address is not known, the variable shall
                contain ff-ff-ff-ff-ff-ff.
                "
    ::= { mrpInterconnectionEntry 14 }

mrpInterconnectionPeerMRMMAC OBJECT-TYPE
    SYNTAX      OCTET STRING
    MAX-ACCESS  read-only
    STATUS      current
    DESCRIPTION "
                Device-MAC-Address of devices interconnection peer's, connected
                to the devices interlink port, ring manager.
                This variable contains the MRM-MAC-Address of the peers ring manager
                contained in the media link check frame received at the interconnection port.
                If the ring managers MAC-Address is not known, the variable shall
                contain ff-ff-ff-ff-ff-ff. "
    ::= { mrpInterconnectionEntry 15 }

mrpInterconnectionPeerRingDomainUUID OBJECT-TYPE
    SYNTAX      IEC62439UuidType
    MAX-ACCESS  read-only
    STATUS      current
    DESCRIPTION "
                The domain UUID of the ring the interconnection peer's, connected
                to the devices interlink port, ring.
                This variable contains the MRM_DomainUUID of the peers ring
                contained in the media link check frame received at the interconnection port.
                "
    ::= { mrpInterconnectionEntry 16 }

-- ***********************************************************************
-- conformance statements
-- ***********************************************************************
mrpRedundancyGroups OBJECT IDENTIFIER::= { mrpConformance 1 }
mrpDomainBasicGroup OBJECT-GROUP
    OBJECTS {
            mrpDomainIndex,
            mrpDomainID,
            mrpDomainName,
            mrpDomainAdminRole,
            mrpDomainOperRole,
            mrpDomainRingPort1,
            mrpDomainRingPort1State,
            mrpDomainRingPort2,
            mrpDomainRingPort2State,
            mrpDomainState,
            mrpDomainBlocked
            }
    STATUS      current
    DESCRIPTION "
            Parameters which are necessary to monitor status of
            MRP domains.
            "
    ::= { mrpRedundancyGroups 1 }

mrpDomainManagerGroup OBJECT-GROUP
    OBJECTS {
            mrpDomainManagerPriority
            }
    STATUS  current
    DESCRIPTION "
            Parameters which are additional to monitor status of
            MRP domain managers.
            "
    ::= { mrpRedundancyGroups 2 }

mrpDomainBlockingCntrlGroup OBJECT-GROUP
    OBJECTS {
            mrpDomainMRMReactOnLinkChange
            }
    STATUS  current
    DESCRIPTION "
                Parameters which are optional to monitor and
                control blocking behavior of MRP domains.
                "
    ::= { mrpRedundancyGroups 3 }

mrpDomainDiagGroup OBJECT-GROUP
    OBJECTS {
            mrpDomainError,
            mrpDomainRingOpenCount,
            mrpDomainLastRingOpenChange,
            mrpDomainRoundTripDelayMax,
            mrpDomainRoundTripDelayMin,
            mrpDomainResetRoundTripDelays
            }
    STATUS  current
    DESCRIPTION "
            Parameters which are optional to monitor
            and control the diagnostic status of MRP domains.
            "
    ::= { mrpRedundancyGroups 4 }

mrpDomainAdvancedGroup OBJECT-GROUP
    OBJECTS {
            mrpDomainVlanId
            }
    STATUS  current
    DESCRIPTION "
            Parameters which are optional to monitor
            the status of MRP domains.
            "
    ::= { mrpRedundancyGroups 5 }

mrpInterconnectionBasicGroup OBJECT-GROUP
    OBJECTS {
            mrpInterconnectionName,
            mrpInterconnectionPort,
            mrpInterconnectionPortState,
            mrpInterconnectionAdminRole,
            mrpInterconnectionOperRole,
            mrpInterconnectionMode,
            mrpInterconnectionState
            }
    STATUS  current
    DESCRIPTION "
            Parameters which are necessary to monitor
            the status of Media redundancy
            Interconnection domains.
            "
    ::= { mrpRedundancyGroups 6 }

mrpInterconnectionDiagGroup OBJECT-GROUP
    OBJECTS {
            mrpInterconnectionError,
            mrpInterconnectionOpenCount,
            mrpInterconnectionLastOpenChange,
            mrpInterconnectionPeerMAC,
            mrpInterconnectionOwnMRMMAC,
            mrpInterconnectionPeerMRMMAC,
            mrpInterconnectionPeerRingDomainUUID
            }
    STATUS  current
    DESCRIPTION "
            Parameters which are optional to monitor
            the diagnostic status of Media
            redundancy Interconnection domains.
            "
    ::= { mrpRedundancyGroups 7 }

mrpInterconnectionAdvancedGroup OBJECT-GROUP
    OBJECTS {
            mrpInterconnectionVlanId
            }
    STATUS  current
    DESCRIPTION "
            Parameters which are optional to monitor the
            status of Media redundancy Interconnection domains.
            "
    ::= { mrpRedundancyGroups 8 }

-- ***********************************************************************
-- compliance specifications
-- ***********************************************************************
mrpRedundancyCompliances OBJECT IDENTIFIER::= { mrpConformance 2 }

mrpDomainBasicCompliance MODULE-COMPLIANCE
    STATUS      current
    DESCRIPTION "
                Basic implementation requirements for MRP support.
                The agent shall support the monitoring of redundancy
                domains.
                "
    MODULE
    MANDATORY-GROUPS {
                mrpDomainBasicGroup
                }
    GROUP       mrpDomainAdvancedGroup
    DESCRIPTION "
                For SNMP agents it is optional to support
                advanced monitoring of redundancy domains.
                "
    ::= { mrpRedundancyCompliances 1 }

mrpDomainManagerCompliance MODULE-COMPLIANCE
    STATUS      current
    DESCRIPTION "
                Manager implementation requirements for MRP
                support. The agent shall support the monitoring
                of redundancy domains.
                "
    MODULE
    MANDATORY-GROUPS {
                mrpDomainBasicGroup,
                mrpDomainManagerGroup
                }
    GROUP       mrpDomainBlockingCntrlGroup
    DESCRIPTION "
                For SNMP agents it is optional to support blocking control.
                "
    GROUP mrpDomainDiagGroup
    DESCRIPTION "
                For SNMP agents it is optional to support
                monitoring of the diagnostic status of MRP domains.
                "
    ::= { mrpRedundancyCompliances 2 }

mrpInterconnectionCompliance MODULE-COMPLIANCE
    STATUS      current
    DESCRIPTION "
                Implementation requirements for MRP Interconnection support.
                The agent shall support the monitoring of
                Media redundancy Interconnection domains.
                "
    MODULE
    MANDATORY-GROUPS {
                mrpInterconnectionBasicGroup
                }
    GROUP       mrpInterconnectionAdvancedGroup
    DESCRIPTION "
                For SNMP agents it is optional to support
                advanced monitoring of Media redundancy
                Interconnection domains.
                "
    GROUP       mrpInterconnectionDiagGroup
    DESCRIPTION "
                For SNMP agents it is optional to support
                monitoring of the diagnostic status of Media
                redundancy Interconnection domains.
                "
    ::= { mrpRedundancyCompliances 3 }
END
-- ***********************************************************************
-- EOF
-- ***********************************************************************
