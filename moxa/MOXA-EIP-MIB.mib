-- ****************************************************************
-- *  Moxa Switching - EtherNet/IP(EIP) PRIVATE MIB
-- *
-- *  Copyright (c) 2021 by Moxa Inc.
-- *  All rights reserved.
-- *****************************************************************

MOXA-EIP-MIB DEFINITIONS ::= BEGIN
    IMPORTS
        MODULE-IDENTITY, OBJECT-TYPE, Integer32,
        enterprises
            FROM SNMPv2-SMI
        TEXTUAL-CONVENTION, TruthValue
            FROM SNMPv2-TC
        systemManagement
            FROM MOXA-GENERAL-MIB;

    mxEip   MODULE-IDENTITY
        LAST-UPDATED "202209080000Z"
        ORGANIZATION "Moxa Inc."
        CONTACT-INFO
                "
                Postal: Moxa Inc.
                13F., No. 3, Sec. 4, New Taipei Blvd.
                Xinzhuang Dist., New Taipei City 242032, Taiwan, R.O.C.

                Tel: +866-2-89191230
                Web: http://www.moxa.com/
                "

        DESCRIPTION
                "The MIB module defines Moxa EtherNet/IP"

        REVISION    "202209080000Z"
        DESCRIPTION    "Initial Revision"
        ::= { systemManagement 10 }

        moxa               OBJECT IDENTIFIER ::= { enterprises 8691 } 
        general            OBJECT IDENTIFIER ::= { moxa 602 }         
        systemManagement   OBJECT IDENTIFIER ::= { general 1 }

-- -------------------------------------------------------------
-- groups in the MOXA-EIP-MIB MIB
-- -------------------------------------------------------------

  eipConfiguration     OBJECT IDENTIFIER ::= { mxEip 1 }

-- -------------------------------------------------------------
-- configuration group
-- -------------------------------------------------------------

    eipConfigGlobalEnable OBJECT-TYPE
        SYNTAX       TruthValue
        MAX-ACCESS   read-write
        STATUS       current
        DESCRIPTION
            "This object indicates if EtherNet/IP is globally enabled/disabled."
        ::= { eipConfiguration 1 }

END
