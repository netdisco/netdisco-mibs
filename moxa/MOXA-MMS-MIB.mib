-- ****************************************************************
-- *  Moxa General - MMS PRIVATE MIB
-- *
-- *  Copyright (c) 2020 by Moxa Inc.
-- *  All rights reserved.
-- *****************************************************************

MOXA-MMS-MIB DEFINITIONS ::= BEGIN
    IMPORTS
        MODULE-IDENTITY, NOTIFICATION-TYPE, OBJECT-TYPE, IpAddress, Integer32,
        enterprises
            FROM SNMPv2-SMI
        TEXTUAL-CONVENTION, DateAndTime, MacAddress, DisplayString, TruthValue, RowStatus
            FROM SNMPv2-TC;

    mxMms MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines Moxa MMS"

        REVISION    "202202170000Z"
        DESCRIPTION "update CONTACT-INFO"

        REVISION    "202010150000Z"
        DESCRIPTION "Initial Revision"

        ::= { systemManagement 8 }

	moxa               OBJECT IDENTIFIER ::= { enterprises 8691 }
	general            OBJECT IDENTIFIER ::= { moxa 602 }
	systemManagement   OBJECT IDENTIFIER ::= { general 1 }

-- -------------------------------------------------------------
-- groups in the MOXA-MMS-MIB MIB
-- -------------------------------------------------------------

  mmsConfiguration     OBJECT IDENTIFIER ::= { mxMms 1 }

-- -------------------------------------------------------------
-- configuration group
-- -------------------------------------------------------------

    mmsConfigGlobalEnable OBJECT-TYPE
        SYNTAX       TruthValue
        MAX-ACCESS   read-only
        STATUS       current
        DESCRIPTION
            "This object indicates if MMS is globally enabled/disabled."
        ::= { mmsConfiguration 1 }

    mmsConfigIEDName OBJECT-TYPE
        SYNTAX OCTET STRING (SIZE(1..20))
        MAX-ACCESS  read-only
        STATUS      current
        DESCRIPTION
            "This object indicates the IED name of MMS."
        ::= { mmsConfiguration 2 }

    mmsConfigTProfileEnable OBJECT-TYPE
        SYNTAX       TruthValue
        MAX-ACCESS   read-only
        STATUS       current
        DESCRIPTION
            "This object indicates if MMS t-profile is enabled/disabled."
        ::= { mmsConfiguration 3 }

    mmsConfigAProfileEnable OBJECT-TYPE
        SYNTAX       TruthValue
        MAX-ACCESS   read-only
        STATUS       current
        DESCRIPTION
            "This object indicates if MMS a-profile is enabled/disabled."
        ::= { mmsConfiguration 4 }

END
