-- ****************************************************************
-- *  Moxa Switching - MAC Authentication Bypass(MAB) PRIVATE MIB
-- *
-- *  Copyright (c) 2021 by Moxa Inc.
-- *  All rights reserved.
-- *****************************************************************

MOXA-MAB-MIB DEFINITIONS ::= BEGIN
    IMPORTS
        MODULE-IDENTITY, NOTIFICATION-TYPE, OBJECT-TYPE, Integer32, Counter32
            FROM SNMPv2-SMI
        TEXTUAL-CONVENTION, DateAndTime, MacAddress, DisplayString, TruthValue, RowStatus
            FROM SNMPv2-TC
        layer2Security
          FROM MOXA-SWITCHING-MIB;

    mxMab   MODULE-IDENTITY
        LAST-UPDATED "202108230000Z"
        ORGANIZATION "Moxa Inc."
        CONTACT-INFO
                "
                Postal: Moxa Inc.
                13F., No. 3, Sec. 4, New Taipei Blvd.
                Xinzhuang Dist., New Taipei City 242032, Taiwan, R.O.C.

                Tel: +866-2-89191230
                Web: http://www.moxa.com/
                "

        DESCRIPTION
                "The MIB module defines Moxa MAB"

        REVISION    "202108230000Z"
        DESCRIPTION    "Initial Revision"
        ::= { layer2Security 3 }

-- -------------------------------------------------------------
-- groups in the MOXA-MAB-MIB MIB
-- -------------------------------------------------------------

  mabConfiguration     OBJECT IDENTIFIER ::= { mxMab 1 }
  mabStatus            OBJECT IDENTIFIER ::= { mxMab 2 }

-- -------------------------------------------------------------
-- configuration group
-- -------------------------------------------------------------

    mabConfigGlobalEnable OBJECT-TYPE
        SYNTAX       TruthValue
        MAX-ACCESS   read-write
        STATUS       current
        DESCRIPTION
            "This object indicates if MAB is globally enabled/disabled."
        ::= { mabConfiguration 1 }

    mabConfigAuthMode OBJECT-TYPE
        SYNTAX  INTEGER {
                    radius(1),
                    local(2)
                }
        MAX-ACCESS  read-write
        STATUS      current
        DESCRIPTION
            "This object is used to configure for the choice of
              local or radius authentication server to be used by
              the authenticator for its authentication services."
        ::= { mabConfiguration 2 }

-- -------------------------------------------------------------
-- port table configuration
-- -------------------------------------------------------------

    mabConfigPortTable OBJECT-TYPE
        SYNTAX SEQUENCE OF MabConfigPortEntry
        MAX-ACCESS not-accessible
        STATUS     current
        DESCRIPTION
            "A table to store the port specific parameters for MAB
            like port MAB status, reauthentication and time period. And the parameters can be manipulated
            by administrators."
        ::= { mabConfiguration 3 }

    mabConfigPortEntry OBJECT-TYPE
        SYNTAX     MabConfigPortEntry
        MAX-ACCESS not-accessible
        STATUS     current
        DESCRIPTION
            "An entry appears in this Port Table represent port information about
            MAB."
        INDEX { mabConfigPortNum }
        ::= { mabConfigPortTable 1 }

    MabConfigPortEntry ::=
        SEQUENCE {
            mabConfigPortNum
                Integer32,
            mabConfigPortEnable
                TruthValue,
            mabConfigQuietPeriod
                Integer32,
            mabConfigReAuthEnable
                TruthValue,
            mabConfigReAuthPeriod
                Integer32
    }

    mabConfigPortNum OBJECT-TYPE
        SYNTAX Integer32 (1..256)
        MAX-ACCESS read-only
        STATUS     current
        DESCRIPTION
            "A unique value, greater than zero, indicating the Port number of
             port configuration table."
        ::= { mabConfigPortEntry 1 }

    mabConfigPortEnable OBJECT-TYPE
        SYNTAX     TruthValue
        MAX-ACCESS read-write
        STATUS     current
        DESCRIPTION
            "This parameter when true(1) indicates that a port is mab enabled
            and false(2) indicates that this feature is disabled
            on the port."
        ::= { mabConfigPortEntry 2 }

    mabConfigQuietPeriod OBJECT-TYPE
        SYNTAX Integer32 (5..300)
        MAX-ACCESS read-write
        STATUS     current
        DESCRIPTION
            "The value, in seconds, of the quietPeriod constant
            currently in use by the Authenticator PAE state
            machine."
        ::= { mabConfigPortEntry 3 }

    mabConfigReAuthEnable OBJECT-TYPE
        SYNTAX     TruthValue
        MAX-ACCESS read-write
        STATUS     current
        DESCRIPTION
            "The enable/disable control used by the Reauthentication
               Timer state machine"
        ::= { mabConfigPortEntry 4 }

    mabConfigReAuthPeriod OBJECT-TYPE
        SYNTAX Integer32 (60..65535)
        MAX-ACCESS read-write
        STATUS     current
        DESCRIPTION
            "The value, in seconds, of the reAuthPeriod constant
            currently in use by the Reauthentication Timer state
            machine."
        ::= { mabConfigPortEntry 5 }

-- -------------------------------------------------------------
-- local database table configuration
-- -------------------------------------------------------------

    mabConfigLocalDatabaseTable OBJECT-TYPE
        SYNTAX SEQUENCE OF MabConfigLocalDatabaseEntry
        MAX-ACCESS not-accessible
        STATUS     current
        DESCRIPTION
            "This table contains authentication related user
            configuration information maintained by MAB
            local authentication server."
        ::= { mabConfiguration 4 }

    mabConfigLocalDatabaseEntry OBJECT-TYPE
        SYNTAX     MabConfigLocalDatabaseEntry
        MAX-ACCESS not-accessible
        STATUS     current
        DESCRIPTION
            "Each entry contains unicast MAC address
            of the user seeking authentication."
        INDEX { mabConfigLocalDatabaseMac }
        ::= { mabConfigLocalDatabaseTable 1 }

    MabConfigLocalDatabaseEntry ::=
        SEQUENCE {
           mabConfigLocalDatabaseMac
                MacAddress,
           mabConfigLocalDatabaseRowStatus
                RowStatus
        }

    mabConfigLocalDatabaseMac OBJECT-TYPE
        SYNTAX     MacAddress
        MAX-ACCESS not-accessible
        STATUS     current
        DESCRIPTION
           "The source MAC address of the authenticated host in local database."
        ::= { mabConfigLocalDatabaseEntry 1 }

    mabConfigLocalDatabaseRowStatus OBJECT-TYPE
        SYNTAX     RowStatus
        MAX-ACCESS read-write
        STATUS     current
        DESCRIPTION
           "The source MAC address row status"
        ::= { mabConfigLocalDatabaseEntry 2 }

-- -------------------------------------------------------------
-- status group
-- -------------------------------------------------------------

    mabStatTotalNumOfAuthInProgressEntry OBJECT-TYPE
        SYNTAX       Counter32
        MAX-ACCESS   read-only
        STATUS       current
        DESCRIPTION
            "To represent the total number of Auth In Progress table entries in RADIUS mode."
        ::= { mabStatus 1 }

    mabStatTotalNumOfLocalAuthEntry OBJECT-TYPE
        SYNTAX       Counter32
        MAX-ACCESS   read-only
        STATUS       current
        DESCRIPTION
            "To represent the total number of authenticated address in local database mode."
        ::= { mabStatus 2 }

END
