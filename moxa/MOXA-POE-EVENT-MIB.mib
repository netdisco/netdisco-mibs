-- ****************************************************************
-- *  Moxa General (Events) - Power over Ethernet Event (POEE) PRIVATE MIB
-- *
-- *  Copyright (c) 2019 by Moxa Inc.
-- *  All rights reserved.
-- *****************************************************************

MOXA-POE-EVENT-MIB DEFINITIONS ::= BEGIN
    IMPORTS
        MODULE-IDENTITY, NOTIFICATION-TYPE, OBJECT-TYPE, IpAddress, Unsigned32,
        enterprises
            FROM SNMPv2-SMI
        TEXTUAL-CONVENTION, DateAndTime, MacAddress, DisplayString, TruthValue, RowStatus
            FROM SNMPv2-TC
        eventNotification
            FROM MOXA-GENERAL-MIB;

    mxPoeEvent MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa event notification of power over ethernet event"

        REVISION    "202202170000Z"
        DESCRIPTION "update CONTACT-INFO"

        REVISION    "201906300000Z"
        DESCRIPTION "Initial Revision"

        ::= { mxEvents 8 }

    moxa                 OBJECT IDENTIFIER ::= { enterprises 8691 }
    general              OBJECT IDENTIFIER ::= { moxa 602 }
    eventNotification    OBJECT IDENTIFIER ::= { general 7 }
    mxEvents             OBJECT IDENTIFIER ::= { eventNotification 1 }

-- -------------------------------------------------------------
-- groups in the MOXA-POE-EVENT-MIB MIB
-- -------------------------------------------------------------

  -- poeeNotification      OBJECT IDENTIFIER ::= { mxPoeEvent 0 }
  poeeConfiguration     OBJECT IDENTIFIER ::= { mxPoeEvent 1 }
  -- poeeStatus            OBJECT IDENTIFIER ::= { mxPoeEvent 2 }
  -- poeeExtensions        OBJECT IDENTIFIER ::= { mxPoeEvent 3 }

-- -------------------------------------------------------------
-- configuration group
-- -------------------------------------------------------------
-- PD Power On

    poeeConfigPdPowerOn OBJECT IDENTIFIER ::= { poeeConfiguration 1 }

    poeeConfigPdPowerOnEnable OBJECT-TYPE
        SYNTAX TruthValue
        MAX-ACCESS read-write
        STATUS current
        DESCRIPTION
            "This enables or disables the event PD Power On in the event notification.
            A value of 'true' (1) indicates that notifications are
            allowed to notify the user while the PD power on.
            A value of 'false'(2) indicates that notifications are not
            allowed to notify the user while the PD power on."
        ::= { poeeConfigPdPowerOn 1 }

    poeeConfigPdPowerOnAction OBJECT IDENTIFIER ::= { poeeConfigPdPowerOn 2 }

    poeeConfigPdPowerOnTrapEnable OBJECT-TYPE
        SYNTAX TruthValue
        MAX-ACCESS read-write
        STATUS current
        DESCRIPTION
            "This enables or disables the notification action trap in the event PD Power On.
            A value of 'true' (1) indicates that the notification action trap is
            allowed to notify the user while the PD power on.
            A value of 'false'(2) indicates that the notification action trap is not
            allowed to notify the user while the PD power on."
        ::= { poeeConfigPdPowerOnAction 1 }

    poeeConfigPdPowerOnEmailEnable OBJECT-TYPE
        SYNTAX TruthValue
        MAX-ACCESS read-write
        STATUS current
        DESCRIPTION
            "This enables or disables the notification action email in the event PD Power On.
            A value of 'true' (1) indicates that the notification action email is
            allowed to notify the user while the PD power on.
            A value of 'false'(2) indicates that the notification action email is not
            allowed to notify the user while the PD power on."
        ::= { poeeConfigPdPowerOnAction 2 }

    poeeConfigPdPowerOnMgmtRelayEnable OBJECT-TYPE
        SYNTAX TruthValue
        MAX-ACCESS read-write
        STATUS current
        DESCRIPTION
            "This enables or disables the notification action MGMT relay in the event PD Power On.
            A value of 'true' (1) indicates that the notification action MGMT relay is
            allowed to notify the user while the PD power on.
            A value of 'false'(2) indicates that the notification action MGMT relay is not
            allowed to notify the user while the PD power on."
        ::= { poeeConfigPdPowerOnAction 3 }

    poeeConfigPdPowerOnPwr1RelayEnable OBJECT-TYPE
        SYNTAX TruthValue
        MAX-ACCESS read-write
        STATUS current
        DESCRIPTION
            "This enables or disables the notification action PWR1 relay in the event PD Power On.
            A value of 'true' (1) indicates that the notification action PWR1 relay is
            allowed to notify the user while the PD power on.
            A value of 'false'(2) indicates that the notification action PWR1 relay is not
            allowed to notify the user while the PD power on."
        ::= { poeeConfigPdPowerOnAction 4 }

    poeeConfigPdPowerOnPwr2RelayEnable OBJECT-TYPE
        SYNTAX TruthValue
        MAX-ACCESS read-write
        STATUS current
        DESCRIPTION
            "This enables or disables the notification action PWR2 relay in the event PD Power On.
            A value of 'true' (1) indicates that the notification action PWR2 relay is
            allowed to notify the user while the PD power on.
            A value of 'false'(2) indicates that the notification action PWR2 relay is not
            allowed to notify the user while the PD power on."
        ::= { poeeConfigPdPowerOnAction 5 }

-- PD Power Off

    poeeConfigPdPowerOff OBJECT IDENTIFIER ::= { poeeConfiguration 2 }

    poeeConfigPdPowerOffEnable OBJECT-TYPE
        SYNTAX TruthValue
        MAX-ACCESS read-write
        STATUS current
        DESCRIPTION
            "This enables or disables the event PD Power Off in the event notification.
            A value of 'true' (1) indicates that notifications are
            allowed to notify the user while the PD power off.
            A value of 'false'(2) indicates that notifications are not
            allowed to notify the user while the PD power off."
        ::= { poeeConfigPdPowerOff 1 }

    poeeConfigPdPowerOffAction OBJECT IDENTIFIER ::= { poeeConfigPdPowerOff 2 }

    poeeConfigPdPowerOffTrapEnable OBJECT-TYPE
        SYNTAX TruthValue
        MAX-ACCESS read-write
        STATUS current
        DESCRIPTION
            "This enables or disables the notification action trap in the event PD Power Off.
            A value of 'true' (1) indicates that the notification action trap is
            allowed to notify the user while the PD power off.
            A value of 'false'(2) indicates that the notification action trap is not
            allowed to notify the user while the PD power off."
        ::= { poeeConfigPdPowerOffAction 1 }

    poeeConfigPdPowerOffEmailEnable OBJECT-TYPE
        SYNTAX TruthValue
        MAX-ACCESS read-write
        STATUS current
        DESCRIPTION
            "This enables or disables the notification action email in the event PD Power Off.
            A value of 'true' (1) indicates that the notification action email is
            allowed to notify the user while the PD power off.
            A value of 'false'(2) indicates that the notification action email is not
            allowed to notify the user while the PD power off."
        ::= { poeeConfigPdPowerOffAction 2 }

    poeeConfigPdPowerOffMgmtRelayEnable OBJECT-TYPE
        SYNTAX TruthValue
        MAX-ACCESS read-write
        STATUS current
        DESCRIPTION
            "This enables or disables the notification action MGMT relay in the event PD Power Off.
            A value of 'true' (1) indicates that the notification action MGMT relay is
            allowed to notify the user while the PD power off.
            A value of 'false'(2) indicates that the notification action MGMT relay is not
            allowed to notify the user while the PD power off."
        ::= { poeeConfigPdPowerOffAction 3 }

    poeeConfigPdPowerOffPwr1RelayEnable OBJECT-TYPE
        SYNTAX TruthValue
        MAX-ACCESS read-write
        STATUS current
        DESCRIPTION
            "This enables or disables the notification action PWR1 relay in the event PD Power Off.
            A value of 'true' (1) indicates that the notification action PWR1 relay is
            allowed to notify the user while the PD power off.
            A value of 'false'(2) indicates that the notification action PWR1 relay is not
            allowed to notify the user while the PD power off."
        ::= { poeeConfigPdPowerOffAction 4 }

    poeeConfigPdPowerOffPwr2RelayEnable OBJECT-TYPE
        SYNTAX TruthValue
        MAX-ACCESS read-write
        STATUS current
        DESCRIPTION
            "This enables or disables the notification action PWR2 relay in the event PD Power Off.
            A value of 'true' (1) indicates that the notification action PWR2 relay is
            allowed to notify the user while the PD power off.
            A value of 'false'(2) indicates that the notification action PWR2 relay is not
            allowed to notify the user while the PD power off."
        ::= { poeeConfigPdPowerOffAction 5 }

-- Low Input Voltage

    poeeConfigLowInputVolatge OBJECT IDENTIFIER ::= { poeeConfiguration 3 }

    poeeConfigLowInputVolatgeEnable OBJECT-TYPE
        SYNTAX TruthValue
        MAX-ACCESS read-write
        STATUS current
        DESCRIPTION
            "This enables or disables the event Low Input Voltage in the event notification.
            A value of 'true' (1) indicates that notifications are
            allowed to notify the user while the input volatge is lower than the spec.
            A value of 'false'(2) indicates that notifications are not
            allowed to notify the user while the input volatge is lower than the spec."
        ::= { poeeConfigLowInputVolatge 1 }

    poeeConfigLowInputVolatgeAction OBJECT IDENTIFIER ::= { poeeConfigLowInputVolatge 2 }

    poeeConfigLowInputVolatgeTrapEnable OBJECT-TYPE
        SYNTAX TruthValue
        MAX-ACCESS read-write
        STATUS current
        DESCRIPTION
            "This enables or disables the notification action trap in the event Low Input Voltage.
            A value of 'true' (1) indicates that the notification action trap is
            allowed to notify the user while the input volatge is lower than the spec.
            A value of 'false'(2) indicates that the notification action trap is not
            allowed to notify the user while the input volatge is lower than the spec."
        ::= { poeeConfigLowInputVolatgeAction 1 }

    poeeConfigLowInputVolatgeEmailEnable OBJECT-TYPE
        SYNTAX TruthValue
        MAX-ACCESS read-write
        STATUS current
        DESCRIPTION
            "This enables or disables the notification action email in the event Low Input Voltage.
            A value of 'true' (1) indicates that the notification action email is
            allowed to notify the user while the input volatge is lower than the spec.
            A value of 'false'(2) indicates that the notification action email is not
            allowed to notify the user while the input volatge is lower than the spec."
        ::= { poeeConfigLowInputVolatgeAction 2 }

    poeeConfigLowInputVolatgeMgmtRelayEnable OBJECT-TYPE
        SYNTAX TruthValue
        MAX-ACCESS read-write
        STATUS current
        DESCRIPTION
            "This enables or disables the notification action MGMT relay in the event Low Input Voltage.
            A value of 'true' (1) indicates that the notification action MGMT relay is
            allowed to notify the user while the input volatge is lower than the spec.
            A value of 'false'(2) indicates that the notification action MGMT relay is not
            allowed to notify the user while the input volatge is lower than the spec."
        ::= { poeeConfigLowInputVolatgeAction 3 }

    poeeConfigLowInputVolatgePwr1RelayEnable OBJECT-TYPE
        SYNTAX TruthValue
        MAX-ACCESS read-write
        STATUS current
        DESCRIPTION
            "This enables or disables the notification action PWR1 relay in the event Low Input Voltage.
            A value of 'true' (1) indicates that the notification action PWR1 relay is
            allowed to notify the user while the input volatge is lower than the spec.
            A value of 'false'(2) indicates that the notification action PWR1 relay is not
            allowed to notify the user while the input volatge is lower than the spec."
        ::= { poeeConfigLowInputVolatgeAction 4 }

    poeeConfigLowInputVolatgePwr2RelayEnable OBJECT-TYPE
        SYNTAX TruthValue
        MAX-ACCESS read-write
        STATUS current
        DESCRIPTION
            "This enables or disables the notification action PWR2 relay in the event Low Input Voltage.
            A value of 'true' (1) indicates that the notification action PWR2 relay is
            allowed to notify the user while the input volatge is lower than the spec.
            A value of 'false'(2) indicates that the notification action PWR2 relay is not
            allowed to notify the user while the input volatge is lower than the spec."
        ::= { poeeConfigLowInputVolatgeAction 5 }

-- PD Over Current

    poeeConfigPdOverCurrent OBJECT IDENTIFIER ::= { poeeConfiguration 4 }

    poeeConfigPdOverCurrentEnable OBJECT-TYPE
        SYNTAX TruthValue
        MAX-ACCESS read-write
        STATUS current
        DESCRIPTION
            "This enables or disables the event PD Over Current in the event notification.
            A value of 'true' (1) indicates that notifications are
            allowed to notify the user while the PD over current.
            A value of 'false'(2) indicates that notifications are not
            allowed to notify the user while the PD over current."
        ::= { poeeConfigPdOverCurrent 1 }

    poeeConfigPdOverCurrentAction OBJECT IDENTIFIER ::= { poeeConfigPdOverCurrent 2 }

    poeeConfigPdOverCurrentTrapEnable OBJECT-TYPE
        SYNTAX TruthValue
        MAX-ACCESS read-write
        STATUS current
        DESCRIPTION
            "This enables or disables the notification action trap in the event PD Over Current.
            A value of 'true' (1) indicates that the notification action trap is
            allowed to notify the user while the PD over current.
            A value of 'false'(2) indicates that the notification action trap is not
            allowed to notify the user while the PD over current."
        ::= { poeeConfigPdOverCurrentAction 1 }

    poeeConfigPdOverCurrentEmailEnable OBJECT-TYPE
        SYNTAX TruthValue
        MAX-ACCESS read-write
        STATUS current
        DESCRIPTION
            "This enables or disables the notification action email in the event PD Over Current.
            A value of 'true' (1) indicates that the notification action email is
            allowed to notify the user while the PD over current.
            A value of 'false'(2) indicates that the notification action email is not
            allowed to notify the user while the PD over current."
        ::= { poeeConfigPdOverCurrentAction 2 }

    poeeConfigPdOverCurrentMgmtRelayEnable OBJECT-TYPE
        SYNTAX TruthValue
        MAX-ACCESS read-write
        STATUS current
        DESCRIPTION
            "This enables or disables the notification action MGMT relay in the event PD Over Current.
            A value of 'true' (1) indicates that the notification action MGMT relay is
            allowed to notify the user while the PD over current.
            A value of 'false'(2) indicates that the notification action MGMT relay is not
            allowed to notify the user while the PD over current."
        ::= { poeeConfigPdOverCurrentAction 3 }

    poeeConfigPdOverCurrentPwr1RelayEnable OBJECT-TYPE
        SYNTAX TruthValue
        MAX-ACCESS read-write
        STATUS current
        DESCRIPTION
            "This enables or disables the notification action PWR1 relay in the event PD Over Current.
            A value of 'true' (1) indicates that the notification action PWR1 relay is
            allowed to notify the user while the PD over current.
            A value of 'false'(2) indicates that the notification action PWR1 relay is not
            allowed to notify the user while the PD over current."
        ::= { poeeConfigPdOverCurrentAction 4 }

    poeeConfigPdOverCurrentPwr2RelayEnable OBJECT-TYPE
        SYNTAX TruthValue
        MAX-ACCESS read-write
        STATUS current
        DESCRIPTION
            "This enables or disables the notification action PWR2 relay in the event PD Over Current.
            A value of 'true' (1) indicates that the notification action PWR2 relay is
            allowed to notify the user while the PD over current.
            A value of 'false'(2) indicates that the notification action PWR2 relay is not
            allowed to notify the user while the PD over current."
        ::= { poeeConfigPdOverCurrentAction 5 }

-- PD No Response

    poeeConfigPdNoResponse OBJECT IDENTIFIER ::= { poeeConfiguration 5 }

    poeeConfigPdNoResponseEnable OBJECT-TYPE
        SYNTAX TruthValue
        MAX-ACCESS read-write
        STATUS current
        DESCRIPTION
            "This enables or disables the event PD No Response in the event notification.
            A value of 'true' (1) indicates that notifications are
            allowed to notify the user while the PD no response.
            A value of 'false'(2) indicates that notifications are not
            allowed to notify the user while the PD no response."
        ::= { poeeConfigPdNoResponse 1 }

    poeeConfigPdNoResponseAction OBJECT IDENTIFIER ::= { poeeConfigPdNoResponse 2 }

    poeeConfigPdNoResponseTrapEnable OBJECT-TYPE
        SYNTAX TruthValue
        MAX-ACCESS read-write
        STATUS current
        DESCRIPTION
            "This enables or disables the notification action trap in the event PD No Response.
            A value of 'true' (1) indicates that the notification action trap is
            allowed to notify the user while the PD no response.
            A value of 'false'(2) indicates that the notification action trap is not
            allowed to notify the user while the PD no response."
        ::= { poeeConfigPdNoResponseAction 1 }

    poeeConfigPdNoResponseEmailEnable OBJECT-TYPE
        SYNTAX TruthValue
        MAX-ACCESS read-write
        STATUS current
        DESCRIPTION
            "This enables or disables the notification action email in the event PD No Response.
            A value of 'true' (1) indicates that the notification action email is
            allowed to notify the user while the PD no response.
            A value of 'false'(2) indicates that the notification action email is not
            allowed to notify the user while the PD no response."
        ::= { poeeConfigPdNoResponseAction 2 }

    poeeConfigPdNoResponseMgmtRelayEnable OBJECT-TYPE
        SYNTAX TruthValue
        MAX-ACCESS read-write
        STATUS current
        DESCRIPTION
            "This enables or disables the notification action MGMT relay in the event PD No Response.
            A value of 'true' (1) indicates that the notification action MGMT relay is
            allowed to notify the user while the PD no response.
            A value of 'false'(2) indicates that the notification action MGMT relay is not
            allowed to notify the user while the PD no response."
        ::= { poeeConfigPdNoResponseAction 3 }

    poeeConfigPdNoResponsePwr1RelayEnable OBJECT-TYPE
        SYNTAX TruthValue
        MAX-ACCESS read-write
        STATUS current
        DESCRIPTION
            "This enables or disables the notification action PWR1 relay in the event PD No Response.
            A value of 'true' (1) indicates that the notification action PWR1 relay is
            allowed to notify the user while the PD no response.
            A value of 'false'(2) indicates that the notification action PWR1 relay is not
            allowed to notify the user while the PD no response."
        ::= { poeeConfigPdNoResponseAction 4 }

    poeeConfigPdNoResponsePwr2RelayEnable OBJECT-TYPE
        SYNTAX TruthValue
        MAX-ACCESS read-write
        STATUS current
        DESCRIPTION
            "This enables or disables the notification action PWR2 relay in the event PD No Response.
            A value of 'true' (1) indicates that the notification action PWR2 relay is
            allowed to notify the user while the PD no response.
            A value of 'false'(2) indicates that the notification action PWR2 relay is not
            allowed to notify the user while the PD no response."
        ::= { poeeConfigPdNoResponseAction 5 }
-- Over Power Budget Limit

    poeeConfigOverPowerBudgetLimit OBJECT IDENTIFIER ::= { poeeConfiguration 6 }

    poeeConfigOverPowerBudgetLimitEnable OBJECT-TYPE
        SYNTAX TruthValue
        MAX-ACCESS read-write
        STATUS current
        DESCRIPTION
            "This enables or disables the event Over Power Budget Limit in the event notification.
            A value of 'true' (1) indicates that notifications are
            allowed to notify the user while the PD power consumption over power budget limit.
            A value of 'false'(2) indicates that notifications are not
            allowed to notify the user while the PD power consumption over power budget limit."
        ::= { poeeConfigOverPowerBudgetLimit 1 }

    poeeConfigOverPowerBudgetLimitAction OBJECT IDENTIFIER ::= { poeeConfigOverPowerBudgetLimit 2 }

    poeeConfigOverPowerBudgetLimitTrapEnable OBJECT-TYPE
        SYNTAX TruthValue
        MAX-ACCESS read-write
        STATUS current
        DESCRIPTION
            "This enables or disables the notification action trap in the event Over Power Budget Limit.
            A value of 'true' (1) indicates that the notification action trap is
            allowed to notify the user while the PD power consumption over power budget limit.
            A value of 'false'(2) indicates that the notification action trap is not
            allowed to notify the user while the PD power consumption over power budget limit."
        ::= { poeeConfigOverPowerBudgetLimitAction 1 }

    poeeConfigOverPowerBudgetLimitEmailEnable OBJECT-TYPE
        SYNTAX TruthValue
        MAX-ACCESS read-write
        STATUS current
        DESCRIPTION
            "This enables or disables the notification action email in the event Over Power Budget Limit.
            A value of 'true' (1) indicates that the notification action email is
            allowed to notify the user while the PD power consumption over power budget limit.
            A value of 'false'(2) indicates that the notification action email is not
            allowed to notify the user while the PD power consumption over power budget limit."
        ::= { poeeConfigOverPowerBudgetLimitAction 2 }

    poeeConfigOverPowerBudgetLimitMgmtRelayEnable OBJECT-TYPE
        SYNTAX TruthValue
        MAX-ACCESS read-write
        STATUS current
        DESCRIPTION
            "This enables or disables the notification action MGMT relay in the event Over Power Budget Limit.
            A value of 'true' (1) indicates that the notification action MGMT relay is
            allowed to notify the user while the PD power consumption over power budget limit.
            A value of 'false'(2) indicates that the notification action MGMT relay is not
            allowed to notify the user while the PD power consumption over power budget limit."
        ::= { poeeConfigOverPowerBudgetLimitAction 3 }

    poeeConfigOverPowerBudgetLimitPwr1RelayEnable OBJECT-TYPE
        SYNTAX TruthValue
        MAX-ACCESS read-write
        STATUS current
        DESCRIPTION
            "This enables or disables the notification action PWR1 relay in the event Over Power Budget Limit.
            A value of 'true' (1) indicates that the notification action PWR1 relay is
            allowed to notify the user while the PD power consumption over power budget limit.
            A value of 'false'(2) indicates that the notification action PWR1 relay is not
            allowed to notify the user while the PD power consumption over power budget limit."
        ::= { poeeConfigOverPowerBudgetLimitAction 4 }

    poeeConfigOverPowerBudgetLimitPwr2RelayEnable OBJECT-TYPE
        SYNTAX TruthValue
        MAX-ACCESS read-write
        STATUS current
        DESCRIPTION
            "This enables or disables the notification action PWR2 relay in the event Over Power Budget Limit.
            A value of 'true' (1) indicates that the notification action PWR2 relay is
            allowed to notify the user while the PD power consumption over power budget limit.
            A value of 'false'(2) indicates that the notification action PWR2 relay is not
            allowed to notify the user while the PD power consumption over power budget limit."
        ::= { poeeConfigOverPowerBudgetLimitAction 5 }
-- Power Detection Failure

    poeeConfigPowerDetectionFailure OBJECT IDENTIFIER ::= { poeeConfiguration 7 }

    poeeConfigPowerDetectionFailureEnable OBJECT-TYPE
        SYNTAX TruthValue
        MAX-ACCESS read-write
        STATUS current
        DESCRIPTION
            "This enables or disables the event Power Detection Failure in the event notification.
            A value of 'true' (1) indicates that notifications are
            allowed to notify the user while the power detection fail.
            A value of 'false'(2) indicates that notifications are not
            allowed to notify the user while the power detection fail."
        ::= { poeeConfigPowerDetectionFailure 1 }

    poeeConfigPowerDetectionFailureAction OBJECT IDENTIFIER ::= { poeeConfigPowerDetectionFailure 2 }

    poeeConfigPowerDetectionFailureTrapEnable OBJECT-TYPE
        SYNTAX TruthValue
        MAX-ACCESS read-write
        STATUS current
        DESCRIPTION
            "This enables or disables the notification action trap in the event Power Detection Failure.
            A value of 'true' (1) indicates that the notification action trap is
            allowed to notify the user while the power detection fail.
            A value of 'false'(2) indicates that the notification action trap is not
            allowed to notify the user while the power detection fail."
        ::= { poeeConfigPowerDetectionFailureAction 1 }

    poeeConfigPowerDetectionFailureEmailEnable OBJECT-TYPE
        SYNTAX TruthValue
        MAX-ACCESS read-write
        STATUS current
        DESCRIPTION
            "This enables or disables the notification action email in the event Power Detection Failure.
            A value of 'true' (1) indicates that the notification action email is
            allowed to notify the user while the power detection fail.
            A value of 'false'(2) indicates that the notification action email is not
            allowed to notify the user while the power detection fail."
        ::= { poeeConfigPowerDetectionFailureAction 2 }

    poeeConfigPowerDetectionFailureMgmtRelayEnable OBJECT-TYPE
        SYNTAX TruthValue
        MAX-ACCESS read-write
        STATUS current
        DESCRIPTION
            "This enables or disables the notification action MGMT relay in the event Power Detection Failure.
            A value of 'true' (1) indicates that the notification action MGMT relay is
            allowed to notify the user while the power detection fail.
            A value of 'false'(2) indicates that the notification action MGMT relay is not
            allowed to notify the user while the power detection fail."
        ::= { poeeConfigPowerDetectionFailureAction 3 }

    poeeConfigPowerDetectionFailurePwr1RelayEnable OBJECT-TYPE
        SYNTAX TruthValue
        MAX-ACCESS read-write
        STATUS current
        DESCRIPTION
            "This enables or disables the notification action PWR1 relay in the event Power Detection Failure.
            A value of 'true' (1) indicates that the notification action PWR1 relay is
            allowed to notify the user while the power detection fail.
            A value of 'false'(2) indicates that the notification action PWR1 relay is not
            allowed to notify the user while the power detection fail."
        ::= { poeeConfigPowerDetectionFailureAction 4 }

    poeeConfigPowerDetectionFailurePwr2RelayEnable OBJECT-TYPE
        SYNTAX TruthValue
        MAX-ACCESS read-write
        STATUS current
        DESCRIPTION
            "This enables or disables the notification action PWR2 relay in the event Power Detection Failure.
            A value of 'true' (1) indicates that the notification action PWR2 relay is
            allowed to notify the user while the power detection fail.
            A value of 'false'(2) indicates that the notification action PWR2 relay is not
            allowed to notify the user while the power detection fail."
        ::= { poeeConfigPowerDetectionFailureAction 5 }
-- non-PD or PD short circuited

    poeeConfigNonPdOrPdShortCircuit OBJECT IDENTIFIER ::= { poeeConfiguration 8 }

    poeeConfigNonPdOrPdShortCircuitEnable OBJECT-TYPE
        SYNTAX TruthValue
        MAX-ACCESS read-write
        STATUS current
        DESCRIPTION
            "This enables or disables the event non-PD or PD short circuited in the event notification.
            A value of 'true' (1) indicates that notifications are
            allowed to notify the user while the non-PD or PD short circuited.
            A value of 'false'(2) indicates that notifications are not
            allowed to notify the user while the non-PD or PD short circuited."
        ::= { poeeConfigNonPdOrPdShortCircuit 1 }

    poeeConfigNonPdOrPdShortCircuitAction OBJECT IDENTIFIER ::= { poeeConfigNonPdOrPdShortCircuit 2 }

    poeeConfigNonPdOrPdShortCircuitTrapEnable OBJECT-TYPE
        SYNTAX TruthValue
        MAX-ACCESS read-write
        STATUS current
        DESCRIPTION
            "This enables or disables the notification action trap in the event non-PD or PD short circuited.
            A value of 'true' (1) indicates that the notification action trap is
            allowed to notify the user while the non-PD or PD short circuited.
            A value of 'false'(2) indicates that the notification action trap is not
            allowed to notify the user while the non-PD or PD short circuited."
        ::= { poeeConfigNonPdOrPdShortCircuitAction 1 }

    poeeConfigNonPdOrPdShortCircuitEmailEnable OBJECT-TYPE
        SYNTAX TruthValue
        MAX-ACCESS read-write
        STATUS current
        DESCRIPTION
            "This enables or disables the notification action email in the event non-PD or PD short circuited.
            A value of 'true' (1) indicates that the notification action email is
            allowed to notify the user while the non-PD or PD short circuited.
            A value of 'false'(2) indicates that the notification action email is not
            allowed to notify the user while the non-PD or PD short circuited."
        ::= { poeeConfigNonPdOrPdShortCircuitAction 2 }

    poeeConfigNonPdOrPdShortCircuitMgmtRelayEnable OBJECT-TYPE
        SYNTAX TruthValue
        MAX-ACCESS read-write
        STATUS current
        DESCRIPTION
            "This enables or disables the notification action MGMT relay in the event non-PD or PD short circuited.
            A value of 'true' (1) indicates that the notification action MGMT relay is
            allowed to notify the user while the non-PD or PD short circuited.
            A value of 'false'(2) indicates that the notification action MGMT relay is not
            allowed to notify the user while the non-PD or PD short circuited."
        ::= { poeeConfigNonPdOrPdShortCircuitAction 3 }

    poeeConfigNonPdOrPdShortCircuitPwr1RelayEnable OBJECT-TYPE
        SYNTAX TruthValue
        MAX-ACCESS read-write
        STATUS current
        DESCRIPTION
            "This enables or disables the notification action PWR1 relay in the event non-PD or PD short circuited.
            A value of 'true' (1) indicates that the notification action PWR1 relay is
            allowed to notify the user while the non-PD or PD short circuited.
            A value of 'false'(2) indicates that the notification action PWR1 relay is not
            allowed to notify the user while the non-PD or PD short circuited."
        ::= { poeeConfigNonPdOrPdShortCircuitAction 4 }

    poeeConfigNonPdOrPdShortCircuitPwr2RelayEnable OBJECT-TYPE
        SYNTAX TruthValue
        MAX-ACCESS read-write
        STATUS current
        DESCRIPTION
            "This enables or disables the notification action PWR2 relay in the event non-PD or PD short circuited.
            A value of 'true' (1) indicates that the notification action PWR2 relay is
            allowed to notify the user while the non-PD or PD short circuited.
            A value of 'false'(2) indicates that the notification action PWR2 relay is not
            allowed to notify the user while the non-PD or PD short circuited."
        ::= { poeeConfigNonPdOrPdShortCircuitAction 5 }
-- -------------------------------------------------------------
-- Status group
-- -------------------------------------------------------------

END
