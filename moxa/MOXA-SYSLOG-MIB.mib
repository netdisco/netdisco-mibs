-- ******************************************************************
-- *  Moxa General (Device Diagnostics) - Syslog PRIVATE MIB
-- *
-- *  Copyright (c) 2019 by Moxa Inc.
-- *  All rights reserved.
-- *****************************************************************

MOXA-SYSLOG-MIB DEFINITIONS ::= BEGIN
    IMPORTS
        MODULE-IDENTITY, OBJECT-TYPE, IpAddress, enterprises
            FROM SNMPv2-SMI
        TEXTUAL-CONVENTION, DisplayString, TruthValue
            FROM SNMPv2-TC;

    mxSyslogServer MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa syslog"

        REVISION    "202202170000Z"
        DESCRIPTION "update CONTACT-INFO"

        REVISION    "201906300000Z"
        DESCRIPTION "Initial Revision"

        ::= { deviceDiagnostics 2 }

    moxa                 OBJECT IDENTIFIER ::= { enterprises 8691 }
    general              OBJECT IDENTIFIER ::= { moxa 602 }
    deviceDiagnostics    OBJECT IDENTIFIER ::= { general 8 }

-- -------------------------------------------------------------
-- groups in the MOXA-SYSLOG-MIB MIB
-- -------------------------------------------------------------

    syslogConfiguration OBJECT IDENTIFIER ::= { mxSyslogServer 1 }

-- -------------------------------------------------------------
-- configuration group
-- -------------------------------------------------------------

    syslogConfigEnable OBJECT-TYPE
        SYNTAX       TruthValue
        MAX-ACCESS   read-write
        STATUS       current
        DESCRIPTION
            "The administrative module status requested by management for Syslog
            Module. This enables or disables Syslog in the system. "
        ::= { syslogConfiguration 1 }

-- Syslog Server Table Configuration Start

    syslogConfigSyslogServerTable OBJECT-TYPE
        SYNTAX SEQUENCE OF SyslogConfigSyslogServerEntry
        MAX-ACCESS not-accessible
        STATUS current
        DESCRIPTION
            "The table listing the Syslog servers with
                 which the client shares a secret."
        ::= { syslogConfiguration 2 }

    syslogConfigSyslogServerEntry OBJECT-TYPE
        SYNTAX SyslogConfigSyslogServerEntry
        MAX-ACCESS not-accessible
        STATUS current
        DESCRIPTION
            "An entry representing a Syslog server
                 which the client send the log messages."
        INDEX { syslogConfigServerNum }
        ::= { syslogConfigSyslogServerTable 1 }

    SyslogConfigSyslogServerEntry ::=
        SEQUENCE {
           syslogConfigServerNum          Integer32,
           syslogConfigServerEnable       TruthValue,
           syslogConfigServerAddress      DisplayString,
           syslogConfigServerUdpPort      Integer32
        }

    syslogConfigServerNum OBJECT-TYPE
        SYNTAX Integer32 (1..3)
        MAX-ACCESS not-accessible
        STATUS current
        DESCRIPTION
            "A unique value, greater than zero, indicating the Server number in
             syslog server table."
        ::= { syslogConfigSyslogServerEntry 1 }

    syslogConfigServerEnable OBJECT-TYPE
        SYNTAX      TruthValue
        MAX-ACCESS  read-write
        STATUS      current
        DESCRIPTION
            "Enables or disables the Syslog Server."
        ::= { syslogConfigSyslogServerEntry 2 }

    syslogConfigServerAddress OBJECT-TYPE
        SYNTAX DisplayString
        MAX-ACCESS read-write
        STATUS current
        DESCRIPTION
            "The Syslog server address referred to in this table entry."
        ::= { syslogConfigSyslogServerEntry 3 }

    syslogConfigServerUdpPort OBJECT-TYPE
        SYNTAX Integer32 (1..65535)
        MAX-ACCESS read-write
        STATUS current
        DESCRIPTION
            "To indicate UDP port in which the Syslog Server entry place."
        ::= { syslogConfigSyslogServerEntry 4 }

END
