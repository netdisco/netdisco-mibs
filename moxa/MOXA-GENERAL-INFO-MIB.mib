-- ****************************************************************
-- *  Moxa Product - General Information PRIVATE MIB
-- *
-- *  Copyright (c) 2019 by Moxa Inc.
-- *  All rights reserved.
-- *****************************************************************

MOXA-GENERAL-INFO-MIB DEFINITIONS ::= BEGIN
    IMPORTS
        MODULE-IDENTITY, NOTIFICATION-TYPE, OBJECT-TYPE, IpAddress, TimeTicks, enterprises,
        Counter32
            FROM SNMPv2-SMI
        TEXTUAL-CONVENTION, DateAndTime, MacAddress, DisplayString, TruthValue, RowStatus
            FROM SNMPv2-TC;

    mxGeneralInfo MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "This MIB module defines Moxa general information"

        REVISION    "202202170000Z"
        DESCRIPTION "update CONTACT-INFO"

        REVISION    "201906300000Z"
        DESCRIPTION "Initial Revision"

        ::= { product 2 }

    moxa                 OBJECT IDENTIFIER ::= { enterprises 8691 }
    product              OBJECT IDENTIFIER ::= { moxa 600 }

-- -------------------------------------------------------------
-- groups in the MOXA-GENERAL-INFO-MIB MIB
-- -------------------------------------------------------------

  -- genInfoNotification    OBJECT IDENTIFIER ::= { mxGeneralInfo 0 }
  -- genInfoConfiguration   OBJECT IDENTIFIER ::= { mxGeneralInfo 1 }
  genInfoStatus          OBJECT IDENTIFIER ::= { mxGeneralInfo 2 }
  -- genInfoExtensions      OBJECT IDENTIFIER ::= { mxGeneralInfo 3 }

-- -------------------------------------------------------------
-- groups in the genInfoStatus
-- -------------------------------------------------------------

    devicePortNumber OBJECT-TYPE
        SYNTAX      Counter32
        MAX-ACCESS  read-only
        STATUS      current
        DESCRIPTION
            "Number of device ports."
        ::= { genInfoStatus 1 }

    deviceMacAddress OBJECT-TYPE
        SYNTAX      MacAddress
        MAX-ACCESS  read-only
        STATUS      current
        DESCRIPTION
            "Device mac address."
        ::= { genInfoStatus 2 }

    deviceSerialNumber OBJECT-TYPE
        SYNTAX      DisplayString
        MAX-ACCESS  read-only
        STATUS      current
        DESCRIPTION
            "Device serial number."
        ::= { genInfoStatus 3 }

    deviceModelName OBJECT-TYPE
        SYNTAX      DisplayString
        MAX-ACCESS  read-only
        STATUS      current
        DESCRIPTION
            "Device Model Name."
        ::= { genInfoStatus 4 }

    deviceProductRevision OBJECT-TYPE
        SYNTAX      DisplayString
        MAX-ACCESS  read-only
        STATUS      current
        DESCRIPTION
            "Device Product Revision."
        ::= { genInfoStatus 5 }

END
