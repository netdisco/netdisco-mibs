-- *****************************************************************
-- *  Moxa General (Device Diagnostics) - Locater PRIVATE MIB
-- *
-- *  Copyright (c) 2019 by Moxa Inc.
-- *  All rights reserved.
-- *****************************************************************

MOXA-LOCATOR-MIB DEFINITIONS ::= BEGIN
    IMPORTS
        MODULE-IDENTITY, OBJECT-TYPE, Integer32,
        enterprises
            FROM SNMPv2-SMI
        TEXTUAL-CONVENTION
            FROM SNMPv2-TC
        deviceDiagnostics
            FROM MOXA-GENERAL-MIB;

    mxLocator MODULE-IDENTITY
        LAST-UPDATED "202202170000Z"
        ORGANIZATION "Moxa Inc."
        CONTACT-INFO
            "
            Postal: Moxa Inc.
            13F., No. 3, Sec. 4, New Taipei Blvd.
            Xinzhuang Dist., New Taipei City 242032, Taiwan, R.O.C.

            Tel: +866-2-89191230
            Web: http://www.moxa.com/
            "
        DESCRIPTION
            "The MIB module defines locator of moxa device"

        REVISION    "202202170000Z"
        DESCRIPTION "update CONTACT-INFO"

        REVISION    "201906300000Z"
        DESCRIPTION "Initial Revision"

        ::= { deviceDiagnostics 5 }

    moxa                 OBJECT IDENTIFIER ::= { enterprises 8691 }
    general              OBJECT IDENTIFIER ::= { moxa 602 }
    deviceDiagnostics    OBJECT IDENTIFIER ::= { general 8 }

-- -------------------------------------------------------------
-- groups in the MOXA-LOCATOR-MIB MIB
-- -------------------------------------------------------------

    -- locatorNotification OBJECT IDENTIFIER ::= { mxLocator 0 }
    locatorConfiguration OBJECT IDENTIFIER ::= { mxLocator 1 }
    -- locatorStatus OBJECT IDENTIFIER ::= { mxLocator 2 }
    -- locatorExtensions OBJECT IDENTIFIER ::= { mxLocator 3 }

-- -------------------------------------------------------------
-- configuration group
-- -------------------------------------------------------------

    locatorConfigActivate OBJECT-TYPE
        SYNTAX      Integer32 (30..300)
        MAX-ACCESS  read-write
        STATUS      current
        DESCRIPTION
                "Activate locator with duration of provided value in seconds"
        ::= { locatorConfiguration 1 }

END
