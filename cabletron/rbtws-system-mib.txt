RBTWS-SYSTEM-MIB DEFINITIONS ::= BEGIN

IMPORTS
    MODULE-IDENTITY, OBJECT-TYPE,
    Unsigned32
        FROM SNMPv2-SMI
    rbtwsMibs
        FROM RBTWS-ROOT-MIB
        ;

rbtwsSystemMib MODULE-IDENTITY
    LAST-UPDATED "200611090059Z"
    ORGANIZATION "Enterasys Networks"
    CONTACT-INFO
        "www.enterasys.com"
    DESCRIPTION
        "System objects for Enterasys Networks wireless switches.

        Copyright 2006 Enterasys Networks, Inc.
        All rights reserved.
        This SNMP Management Information Base
        Specification (Specification) embodies
        confidential and proprietary intellectual property.

        This Specification is supplied 'AS IS' and Enterasys Networks
        makes no warranty, either express or implied, as to the use,
        operation, condition, or performance of the Specification."

    REVISION "200611090004Z"
    DESCRIPTION "v1.0.3: Removed unused imports"

    REVISION "200606060003Z"
    DESCRIPTION "v1.0.2: Initial version, for 5.0 release"

    ::= { rbtwsMibs 8 }

-- Object definitions

--
-- The System MIB Tree
--

rbtwsSysObjects    OBJECT IDENTIFIER ::= { rbtwsSystemMib 1 }
rbtwsSysDataObjects  OBJECT IDENTIFIER ::= { rbtwsSysObjects 1 }


rbtwsSysCpuMemoryUsedBytes OBJECT-TYPE
    SYNTAX      Unsigned32
    MAX-ACCESS  read-only
    STATUS      current
    DESCRIPTION
        "CPU memory used in bytes."
    ::= { rbtwsSysDataObjects 1 }

rbtwsSysCpuMemoryTotalBytes OBJECT-TYPE
    SYNTAX      Unsigned32
    MAX-ACCESS  read-only
    STATUS      current
    DESCRIPTION
        "CPU total physical memory in bytes."
    ::= { rbtwsSysDataObjects 2 }

rbtwsSysFlashMemoryUsedBytes OBJECT-TYPE
    SYNTAX      Unsigned32
    MAX-ACCESS  read-only
    STATUS      current
    DESCRIPTION
        "Flash memory used in bytes."
    ::= { rbtwsSysDataObjects 3 }

rbtwsSysFlashMemoryTotalBytes OBJECT-TYPE
    SYNTAX      Unsigned32
    MAX-ACCESS  read-only
    STATUS      current
    DESCRIPTION
        "Flash memory available in bytes."
    ::= { rbtwsSysDataObjects 4 }

rbtwsSysCpuAverageLoad OBJECT-TYPE
    SYNTAX      Unsigned32 (0..100)
    MAX-ACCESS  read-only
    STATUS      current
    DESCRIPTION
        "CPU load average."
    ::= { rbtwsSysDataObjects 5 }

END
