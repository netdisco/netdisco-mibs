RBTWS-AP-STATUS-MIB DEFINITIONS ::= BEGIN

IMPORTS
    MODULE-COMPLIANCE, OBJECT-GROUP
        FROM SNMPv2-CONF
    MODULE-IDENTITY, OBJECT-TYPE,
    IpAddress, Unsigned32
        FROM SNMPv2-SMI
    DisplayString, MacAddress
        FROM SNMPv2-TC
    RbtwsApAttachType, RbtwsApState, RbtwsApSerialNum, RbtwsApFingerprint,
    RbtwsRadioNum, RbtwsPowerLevel, RbtwsChannelNum,
    RbtwsRadioEnable, RbtwsRadioConfigState, RbtwsApPortOrDapNum
        FROM RBTWS-AP-TC
    rbtwsMibs
        FROM RBTWS-ROOT-MIB;


rbtwsApStatusMib MODULE-IDENTITY
    LAST-UPDATED "200607291640Z"
    ORGANIZATION "Enterasys Networks"
    CONTACT-INFO
        "www.enterasys.com"
    DESCRIPTION
        "AP Status objects for Enterasys Networks wireless switches.

        AP = Access Point;
        AC = Access Controller (wireless switch),
             the device that runs a SNMP Agent implementing this MIB.

        Copyright 2006 Enterasys Networks, Inc.
        All rights reserved.
        This SNMP Management Information Base
        Specification (Specification) embodies
        confidential and proprietary intellectual property.

        This Specification is supplied 'AS IS' and Enterasys Networks
        makes no warranty, either express or implied, as to the use,
        operation, condition, or performance of the Specification."

    REVISION "200607280033Z"
    DESCRIPTION "v2.0.2: Removed unused imports"

    REVISION "200607280032Z"
    DESCRIPTION "v2.0.1: Fixed imports and compliance group"

    REVISION "200605100017Z"
    DESCRIPTION "v2.0: Adding number of client sessions per AP, radio."

    REVISION "200603300016Z"
    DESCRIPTION "v1.0: Initial version, for 4.1 release"

    ::= { rbtwsMibs 5 }


-- Object definitions

--
-- The AP Status MIB Tree
--

rbtwsApStatusObjects    OBJECT IDENTIFIER ::= { rbtwsApStatusMib 1 }
rbtwsApStatDataObjects  OBJECT IDENTIFIER ::= { rbtwsApStatusObjects 1 }


-- ==================================
--
-- Scalars
--

rbtwsApStatNumAps OBJECT-TYPE
    SYNTAX      Unsigned32
    MAX-ACCESS  read-only
    STATUS      current
    DESCRIPTION
        "Number of APs present and seen by AC (AP in ''ALIVE'' state)."
    ::= { rbtwsApStatDataObjects 1 }


-- ==================================
-- AP Status table

rbtwsApStatApStatusTable OBJECT-TYPE
    SYNTAX      SEQUENCE OF RbtwsApStatApStatusEntry
    MAX-ACCESS  not-accessible
    STATUS      current
    DESCRIPTION
        "A table describing all the APs currently present
        and managed by this AC (APs in ''ALIVE'' state).
        Same data is available indexed by MAC in
        'rbtwsApStatApStatusMacTable'."
    ::= { rbtwsApStatDataObjects 2 }

rbtwsApStatApStatusEntry OBJECT-TYPE
    SYNTAX      RbtwsApStatApStatusEntry
    MAX-ACCESS  not-accessible
    STATUS      current
    DESCRIPTION
        "Information about a particular AP attached to the AC."
    INDEX   { rbtwsApStatApStatusSerialNum }
    ::= { rbtwsApStatApStatusTable 1 }

RbtwsApStatApStatusEntry ::= SEQUENCE {
        rbtwsApStatApStatusSerialNum      RbtwsApSerialNum,

        rbtwsApStatApStatusBaseMac        MacAddress,

        rbtwsApStatApStatusAttachType     RbtwsApAttachType,
        rbtwsApStatApStatusPortOrDapNum   RbtwsApPortOrDapNum,

        rbtwsApStatApStatusApState        RbtwsApState,
        rbtwsApStatApStatusModel          DisplayString,
        rbtwsApStatApStatusFingerprint    RbtwsApFingerprint,
        rbtwsApStatApStatusApName         DisplayString,

        rbtwsApStatApStatusVlan           DisplayString,
        rbtwsApStatApStatusIpAddress      IpAddress,
        rbtwsApStatApStatusUptimeSecs     Unsigned32,

        rbtwsApStatApStatusCpuInfo        DisplayString,
        rbtwsApStatApStatusManufacturerId DisplayString,
        rbtwsApStatApStatusRamBytes       Unsigned32,
        rbtwsApStatApStatusHardwareRev    DisplayString,

        rbtwsApStatApStatusClientSessions Unsigned32
    }

rbtwsApStatApStatusSerialNum OBJECT-TYPE
    SYNTAX      RbtwsApSerialNum
    MAX-ACCESS  not-accessible
    STATUS      current
    DESCRIPTION
        "The Serial Number of this AP."
    ::= { rbtwsApStatApStatusEntry 1 }

rbtwsApStatApStatusBaseMac OBJECT-TYPE
    SYNTAX      MacAddress
    MAX-ACCESS  read-only
    STATUS      current
    DESCRIPTION
        "The Base MAC address of this AP."
    ::= { rbtwsApStatApStatusEntry 2 }

rbtwsApStatApStatusAttachType OBJECT-TYPE
    SYNTAX      RbtwsApAttachType
    MAX-ACCESS  read-only
    STATUS      current
    DESCRIPTION
        "How this AP is attached to the AC
        (directly or via L2/L3 network)."
    ::= { rbtwsApStatApStatusEntry 3 }

rbtwsApStatApStatusPortOrDapNum OBJECT-TYPE
    SYNTAX      RbtwsApPortOrDapNum
    MAX-ACCESS  read-only
    STATUS      current
    DESCRIPTION
        "The Port Number if this AP is directly attached,
        or the CLI-assigned DAP Number if attached via L2/L3 network."
    ::= { rbtwsApStatApStatusEntry 4 }

rbtwsApStatApStatusApState OBJECT-TYPE
    SYNTAX      RbtwsApState
    MAX-ACCESS  read-only
    STATUS      current
    DESCRIPTION
        "The State of this AP."
    ::= { rbtwsApStatApStatusEntry 5 }

rbtwsApStatApStatusModel OBJECT-TYPE
    SYNTAX      DisplayString
    MAX-ACCESS  read-only
    STATUS      current
    DESCRIPTION
        "The Model name of this AP."
    ::= { rbtwsApStatApStatusEntry 6 }

rbtwsApStatApStatusFingerprint OBJECT-TYPE
    SYNTAX      RbtwsApFingerprint
    MAX-ACCESS  read-only
    STATUS      current
    DESCRIPTION
        "The RSA key fingerprint configured on this AP (binary value:
        it is the MD5 hash of the public key of the RSA key pair).
        For directly attached APs the fingerprint is a zero length string."
    ::= { rbtwsApStatApStatusEntry 7 }

rbtwsApStatApStatusApName OBJECT-TYPE
    SYNTAX      DisplayString
    MAX-ACCESS  read-only
    STATUS      current
    DESCRIPTION
        "The name of this AP, as assigned in AC's CLI;
        defaults to <Access-Type><Number> (examples: 'MP01', 'DMP23');
        could have been changed from CLI to a meaningful name,
        for example the location of the AP (example: 'MeetingRoom73')."
    ::= { rbtwsApStatApStatusEntry 8 }

rbtwsApStatApStatusVlan OBJECT-TYPE
    SYNTAX      DisplayString
    MAX-ACCESS  read-only
    STATUS      current
    DESCRIPTION
        "The name of the VLAN associated with this DAP.
        Only valid for network attached APs, otherwise zero length string."
    ::= { rbtwsApStatApStatusEntry 9 }

rbtwsApStatApStatusIpAddress OBJECT-TYPE
    SYNTAX      IpAddress
    MAX-ACCESS  read-only
    STATUS      current
    DESCRIPTION
        "The IP Address of this DAP.
        Only valid for network attached APs, otherwise 0.0.0.0."
    ::= { rbtwsApStatApStatusEntry 10 }

rbtwsApStatApStatusUptimeSecs OBJECT-TYPE
    SYNTAX      Unsigned32
    MAX-ACCESS  read-only
    STATUS      current
    DESCRIPTION
        "Time in seconds since this AP's last boot."
    ::= { rbtwsApStatApStatusEntry 11 }

rbtwsApStatApStatusCpuInfo OBJECT-TYPE
    SYNTAX      DisplayString
    MAX-ACCESS  read-only
    STATUS      current
    DESCRIPTION
        "Information about this AP's CPU."
    ::= { rbtwsApStatApStatusEntry 12 }

rbtwsApStatApStatusManufacturerId OBJECT-TYPE
    SYNTAX      DisplayString
    MAX-ACCESS  read-only
    STATUS      current
    DESCRIPTION
        "Information about this AP's manufacturer."
    ::= { rbtwsApStatApStatusEntry 13 }

rbtwsApStatApStatusRamBytes OBJECT-TYPE
    SYNTAX      Unsigned32
    MAX-ACCESS  read-only
    STATUS      current
    DESCRIPTION
        "The memory capacity of this AP (in bytes)."
    ::= { rbtwsApStatApStatusEntry 14 }

rbtwsApStatApStatusHardwareRev OBJECT-TYPE
    SYNTAX      DisplayString
    MAX-ACCESS  read-only
    STATUS      current
    DESCRIPTION
        "The hardware revision of this AP (e.g. 'A3')."
    ::= { rbtwsApStatApStatusEntry 15 }

rbtwsApStatApStatusClientSessions OBJECT-TYPE
    SYNTAX      Unsigned32
    MAX-ACCESS  read-only
    STATUS      current
    DESCRIPTION
        "The number of client sessions on this AP."
    ::= { rbtwsApStatApStatusEntry 16 }


-- ===================================
-- AP Status table indexed by Base MAC

rbtwsApStatApStatusMacTable OBJECT-TYPE
    SYNTAX      SEQUENCE OF RbtwsApStatApStatusMacEntry
    MAX-ACCESS  not-accessible
    STATUS      current
    DESCRIPTION
        "A table describing all the APs currently present
        and managed by this AC (APs in ''ALIVE'' state).
        Same data is available indexed by Serial Number in
        'rbtwsApStatApStatusTable'."
    ::= { rbtwsApStatDataObjects 3 }

rbtwsApStatApStatusMacEntry OBJECT-TYPE
    SYNTAX      RbtwsApStatApStatusMacEntry
    MAX-ACCESS  not-accessible
    STATUS      current
    DESCRIPTION
        "Information about a particular AP attached to the AC."
    INDEX   { rbtwsApStatApStatusMacBaseMac }
    ::= { rbtwsApStatApStatusMacTable 1 }

RbtwsApStatApStatusMacEntry ::= SEQUENCE {
        rbtwsApStatApStatusMacBaseMac        MacAddress,

        rbtwsApStatApStatusMacSerialNum      RbtwsApSerialNum,

        rbtwsApStatApStatusMacAttachType     RbtwsApAttachType,
        rbtwsApStatApStatusMacPortOrDapNum   RbtwsApPortOrDapNum,

        rbtwsApStatApStatusMacApState        RbtwsApState,
        rbtwsApStatApStatusMacModel          DisplayString,
        rbtwsApStatApStatusMacFingerprint    RbtwsApFingerprint,
        rbtwsApStatApStatusMacApName         DisplayString,

        rbtwsApStatApStatusMacVlan           DisplayString,
        rbtwsApStatApStatusMacIpAddress      IpAddress,
        rbtwsApStatApStatusMacUptimeSecs     Unsigned32,

        rbtwsApStatApStatusMacCpuInfo        DisplayString,
        rbtwsApStatApStatusMacManufacturerId DisplayString,
        rbtwsApStatApStatusMacRamBytes       Unsigned32,
        rbtwsApStatApStatusMacHardwareRev    DisplayString,

        rbtwsApStatApStatusMacClientSessions Unsigned32
    }

rbtwsApStatApStatusMacBaseMac OBJECT-TYPE
    SYNTAX      MacAddress
    MAX-ACCESS  not-accessible
    STATUS      current
    DESCRIPTION
        "The Base MAC address of this AP."
    ::= { rbtwsApStatApStatusMacEntry 1 }

rbtwsApStatApStatusMacSerialNum OBJECT-TYPE
    SYNTAX      RbtwsApSerialNum
    MAX-ACCESS  read-only
    STATUS      current
    DESCRIPTION
        "The Serial Number of this AP."
    ::= { rbtwsApStatApStatusMacEntry 2 }

rbtwsApStatApStatusMacAttachType OBJECT-TYPE
    SYNTAX      RbtwsApAttachType
    MAX-ACCESS  read-only
    STATUS      current
    DESCRIPTION
        "How this AP is attached to the AC
        (directly or via L2/L3 network)."
    ::= { rbtwsApStatApStatusMacEntry 3 }

rbtwsApStatApStatusMacPortOrDapNum OBJECT-TYPE
    SYNTAX      RbtwsApPortOrDapNum
    MAX-ACCESS  read-only
    STATUS      current
    DESCRIPTION
        "The Port Number if this AP is directly attached,
        or the CLI-assigned DAP Number if attached via L2/L3 network."
    ::= { rbtwsApStatApStatusMacEntry 4 }

rbtwsApStatApStatusMacApState OBJECT-TYPE
    SYNTAX      RbtwsApState
    MAX-ACCESS  read-only
    STATUS      current
    DESCRIPTION
        "The State of this AP."
    ::= { rbtwsApStatApStatusMacEntry 5 }

rbtwsApStatApStatusMacModel OBJECT-TYPE
    SYNTAX      DisplayString
    MAX-ACCESS  read-only
    STATUS      current
    DESCRIPTION
        "The Model name of this AP."
    ::= { rbtwsApStatApStatusMacEntry 6 }

rbtwsApStatApStatusMacFingerprint OBJECT-TYPE
    SYNTAX      RbtwsApFingerprint
    MAX-ACCESS  read-only
    STATUS      current
    DESCRIPTION
        "The RSA key fingerprint configured on this AP (binary value:
        it is the MD5 hash of the public key of the RSA key pair).
        For directly attached APs the fingerprint is a zero length string."
    ::= { rbtwsApStatApStatusMacEntry 7 }

rbtwsApStatApStatusMacApName OBJECT-TYPE
    SYNTAX      DisplayString
    MAX-ACCESS  read-only
    STATUS      current
    DESCRIPTION
        "The name of this AP, as assigned in AC's CLI;
        defaults to <Access-Type><Number> (examples: 'MP01', 'DMP23');
        could have been changed from CLI to a meaningful name,
        for example the location of the AP (example: 'MeetingRoom73')."
    ::= { rbtwsApStatApStatusMacEntry 8 }

rbtwsApStatApStatusMacVlan OBJECT-TYPE
    SYNTAX      DisplayString
    MAX-ACCESS  read-only
    STATUS      current
    DESCRIPTION
        "The name of the VLAN associated with this DAP.
        Only valid for network attached APs, otherwise zero length string."
    ::= { rbtwsApStatApStatusMacEntry 9 }

rbtwsApStatApStatusMacIpAddress OBJECT-TYPE
    SYNTAX      IpAddress
    MAX-ACCESS  read-only
    STATUS      current
    DESCRIPTION
        "The IP Address of this DAP.
        Only valid for network attached APs, otherwise 0.0.0.0."
    ::= { rbtwsApStatApStatusMacEntry 10 }

rbtwsApStatApStatusMacUptimeSecs OBJECT-TYPE
    SYNTAX      Unsigned32
    MAX-ACCESS  read-only
    STATUS      current
    DESCRIPTION
        "Time in seconds since this AP's last boot."
    ::= { rbtwsApStatApStatusMacEntry 11 }

rbtwsApStatApStatusMacCpuInfo OBJECT-TYPE
    SYNTAX      DisplayString
    MAX-ACCESS  read-only
    STATUS      current
    DESCRIPTION
        "Information about this AP's CPU."
    ::= { rbtwsApStatApStatusMacEntry 12 }

rbtwsApStatApStatusMacManufacturerId OBJECT-TYPE
    SYNTAX      DisplayString
    MAX-ACCESS  read-only
    STATUS      current
    DESCRIPTION
        "Information about this AP's manufacturer."
    ::= { rbtwsApStatApStatusMacEntry 13 }

rbtwsApStatApStatusMacRamBytes OBJECT-TYPE
    SYNTAX      Unsigned32
    MAX-ACCESS  read-only
    STATUS      current
    DESCRIPTION
        "The memory capacity of this AP (in bytes)."
    ::= { rbtwsApStatApStatusMacEntry 14 }

rbtwsApStatApStatusMacHardwareRev OBJECT-TYPE
    SYNTAX      DisplayString
    MAX-ACCESS  read-only
    STATUS      current
    DESCRIPTION
        "The hardware revision of this AP (e.g. 'A3')."
    ::= { rbtwsApStatApStatusMacEntry 15 }

rbtwsApStatApStatusMacClientSessions OBJECT-TYPE
    SYNTAX      Unsigned32
    MAX-ACCESS  read-only
    STATUS      current
    DESCRIPTION
        "The number of client sessions on this AP."
    ::= { rbtwsApStatApStatusMacEntry 16 }


-- ==================================
-- Radio Status table

rbtwsApStatRadioStatusTable OBJECT-TYPE
    SYNTAX      SEQUENCE OF RbtwsApStatRadioStatusEntry
    MAX-ACCESS  not-accessible
    STATUS      current
    DESCRIPTION
        "A table describing the radios on all the APs currently present
        and managed by this AC (APs in ''ALIVE'' state).
        Same data is available indexed by Radio Base MAC in
        'rbtwsApStatRadioStatusMacTable'."
    ::= { rbtwsApStatDataObjects 4 }

rbtwsApStatRadioStatusEntry OBJECT-TYPE
    SYNTAX      RbtwsApStatRadioStatusEntry
    MAX-ACCESS  not-accessible
    STATUS      current
    DESCRIPTION
        "Information about a particular radio on an AP attached to the AC."
    INDEX   { rbtwsApStatRadioStatusApSerialNum,
              rbtwsApStatRadioStatusRadioNum }
    ::= { rbtwsApStatRadioStatusTable 1 }

RbtwsApStatRadioStatusEntry ::= SEQUENCE {
        rbtwsApStatRadioStatusApSerialNum    RbtwsApSerialNum,
        rbtwsApStatRadioStatusRadioNum       RbtwsRadioNum,
        rbtwsApStatRadioStatusBaseMac        MacAddress,

        rbtwsApStatRadioStatusEnable             RbtwsRadioEnable,
        rbtwsApStatRadioStatusRadioConfigState   RbtwsRadioConfigState,
        rbtwsApStatRadioStatusCurrentPowerLevel  RbtwsPowerLevel,
        rbtwsApStatRadioStatusCurrentChannelNum  RbtwsChannelNum,

        rbtwsApStatRadioStatusClientSessions     Unsigned32
    }

rbtwsApStatRadioStatusApSerialNum OBJECT-TYPE
    SYNTAX      RbtwsApSerialNum
    MAX-ACCESS  not-accessible
    STATUS      current
    DESCRIPTION
        "The Serial Number of the AP containing this radio."
    ::= { rbtwsApStatRadioStatusEntry 1 }

rbtwsApStatRadioStatusRadioNum OBJECT-TYPE
    SYNTAX      RbtwsRadioNum
    MAX-ACCESS  not-accessible
    STATUS      current
    DESCRIPTION
        "The Number of this Radio on the AP."
    ::= { rbtwsApStatRadioStatusEntry 2 }

rbtwsApStatRadioStatusBaseMac OBJECT-TYPE
    SYNTAX      MacAddress
    MAX-ACCESS  read-only
    STATUS      current
    DESCRIPTION
        "The Base MAC address of this radio."
    ::= { rbtwsApStatRadioStatusEntry 3 }

rbtwsApStatRadioStatusEnable OBJECT-TYPE
    SYNTAX      RbtwsRadioEnable
    MAX-ACCESS  read-only
    STATUS      current
    DESCRIPTION
        "The configured mode (enable/disable) of this radio."
    ::= { rbtwsApStatRadioStatusEntry 4 }

rbtwsApStatRadioStatusRadioConfigState OBJECT-TYPE
    SYNTAX      RbtwsRadioConfigState
    MAX-ACCESS  read-only
    STATUS      current
    DESCRIPTION
        "The configuration state of this radio (INIT, FAIL, OK)."
    ::= { rbtwsApStatRadioStatusEntry 5 }

rbtwsApStatRadioStatusCurrentPowerLevel OBJECT-TYPE
    SYNTAX      RbtwsPowerLevel
    MAX-ACCESS  read-only
    STATUS      current
    DESCRIPTION
        "The Current Power Level of this radio."
    ::= { rbtwsApStatRadioStatusEntry 6 }

rbtwsApStatRadioStatusCurrentChannelNum OBJECT-TYPE
    SYNTAX      RbtwsChannelNum
    MAX-ACCESS  read-only
    STATUS      current
    DESCRIPTION
        "The Current Channel Number of this radio."
    ::= { rbtwsApStatRadioStatusEntry 7 }

rbtwsApStatRadioStatusClientSessions OBJECT-TYPE
    SYNTAX      Unsigned32
    MAX-ACCESS  read-only
    STATUS      current
    DESCRIPTION
        "The number of client sessions on this radio."
    ::= { rbtwsApStatRadioStatusEntry 8 }


-- ============================================
-- Radio Status table indexed by Radio Base MAC

rbtwsApStatRadioStatusMacTable OBJECT-TYPE
    SYNTAX      SEQUENCE OF RbtwsApStatRadioStatusMacEntry
    MAX-ACCESS  not-accessible
    STATUS      current
    DESCRIPTION
        "A table describing the radios on all the APs currently present
        and managed by this AC (APs in ''ALIVE'' state).
        Same data is available indexed by AP Serial Number and Radio Number in
        'rbtwsApStatRadioStatusTable'."
    ::= { rbtwsApStatDataObjects 5 }

rbtwsApStatRadioStatusMacEntry OBJECT-TYPE
    SYNTAX      RbtwsApStatRadioStatusMacEntry
    MAX-ACCESS  not-accessible
    STATUS      current
    DESCRIPTION
        "Information about a particular radio on an AP attached to the AC."
    INDEX   { rbtwsApStatRadioStatusMacBaseMac }
    ::= { rbtwsApStatRadioStatusMacTable 1 }

RbtwsApStatRadioStatusMacEntry ::= SEQUENCE {
        rbtwsApStatRadioStatusMacBaseMac        MacAddress,
        rbtwsApStatRadioStatusMacApSerialNum    RbtwsApSerialNum,
        rbtwsApStatRadioStatusMacRadioNum       RbtwsRadioNum,

        rbtwsApStatRadioStatusMacEnable             RbtwsRadioEnable,
        rbtwsApStatRadioStatusMacRadioConfigState   RbtwsRadioConfigState,
        rbtwsApStatRadioStatusMacCurrentPowerLevel  RbtwsPowerLevel,
        rbtwsApStatRadioStatusMacCurrentChannelNum  RbtwsChannelNum,

        rbtwsApStatRadioStatusMacClientSessions     Unsigned32
    }

rbtwsApStatRadioStatusMacBaseMac OBJECT-TYPE
    SYNTAX      MacAddress
    MAX-ACCESS  not-accessible
    STATUS      current
    DESCRIPTION
        "The Base MAC address of this radio."
    ::= { rbtwsApStatRadioStatusMacEntry 1 }

rbtwsApStatRadioStatusMacApSerialNum OBJECT-TYPE
    SYNTAX      RbtwsApSerialNum
    MAX-ACCESS  read-only
    STATUS      current
    DESCRIPTION
        "The Serial Number of the AP containing this radio."
    ::= { rbtwsApStatRadioStatusMacEntry 2 }

rbtwsApStatRadioStatusMacRadioNum OBJECT-TYPE
    SYNTAX      RbtwsRadioNum
    MAX-ACCESS  read-only
    STATUS      current
    DESCRIPTION
        "The Number of this Radio on the AP."
    ::= { rbtwsApStatRadioStatusMacEntry 3 }

rbtwsApStatRadioStatusMacEnable OBJECT-TYPE
    SYNTAX      RbtwsRadioEnable
    MAX-ACCESS  read-only
    STATUS      current
    DESCRIPTION
        "The configured mode (enable/disable) of this radio."
    ::= { rbtwsApStatRadioStatusMacEntry 4 }

rbtwsApStatRadioStatusMacRadioConfigState OBJECT-TYPE
    SYNTAX      RbtwsRadioConfigState
    MAX-ACCESS  read-only
    STATUS      current
    DESCRIPTION
        "The configuration state of this radio (INIT, FAIL, OK)."
    ::= { rbtwsApStatRadioStatusMacEntry 5 }

rbtwsApStatRadioStatusMacCurrentPowerLevel OBJECT-TYPE
    SYNTAX      RbtwsPowerLevel
    MAX-ACCESS  read-only
    STATUS      current
    DESCRIPTION
        "The Current Power Level of this radio."
    ::= { rbtwsApStatRadioStatusMacEntry 6 }

rbtwsApStatRadioStatusMacCurrentChannelNum OBJECT-TYPE
    SYNTAX      RbtwsChannelNum
    MAX-ACCESS  read-only
    STATUS      current
    DESCRIPTION
        "The Current Channel Number of this radio."
    ::= { rbtwsApStatRadioStatusMacEntry 7 }

rbtwsApStatRadioStatusMacClientSessions OBJECT-TYPE
    SYNTAX      Unsigned32
    MAX-ACCESS  read-only
    STATUS      current
    DESCRIPTION
        "The number of client sessions on this radio."
    ::= { rbtwsApStatRadioStatusMacEntry 8 }


-- ==================================
-- Radio Service table

rbtwsApStatRadioServiceTable OBJECT-TYPE
    SYNTAX      SEQUENCE OF RbtwsApStatRadioServiceEntry
    MAX-ACCESS  not-accessible
    STATUS      current
    DESCRIPTION
        "A table describing the radio services associated with
        the APs currently present and managed by this AC.
        Same data is available indexed by BSSID in
        'rbtwsApStatRadioServiceMacTable'."
    ::= { rbtwsApStatDataObjects 6 }

rbtwsApStatRadioServiceEntry OBJECT-TYPE
    SYNTAX      RbtwsApStatRadioServiceEntry
    MAX-ACCESS  not-accessible
    STATUS      current
    DESCRIPTION
        "Information about a particular service (SSID) on a radio."
    INDEX   { rbtwsApStatRadioServApSerialNum,
              rbtwsApStatRadioServRadioNum,
              rbtwsApStatRadioServSsid }
    ::= { rbtwsApStatRadioServiceTable 1 }

RbtwsApStatRadioServiceEntry ::= SEQUENCE {
        rbtwsApStatRadioServApSerialNum          RbtwsApSerialNum,
        rbtwsApStatRadioServRadioNum             RbtwsRadioNum,
        rbtwsApStatRadioServSsid                 DisplayString,

        rbtwsApStatRadioServBssid                MacAddress,
        rbtwsApStatRadioServServiceProfileName   DisplayString
    }

rbtwsApStatRadioServApSerialNum OBJECT-TYPE
    SYNTAX      RbtwsApSerialNum
    MAX-ACCESS  not-accessible
    STATUS      current
    DESCRIPTION
        "The Serial Number of the AP containing this radio."
    ::= { rbtwsApStatRadioServiceEntry 1 }

rbtwsApStatRadioServRadioNum OBJECT-TYPE
    SYNTAX      RbtwsRadioNum
    MAX-ACCESS  not-accessible
    STATUS      current
    DESCRIPTION
        "The Number of this Radio on the AP."
    ::= { rbtwsApStatRadioServiceEntry 2 }

rbtwsApStatRadioServSsid OBJECT-TYPE
    SYNTAX      DisplayString
    MAX-ACCESS  not-accessible
    STATUS      current
    DESCRIPTION
        "The service/SSID name in use on this radio."
    ::= { rbtwsApStatRadioServiceEntry 3 }

rbtwsApStatRadioServBssid OBJECT-TYPE
    SYNTAX      MacAddress
    MAX-ACCESS  read-only
    STATUS      current
    DESCRIPTION
        "The MAC address (a.k.a. BSSID) of this service/SSID on this radio."
    ::= { rbtwsApStatRadioServiceEntry 4 }

rbtwsApStatRadioServServiceProfileName OBJECT-TYPE
    SYNTAX      DisplayString
    MAX-ACCESS  read-only
    STATUS      current
    DESCRIPTION
        "The Name of the Service Profile having this SSID
        and associated to the (only) radio profile of this radio."
    ::= { rbtwsApStatRadioServiceEntry 5 }


-- ==========================================
-- Radio Service table indexed by MAC (BSSID)

rbtwsApStatRadioServiceMacTable OBJECT-TYPE
    SYNTAX      SEQUENCE OF RbtwsApStatRadioServiceMacEntry
    MAX-ACCESS  not-accessible
    STATUS      current
    DESCRIPTION
        "A table describing the radio services associated with
        the APs currently present and managed by this AC.
        Same data is available indexed by AP Serial Number,
        Radio Number and SSID in 'rbtwsApStatRadioServiceTable'."
    ::= { rbtwsApStatDataObjects 7 }

rbtwsApStatRadioServiceMacEntry OBJECT-TYPE
    SYNTAX      RbtwsApStatRadioServiceMacEntry
    MAX-ACCESS  not-accessible
    STATUS      current
    DESCRIPTION
        "Information about a particular service (SSID) on a radio."
    INDEX   { rbtwsApStatRadioServMacBssid }
    ::= { rbtwsApStatRadioServiceMacTable 1 }

RbtwsApStatRadioServiceMacEntry ::= SEQUENCE {
        rbtwsApStatRadioServMacBssid                MacAddress,

        rbtwsApStatRadioServMacApSerialNum          RbtwsApSerialNum,
        rbtwsApStatRadioServMacRadioNum             RbtwsRadioNum,
        rbtwsApStatRadioServMacSsid                 DisplayString,
        rbtwsApStatRadioServMacServiceProfileName   DisplayString
    }

rbtwsApStatRadioServMacBssid OBJECT-TYPE
    SYNTAX      MacAddress
    MAX-ACCESS  not-accessible
    STATUS      current
    DESCRIPTION
        "The MAC address (a.k.a. BSSID) of this service/SSID on this radio."
    ::= { rbtwsApStatRadioServiceMacEntry 1 }

rbtwsApStatRadioServMacApSerialNum OBJECT-TYPE
    SYNTAX      RbtwsApSerialNum
    MAX-ACCESS  read-only
    STATUS      current
    DESCRIPTION
        "The Serial Number of the AP containing this radio."
    ::= { rbtwsApStatRadioServiceMacEntry 2 }

rbtwsApStatRadioServMacRadioNum OBJECT-TYPE
    SYNTAX      RbtwsRadioNum
    MAX-ACCESS  read-only
    STATUS      current
    DESCRIPTION
        "The Number of this Radio on the AP."
    ::= { rbtwsApStatRadioServiceMacEntry 3 }

rbtwsApStatRadioServMacSsid OBJECT-TYPE
    SYNTAX      DisplayString
    MAX-ACCESS  read-only
    STATUS      current
    DESCRIPTION
        "The service/SSID name in use on this radio."
    ::= { rbtwsApStatRadioServiceMacEntry 4 }

rbtwsApStatRadioServMacServiceProfileName OBJECT-TYPE
    SYNTAX      DisplayString
    MAX-ACCESS  read-only
    STATUS      current
    DESCRIPTION
        "The Name of the Service Profile having this SSID
        and associated to the (only) radio profile of this radio."
    ::= { rbtwsApStatRadioServiceMacEntry 5 }


-- ============================================================================
--
-- Conformance
--

rbtwsApStatusConformance  OBJECT IDENTIFIER ::= { rbtwsApStatusObjects 2 }
rbtwsApStatusCompliances  OBJECT IDENTIFIER ::= { rbtwsApStatusConformance 1 }
rbtwsApStatusGroups       OBJECT IDENTIFIER ::= { rbtwsApStatusConformance 2 }

-- Compliance

rbtwsApStatusCompliance MODULE-COMPLIANCE
    STATUS      current
    DESCRIPTION
        "The compliance statement for devices that implement AP Status MIB."
    MODULE  -- rbtwsApStatusMib

    MANDATORY-GROUPS {
            rbtwsApStatusCommonGroup
            }

    ::= { rbtwsApStatusCompliances 1 }

-- Units of Conformance

rbtwsApStatusCommonGroup OBJECT-GROUP
        OBJECTS {
                 rbtwsApStatNumAps,
                 rbtwsApStatApStatusBaseMac,
                 rbtwsApStatApStatusAttachType,
                 rbtwsApStatApStatusPortOrDapNum,
                 rbtwsApStatApStatusApState,
                 rbtwsApStatApStatusModel,
                 rbtwsApStatApStatusFingerprint,
                 rbtwsApStatApStatusApName,
                 rbtwsApStatApStatusVlan,
                 rbtwsApStatApStatusIpAddress,
                 rbtwsApStatApStatusUptimeSecs,
                 rbtwsApStatApStatusCpuInfo,
                 rbtwsApStatApStatusManufacturerId,
                 rbtwsApStatApStatusRamBytes,
                 rbtwsApStatApStatusHardwareRev,
                 rbtwsApStatApStatusMacSerialNum,
                 rbtwsApStatApStatusMacAttachType,
                 rbtwsApStatApStatusMacPortOrDapNum,
                 rbtwsApStatApStatusMacApState,
                 rbtwsApStatApStatusMacModel,
                 rbtwsApStatApStatusMacFingerprint,
                 rbtwsApStatApStatusMacApName,
                 rbtwsApStatApStatusMacVlan,
                 rbtwsApStatApStatusMacIpAddress,
                 rbtwsApStatApStatusMacUptimeSecs,
                 rbtwsApStatApStatusMacCpuInfo,
                 rbtwsApStatApStatusMacManufacturerId,
                 rbtwsApStatApStatusMacRamBytes,
                 rbtwsApStatApStatusMacHardwareRev,
                 rbtwsApStatRadioStatusBaseMac,
                 rbtwsApStatRadioStatusEnable,
                 rbtwsApStatRadioStatusRadioConfigState,
                 rbtwsApStatRadioStatusCurrentPowerLevel,
                 rbtwsApStatRadioStatusCurrentChannelNum,
                 rbtwsApStatRadioStatusMacApSerialNum,
                 rbtwsApStatRadioStatusMacRadioNum,
                 rbtwsApStatRadioStatusMacEnable,
                 rbtwsApStatRadioStatusMacRadioConfigState,
                 rbtwsApStatRadioStatusMacCurrentPowerLevel,
                 rbtwsApStatRadioStatusMacCurrentChannelNum,
                 rbtwsApStatRadioServBssid,
                 rbtwsApStatRadioServServiceProfileName,
                 rbtwsApStatRadioServMacApSerialNum,
                 rbtwsApStatRadioServMacRadioNum,
                 rbtwsApStatRadioServMacSsid,
                 rbtwsApStatRadioServMacServiceProfileName
                }
        STATUS      current
        DESCRIPTION
        "Mandatory group of objects implemented to provide AP Status info."
        ::= { rbtwsApStatusGroups 1 }

END
