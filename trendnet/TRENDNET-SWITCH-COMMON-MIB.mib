--  =======================================================================
--  PROPRIETARY MIB FOR TRENDnet Switch PRODUCTS
--  =======================================================================
--  Copyright 2017 Trendnet, Inc.  All Rights Reserved.
--  This is the private MIB for TRENDnet management products.  

--  =======================================================================
--  Version: 1.0.0, 2017.03.30
--  2017.06.05: Removed nway-disabled-1Gigabps-Half(10) for comPortSpeedState.
--  =======================================================================



--  =======================================================================
--  trendnetSwitchCommon MIB Object list:
--  trendnetSwitchCommon     OBJECT IDENTIFIER ::= { trendnet 1 }
--    comModelName            OBJECT IDENTIFIER ::= { trendnetSwitchCommon 1 }
--    comHostName             OBJECT IDENTIFIER ::= { trendnetSwitchCommon 2 }
--    comBootCodeVersion      OBJECT IDENTIFIER ::= { trendnetSwitchCommon 3 }
--    comFirmwareVersion      OBJECT IDENTIFIER ::= { trendnetSwitchCommon 4 }
--    comBuiltDate            OBJECT IDENTIFIER ::= { trendnetSwitchCommon 5 }
--    comSerialNumber         OBJECT IDENTIFIER ::= { trendnetSwitchCommon 6 }
--    comMacAddress           OBJECT IDENTIFIER ::= { trendnetSwitchCommon 7 }
--    comMemoryInfo           OBJECT IDENTIFIER ::= { trendnetSwitchCommon 8 }
--    comCPULoadingInfo       OBJECT IDENTIFIER ::= { trendnetSwitchCommon 9 }
--    comSystemUpTime         OBJECT IDENTIFIER ::= { trendnetSwitchCommon 10 }
--    comPortInfoTable        OBJECT IDENTIFIER ::= { trendnetSwitchCommon 11 }
--      comPortEntry            OBJECT IDENTIFIER ::= { comPortInfoTable 1 }
--        comPortIndex              OBJECT IDENTIFIER ::= { comPortEntry 1 }
--        comPortAdminState         OBJECT IDENTIFIER ::= { comPortEntry 2 }
--        comPortSpeedState         OBJECT IDENTIFIER ::= { comPortEntry 3 }
--        comPortFlowCtrlState      OBJECT IDENTIFIER ::= { comPortEntry 4 }
--        comPortLinkStatus         OBJECT IDENTIFIER ::= { comPortEntry 5 }
--        comPortMediumType         OBJECT IDENTIFIER ::= { comPortEntry 6 }
--        comPortUpTime             OBJECT IDENTIFIER ::= { comPortEntry 7 }
--        comPortStatus             OBJECT IDENTIFIER ::= { comPortEntry 8 }
--        comPortDescr              OBJECT IDENTIFIER ::= { comPortEntry 9 }
--        comPortUtilization        OBJECT IDENTIFIER ::= { comPortEntry 10}
--    comPortStatisticsTable  OBJECT IDENTIFIER ::= { trendnetSwitchCommon 12 }
--      comPortStatisticsEntry  OBJECT IDENTIFIER ::= { comPortStatisticsTable 1 }
--        comPortStatisticsIndex    OBJECT IDENTIFIER ::= { comPortStatisticsEntry 1 }
--        comPortStatisticsInBcastPkt   OBJECT IDENTIFIER ::= { comPortStatisticsEntry 1 }
--        comPortStatisticsInMcastPkt   OBJECT IDENTIFIER ::= { comPortStatisticsEntry 2 }
--        comPortStatisticsInUcastPkt   OBJECT IDENTIFIER ::= { comPortStatisticsEntry 3 }
--        comPortStatisticsInErrorPkt   OBJECT IDENTIFIER ::= { comPortStatisticsEntry 4 }
--        comPortStatisticsOutBcastPkt  OBJECT IDENTIFIER ::= { comPortStatisticsEntry 5 }
--        comPortStatisticsOutMcastPkt  OBJECT IDENTIFIER ::= { comPortStatisticsEntry 6 }
--        comPortStatisticsOutUcastPkt  OBJECT IDENTIFIER ::= { comPortStatisticsEntry 7 }
--        comPortStatisticsOutErrorPkt  OBJECT IDENTIFIER ::= { comPortStatisticsEntry 8 }
--    trendnetSwitchProtocols    OBJECT IDENTIFIER :: = { trendnetSwitchCommon 13 }
--      comLldp             OBJECT IDENTIFIER ::= { trendnetSwitchProtocols 1 }
--        comlldpGlobalConfigMode       OBJECT IDENTIFIER ::= { comLldp 1 }
--	    comAutoProvision    OBJECT IDENTIFIER :: = ( trendnetSwitchProtocols 2}
--        comAutoProvisionState         OBJECT IDENTIFIER :: = ( comAutoProvision 1}
--        comAutoProvisionProtocol      OBJECT IDENTIFIER :: = ( comAutoProvision 2}
--        comAutoProvisionFolderPath    OBJECT IDENTIFIER :: = ( comAutoProvision 3}
--        comAutoProvisionFTPUser       OBJECT IDENTIFIER :: = ( comAutoProvision 4}
--        comAutoProvisionFTPPassword   OBJECT IDENTIFIER :: = ( comAutoProvision 5}
--        comAutoProvisionServerIP      OBJECT IDENTIFIER :: = ( comAutoProvision 6}
--        comAutoProvisionServerIPv6    OBJECT IDENTIFIER :: = ( comAutoProvision 7}
--	  comRebootSystem       OBJECT IDENTIFIER :: = ( trendnetSwitchCommon 14}
--	  comSaveConfiguratins  OBJECT IDENTIFIER :: = ( trendnetSwitchCommon 15}
--	  comCliHookConfiguratins  OBJECT IDENTIFIER :: = ( trendnetSwitchCommon 16} 
--  =======================================================================


TRENDNET-SWITCH-COMMON-MIB DEFINITIONS ::= BEGIN

IMPORTS
MODULE-IDENTITY, 	OBJECT-IDENTITY,
  OBJECT-TYPE, Integer32, enterprises
		FROM SNMPv2-SMI
		
	DisplayString
		FROM SNMPv2-TC;

--  =================================================================
--  PRODUCT IDENTITY
--  =================================================================
trendnet   		            OBJECT IDENTIFIER ::= { enterprises 28866 }

--  =================================================================
--  MODULE IDENTITY
--  =================================================================
trendnetSwitchCommon	MODULE-IDENTITY
    LAST-UPDATED	"201306190000Z"
    ORGANIZATION	"TRENDnet, Inc."
    CONTACT-INFO
            " Customer Services:         		
            http://www.trendnet.com/home"
    DESCRIPTION
            "This is a proprietary MIB for management products."
    REVISION    
			"201305240000Z"
    DESCRIPTION
        	"The Structure of Layer 2 Network Management Information for the
		     proprietary enterprise."
--	    contact IANA for actual number 28866
    ::= { trendnet 1 }        
--  ========================================================================
--	trendnetSwitchCommon		OBJECT IDENTIFIER :: = ( trendnet 1 }
--  ========================================================================

    comModelName OBJECT-TYPE
        SYNTAX  DisplayString (SIZE (0..32))
        MAX-ACCESS  read-only
        STATUS  current
        DESCRIPTION
            "The name of the Switch Model."
        ::= { trendnetSwitchCommon 1 }

    comHostName OBJECT-TYPE
        SYNTAX  DisplayString (SIZE (0..64))
        MAX-ACCESS  read-write
        STATUS  current
        DESCRIPTION
            "The host name of the Switch."
        ::= { trendnetSwitchCommon 2 }

    comBootCodeVersion OBJECT-TYPE
        SYNTAX  DisplayString (SIZE (0..24))
        MAX-ACCESS  read-only
        STATUS  current
        DESCRIPTION
            "The boot code version."
        ::= { trendnetSwitchCommon 3 }

    comFirmwareVersion OBJECT-TYPE
        SYNTAX  DisplayString (SIZE (0..24))
        MAX-ACCESS  read-only
        STATUS  current
        DESCRIPTION
            "The firmware version."
        ::= { trendnetSwitchCommon 4 }

    comBuiltDate OBJECT-TYPE
        SYNTAX  DisplayString (SIZE (0..32))
        MAX-ACCESS  read-only
        STATUS  current
        DESCRIPTION
            "The date of the built firmware."
        ::= { trendnetSwitchCommon 5 }

    comSerialNumber OBJECT-TYPE
        SYNTAX  DisplayString (SIZE (0..35))
        MAX-ACCESS  read-only
        STATUS  current
        DESCRIPTION
            "The serial number of the Switch."
        ::= { trendnetSwitchCommon 6 }

    comMacAddress OBJECT-TYPE
        SYNTAX  OCTET STRING (SIZE (6))
        MAX-ACCESS  read-only
        STATUS  current
        DESCRIPTION
            "The MAC address of the Switch."
        ::= { trendnetSwitchCommon 7 }

    comMemoryInfo OBJECT-TYPE
        SYNTAX  DisplayString (SIZE (0..100))
        MAX-ACCESS  read-only
        STATUS  current
        DESCRIPTION
            "The system memory information."
        ::= { trendnetSwitchCommon 8 }

    comCPULoadingInfo OBJECT-TYPE
        SYNTAX  INTEGER (0..9999)
        MAX-ACCESS  read-only
        STATUS  current
        DESCRIPTION
            "The information about the CPU loading in hundredths of percentage."
        ::= { trendnetSwitchCommon 9 }

    comSystemUpTime	OBJECT-TYPE
        SYNTAX  TimeTicks
		ACCESS	read-only
		STATUS	current
		DESCRIPTION	
			"The time(in hundredths of a second) from CPU start working."
		::= { trendnetSwitchCommon 10 }

--  ------------------------------------------------------------------------
--	comPortInfoTable    OBJECT IDENTIFIER :: = ( trendnetSwitchCommon 11}
--  ------------------------------------------------------------------------

    portInfoTable OBJECT-TYPE 
        SYNTAX SEQUENCE OF PortInfoEntry 
        MAX-ACCESS not-accessible
        STATUS current
        DESCRIPTION "A table that contains information about every port."
        ::= { trendnetSwitchCommon 11 }

    portInfoEntry OBJECT-TYPE
        SYNTAX PortInfoEntry
        MAX-ACCESS not-accessible
        STATUS current
        DESCRIPTION "A list of information for each port of the device."
        INDEX { comPortIndex }
        ::={ portInfoTable 1 }

    comPortIndex OBJECT-TYPE
        SYNTAX INTEGER( 1..65535 )
        MAX-ACCESS read-only
        STATUS current
        DESCRIPTION "This object indicates the module's port number.(1..Max port
	        number in the module)"
        ::={ portInfoEntry 1 }

    comPortAdminState OBJECT-TYPE
        SYNTAX  INTEGER {
               disabled(1),
               enabled(2)
               }
        MAX-ACCESS read-write
        STATUS current
        DESCRIPTION 
            "This object decide the port enabled or disabled."
        ::={ portInfoEntry 2 }

    comPortSpeedState OBJECT-TYPE
        SYNTAX  INTEGER {
               nway-enabled(1),
               nway-disabled-10Mbps-Full(2),
               nway-enabled-10Mbps-Full(3),
               nway-disabled-10Mbps-Half(4),
               nway-disabled-100Mbps-Full(5),
               nway-enabled-100Mbps-Full(6),
               nway-disabled-100Mbps-Half(7),
               nway-disabled-1Gigabps-Full(8),
               nway-enabled-1Gigabps-Full(9)
               }
        MAX-ACCESS read-write
        STATUS      current
        DESCRIPTION
            "Chose the port speed, duplex mode, and N-Way function mode."
        ::= { portInfoEntry 3 }

    comPortFlowCtrlState OBJECT-TYPE
        SYNTAX  INTEGER {
               off(1),
               on(2)
               }
        MAX-ACCESS  read-write
        STATUS      current
        DESCRIPTION
            "This object decide the port flow control is enabled or disabled."
        ::= { portInfoEntry 4 }

    comPortLinkStatus OBJECT-TYPE
        SYNTAX INTEGER {
               other(1),
               link-down(2),
               link-up-10M-full(3),
               link-up-10M-half(4),
               link-up-100M-full(5),
               link-up-100M-half(6),
               link-up-1000M-full(7),
               link-up-1000M-half(8)
               }
        MAX-ACCESS read-only
        STATUS current
        DESCRIPTION "This object indicates the port link status."
        ::={ portInfoEntry 5 }

    comPortMediumType OBJECT-TYPE
        SYNTAX INTEGER{
            other(1),
        	copper(2),
        	fiber(3)
        }
        MAX-ACCESS read-only
        STATUS current
        DESCRIPTION
            "Indicates medium type of the port number."
        ::={portInfoEntry 6}

    comPortUpTime	OBJECT-TYPE
        SYNTAX  DisplayString (SIZE (0..64))
        ACCESS	read-only
        STATUS	current
        DESCRIPTION	
            "The time from last link up."
        ::= { portInfoEntry 7 }

    comPortStatus	OBJECT-TYPE
        SYNTAX  INTEGER{
            normally(0),
            disabled-By-Bpdu-Guard(1),
            disabled-By-Loop-Detection(2),        	
            disabled-By-Poe-Pd-No-Power(4),        	
            disabled-By-Port-Admin(8),            
            disabled-By-Switch-Lock(16),            
            disabled-By-Traffic-Monitor(32),            
            disabled-By-Udld(48),            
            disabled-By-Dual-Homing(4096),
            blocked-By-Erps(8192),            
            blocked-By-Jet-Ring(16384),
            blocked-By-Bpdu-Root-Guard(256),
            bLocked-By-Loop-Detection(512),
            blocked-By-Stp(1024),
            blocked-By-Xpress-Ring(2048) 	
        }
        ACCESS	read-only
        STATUS	current
        DESCRIPTION	
            "The port status information."
        ::= { portInfoEntry 8 }

    comPortDescr	OBJECT-TYPE
        SYNTAX  DisplayString (SIZE (0..100))
        ACCESS  read-write
        STATUS  current
        DESCRIPTION
            "A textual description of the port. It is mandatory that this only contain
             printable ASCII characters."
		::= { portInfoEntry 9 }

    comPortUtilization OBJECT-TYPE
        SYNTAX  INTEGER (0..9999)
        MAX-ACCESS  read-only
        STATUS  current
        DESCRIPTION
            "The information about the port utilization in hundredths of percentage."
        ::= { portInfoEntry 10}

--  ------------------------------------------------------------------------
--	comPortStatisticsTable    OBJECT IDENTIFIER :: = ( trendnetSwitchCommon 12}
--  ------------------------------------------------------------------------

    portStatisticsTable OBJECT-TYPE 
        SYNTAX SEQUENCE OF PortStatisticsEntry 
        MAX-ACCESS not-accessible
        STATUS current
        DESCRIPTION "A table that contains statistics about every port."
        ::= { trendnetSwitchCommon 12 }

    portStatisticsEntry OBJECT-TYPE
        SYNTAX PortStatisticsEntry
        MAX-ACCESS not-accessible
        STATUS current
        DESCRIPTION "A list of statistics for each port of the device."
        INDEX { comPortStatisticsIndex }
        ::={ portStatisticsTable 1 }

    comPortStatisticsIndex OBJECT-TYPE
        SYNTAX INTEGER( 1..65535 )
        MAX-ACCESS read-only
        STATUS current
        DESCRIPTION "This object indicates the module's port number.(1..Max port
	        number in the module)"
        ::={ portStatisticsEntry 1 }

    comPortStatisticsInBcastPkt OBJECT-TYPE
        SYNTAX  Counter32
        MAX-ACCESS read-only
        STATUS current
        DESCRIPTION 
            "The inbound broadcast packet counter."
        ::={ portStatisticsEntry 2 }

    comPortStatisticsInMcastPkt OBJECT-TYPE
        SYNTAX  Counter32
        MAX-ACCESS read-only
        STATUS current
        DESCRIPTION 
            "The inbound multicast packet counter."
        ::={ portStatisticsEntry 3 }

    comPortStatisticsInUcastPkt OBJECT-TYPE
        SYNTAX  Counter32
        MAX-ACCESS read-only
        STATUS current
        DESCRIPTION 
            "The inbound unicast packet counter."
        ::={ portStatisticsEntry 4 }

    comPortStatisticsInErrorPkt OBJECT-TYPE
        SYNTAX  Counter32
        MAX-ACCESS read-only
        STATUS current
        DESCRIPTION 
            "The inbound error packet counter."
        ::={ portStatisticsEntry 5 }

    comPortStatisticsOutBcastPkt OBJECT-TYPE
        SYNTAX  Counter32
        MAX-ACCESS read-only
        STATUS current
        DESCRIPTION 
            "The outbound broadcast packet counter."
        ::={ portStatisticsEntry 6 }

    comPortStatisticsOutMcastPkt OBJECT-TYPE
        SYNTAX  Counter32
        MAX-ACCESS read-only
        STATUS current
        DESCRIPTION
            "The outbound multicast packet counter."
        ::={ portStatisticsEntry 7 }

    comPortStatisticsOutUcastPkt OBJECT-TYPE
        SYNTAX  Counter32
        MAX-ACCESS read-only
        STATUS current
        DESCRIPTION 
            "The outbound unicast packet counter."
        ::={ portStatisticsEntry 8 }

    comPortStatisticsOutErrorPkt OBJECT-TYPE
        SYNTAX  Counter32
        MAX-ACCESS read-only
        STATUS current
        DESCRIPTION 
            "The outbound error packet counter."
        ::={ portStatisticsEntry 9 }

--  ======================================================================================
--	trendnetSwitchProtocols    OBJECT IDENTIFIER ::= { trendnetSwitchCommon 13 }
--  ======================================================================================
trendnetSwitchProtocols    OBJECT IDENTIFIER ::= { trendnetSwitchCommon 13 }

--  ------------------------------------------------------------------------
--	  comLldp   OBJECT IDENTIFIER ::= { trendnetSwitchProtocols 1 }
--  ------------------------------------------------------------------------

comLldp   OBJECT IDENTIFIER ::= { trendnetSwitchProtocols 1 }

comlldpGlobalConfigMode OBJECT-TYPE
    SYNTAX INTEGER { 
       enabled(1), 
       disabled(2)
    }
    MAX-ACCESS  read-write
    STATUS      current
    DESCRIPTION
            "The administratively desired status of the local LLDP protocol.
             
			If the associated lldpGlobalConfigMode object has a
            value of 'enabled(1)', then LLDP protocol will enabled on
			the device.
			
			If the associated lldpGlobalConfigMode object has a
            value of 'disabled(2)', then LLDP protocol will disabled on
			the device.
			
            The default value for lldpGlobalConfigMode object is
            disabled on the device.

            The value of this object must be restored from non-volatile
            storage after a re-initialization of the management system."
    REFERENCE 
            "IEEE 802.1AB-2005 10.5.3.3/Proprietary configuration"
    DEFVAL     { disabled }
    ::= { comLldp 1 }

--  ------------------------------------------------------------------------
--	  comAutoProvision      OBJECT IDENTIFIER :: = ( trendnetSwitchProtocols 2}
--  ------------------------------------------------------------------------

comAutoProvision        OBJECT IDENTIFIER ::= { trendnetSwitchProtocols 2 }

    comAutoProvisionState OBJECT-TYPE 
        SYNTAX  INTEGER {
               disabled(1),
               enabled(2)
               }
        MAX-ACCESS read-write
        STATUS current
        DESCRIPTION "Enabes / Disable the AutoProvision function."
        ::= { comAutoProvision 1 }

    comAutoProvisionProtocol OBJECT-TYPE 
        SYNTAX  INTEGER {
               tftp(1),
               ftp(2),
               http(3)
               }
        MAX-ACCESS read-write
        STATUS current
        DESCRIPTION "Configures the protocol for the AutoProvision function."
        ::= { comAutoProvision 2 }

    comAutoProvisionFolderPath OBJECT-TYPE 
        SYNTAX  DisplayString (SIZE (0..63))
        MAX-ACCESS read-write
        STATUS current
        DESCRIPTION "Configures the folder path of the firmware."
        ::= { comAutoProvision 3 }

    comAutoProvisionFTPUser OBJECT-TYPE 
        SYNTAX  DisplayString (SIZE (0..32))
        MAX-ACCESS read-write
        STATUS current
        DESCRIPTION "Configures the FTP user name."
        ::= { comAutoProvision 4 }

    comAutoProvisionFTPPassword OBJECT-TYPE 
        SYNTAX  DisplayString (SIZE (0..32))
        MAX-ACCESS read-write
        STATUS current
        DESCRIPTION "Configures the FTP password."
        ::= { comAutoProvision 5 }

    comAutoProvisionServerIP OBJECT-TYPE 
        SYNTAX  IpAddress
        MAX-ACCESS read-write
        STATUS current
        DESCRIPTION "Configures the server IP address."
        ::= { comAutoProvision 6 }

    comAutoProvisionServerIPv6 OBJECT-TYPE 
        SYNTAX  DisplayString (SIZE (0..40))
        MAX-ACCESS read-write
        STATUS current
        DESCRIPTION "Configures the server IPv6 address."
        ::= { comAutoProvision 7 }


--  ------------------------------------------------------------------------
--	comRebootSystem    OBJECT IDENTIFIER :: = ( trendnetSwitchCommon 14}
--  ------------------------------------------------------------------------
    comRebootSystem OBJECT-TYPE 
        SYNTAX  INTEGER {
               disabled(1),
               enabled(2)
               }
        MAX-ACCESS read-write
        STATUS current
        DESCRIPTION "Reboot the Switch."
        ::= { trendnetSwitchCommon 14 }

--  ------------------------------------------------------------------------
--	comSaveConfiguratins    OBJECT IDENTIFIER :: = ( trendnetSwitchCommon 15}
--  ------------------------------------------------------------------------
    comSaveConfiguratins OBJECT-TYPE 
        SYNTAX  INTEGER {
               disabled(1),
               enabled(2)
               }
        MAX-ACCESS read-write
        STATUS current
        DESCRIPTION "Save all of the current configurations to NV-RAM."
        ::= { trendnetSwitchCommon 15 }

--  ------------------------------------------------------------------------
--	comCliHookConfiguratins    OBJECT IDENTIFIER :: = ( trendnetSwitchCommon 16}
--  ------------------------------------------------------------------------
    comCliHookConfigurations OBJECT-TYPE 
        SYNTAX  DisplayString (SIZE (0..256))
        MAX-ACCESS read-write
        STATUS current
        DESCRIPTION "Configures the particular command."
        ::= { trendnetSwitchCommon 16 }

    PortInfoEntry ::= 
        SEQUENCE {
            comPortIndex INTEGER,
            comPortAdminState INTEGER,
            comPortSpeedState INTEGER,
            comPortFlowCtrlState INTEGER,
            comPortLinkStatus INTEGER,
            comPortMediumType INTEGER,
            comPortUpTime DisplayString,
            comPortStatus INTEGER,
            comPortDescr DisplayString,
            comPortUtilization INTEGER
        }

    PortStatisticsEntry ::= 
        SEQUENCE {
            comPortStatisticsIndex INTEGER,
            comPortStatisticsInBcastPkt Counter32,
            comPortStatisticsInMcastPkt Counter32,
            comPortStatisticsInUcastPkt Counter32,
            comPortStatisticsInErrorPkt Counter32,
            comPortStatisticsOutBcastPkt Counter32,
            comPortStatisticsOutMcastPkt Counter32,
            comPortStatisticsOutUcastPkt Counter32,
            comPortStatisticsOutErrorPkt Counter32
        }

END
